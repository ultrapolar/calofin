;;; ------------------------------------------------------------------
;;;  check_drawing.lsp -- CHECK: attachment QA for AutoCAD drawings
;;;
;;;  Adds the CHECK command (alias DIMARCCHECK). After asking you to
;;;  highlight the drawing, it runs two audits over the selection:
;;;
;;;  1. Dimensions (linear / aligned / rotated): both definition
;;;     points must lie on an object of some kind (line, arc, circle,
;;;     polyline, ellipse, spline) -- OR on an ANCHOR: a point TWO
;;;     OR MORE DIMENSIONS measure to counts as an object and is left
;;;     exactly where it is, geometry under it or not. Dimensioning
;;;     twice to the same spot -- the pair of dims pinning down a
;;;     hypotenuse corner is the everyday case -- is how you say that
;;;     spot is the object, and CHECK shifts nothing off it; a stray
;;;     point nearer an anchor than any line is shifted onto the
;;;     anchor. A dimension with a stray
;;;     definition point gets:
;;;       - a construction line (XLINE) drawn through its two dimmed
;;;         points on the construction layer (CHECK-CONSTRUCTION,
;;;         yellow, by default),
;;;       - the stray point shifted onto the closest point of the
;;;         closest object,
;;;       - its color changed (red by default) so you can see it was
;;;         shifted.
;;;
;;;  2. Arcs: each arc endpoint must sit at the END of another object.
;;;       - On an object but not at its end -> endpoint moved to the
;;;         closest end of that object.
;;;       - Not on anything -> endpoint moved to the closest endpoint
;;;         of any object in the selection (or, when every nearby
;;;         object is closed, the closest point on the closest one).
;;;     A moved arc is re-fitted through its fixed end, its old
;;;     midpoint and the new end, then recolored (magenta by default).
;;;
;;;  Everything runs inside one UNDO group; a single U reverts every
;;;  change CHECK made. A dimension or arc on a LOCKED layer cannot be
;;;  changed: one that needs a fix is named and counted apart in the
;;;  summary ("NOT shifted"), never passed as clean. Tunables are just
;;;  below.
;;; ------------------------------------------------------------------

;;; SHARED BUILD: requires CALOFIN-LIB.lsp (load via CALOFIN-LOADER.lsp).
;;; Generic helpers live there under cal: - see STANDARDS.md.
;;;

(setq *checkdrawing-version* "v1.12")  ; announced on load; release_lisp.py
                                          ; stamps the dated twin in releases/

(vl-load-com)

;;; ======================================================================
;;;  TUNABLES -- every value CHECK reads that someone might want to
;;;  change lives in this block, and nowhere else in the file.
;;;
;;;  How to change one: edit the number or string, save, and APPLOAD the
;;;  file again.  To try a value for one session only, type the setq at
;;;  the command line -- e.g. (setq *cfchk-tol* 0.001) -- because every
;;;  knob is read when CHECK runs, not when the file loads.
;;;
;;;  Units: distances are drawing units (1 unit = 1 inch on the shop's
;;;  sheets); colours are ACI numbers (1 red, 2 yellow, 3 green, 4 cyan,
;;;  5 blue, 6 magenta, 7 white, 8 grey, 256 ByLayer).
;;; ----------------------------------------------------------------------

;; -- what counts as attached ------------------------------------------

;; A dimension point or an arc end that sits within this distance of
;; an object is ATTACHED and left alone.  It is also the smallest shift
;; CHECK will make, so raising it forgives bigger gaps AND suppresses
;; the small corrections it would otherwise apply; lowering it makes
;; the audit stricter on both counts.
(setq *cfchk-tol*          1.0e-4)  ; drawing units

;; Two dimensions measuring to the same spot make it an ANCHOR: a point
;; that is left exactly where it is, geometry under it or not, and that
;; a stray point nearer to it than to any line is shifted onto.  This
;; is how close two definition points must be to count as one spot.
;; Raising it merges nearby but distinct points into one anchor, which
;; then stops them being corrected.
(setq *cfchk-anchor-tol*   1.0e-4)  ; drawing units

;; ...and how many dimensions must meet there.  2 is the everyday case
;; (the pair of dims pinning a hypotenuse corner).  1 or 0 would make
;; every definition point its own anchor and silently switch the
;; dimension audit off, so keep it at 2 or more.
(setq *cfchk-anchor-min*   2)       ; dimensions meeting at one spot

;; Entity types a dimension point or an arc end may attach to.  Every
;; name must be a curve AutoCAD can measure to (vlax-curve-*); a type
;; that is not is tolerated but never matches.
(setq *cfchk-curve-types*
      '("LINE" "ARC" "CIRCLE" "ELLIPSE" "LWPOLYLINE" "POLYLINE" "SPLINE"))

;; Which kinds of dimension are audited, by the low three bits of DXF
;; group 70: 0 = rotated (horizontal / vertical), 1 = aligned.  The
;; other kinds -- angular (2, 5), diameter (3), radius (4), ordinate
;; (6) -- have no pair of definition points to shift and are counted
;; as "unsupported type skipped".
(setq *cfchk-dim-types*    '(0 1))

;; -- what CHECK draws and recolours -----------------------------------

(setq *cfchk-dim-color*    1)       ; ACI: dimensions whose points were shifted (red)
(setq *cfchk-arc-color*    6)       ; ACI: arcs whose endpoints were snapped (magenta)

;; Construction lines (XLINEs) through the ORIGINAL points of every
;; shifted dimension go on this layer, created on first use; delete or
;; freeze the layer when the review is done.  The colour is applied
;; only when CHECK creates the layer -- a layer already in the drawing
;; keeps its own colour, and the XLINEs draw ByLayer.
(setq *cfchk-constr-layer* "CHECK-CONSTRUCTION")
(setq *cfchk-constr-color* 2)       ; ACI (yellow)

;; -- how the report reads ---------------------------------------------

;; Distances in the command-line report go through (rtos d mode prec):
;; mode 2 is decimal, 3 engineering, 4 architectural (feet-inches);
;; prec is decimal places (for mode 4: the inch is split 2^prec ways).
;; The tolerance is echoed with more places than a shift because it is
;; usually smaller than one.
(setq *cfchk-dist-mode*    2)       ; rtos mode
(setq *cfchk-dist-prec*    4)       ; places for a shift or snap distance
(setq *cfchk-tol-prec*     6)       ; places for the tolerance in the summary

;; -- numerical guards (rarely changed) --------------------------------

;; Two points closer than this are the SAME point: no construction
;; line is drawn through them, an arc is never re-fitted onto its own
;; other end, and a snap target that close to that end is passed over.
;; Only a drawing at an extreme scale should need this moved.
(setq *cfchk-same-pt*      1e-8)    ; drawing units

;; An ARC is only audited when its extrusion normal (DXF 210) is within
;; this of world +Z; a tilted or mirrored (0 0 -1) arc is counted as
;; "non-planar skipped" instead of being re-fitted in the wrong plane.
(setq *cfchk-planar-eps*   1e-9)    ; dimensionless (normal components)

;; Not knobs, on purpose: the collinearity guard inside
;; cfchk:circumcenter (1e-12) and the Continuous linetype
;; cfchk:ensure-layer gives a new layer.  Both helpers are library
;; bodies -- the grouped build takes them from CALOFIN-LIB.lsp -- so a
;; value changed here would be honoured by one build and not the other.
;;; ----------------------------------------------------------------------
;;;  END TUNABLES.  CHECK keeps no state between runs.
;;; ======================================================================

;; --- small helpers -------------------------------------------------

;; A distance as the report prints it (see *cfchk-dist-mode*).
(defun cfchk:dist (d)
  (rtos d *cfchk-dist-mode* *cfchk-dist-prec*))

;; The word for an ACI colour, so the report follows the colour knobs
;; instead of saying "red" whatever *cfchk-dim-color* is set to.
(defun cfchk:color-name (aci / p)
  (setq p (assoc aci '((1 . "red") (2 . "yellow") (3 . "green")
                       (4 . "cyan") (5 . "blue") (6 . "magenta")
                       (7 . "white") (8 . "grey"))))
  (if p (cdr p) (strcat "colour " (itoa aci))))

(defun cfchk:locked-p (ent / lay rec)
  ;; T when ent sits on a LOCKED layer.  entmod answers nil there and
  ;; changes nothing, and a nil from a fix reads as "nothing needed
  ;; fixing" -- so a stray point on a locked DIMS layer, the usual
  ;; state of a finished sheet, was counted checked and clean.  The
  ;; fixers ask this first and answer 'refused instead.
  (setq lay (cdr (assoc 8 (entget ent)))
        rec (if lay (tblsearch "LAYER" lay)))
  (and rec (= 4 (logand 4 (cdr (assoc 70 rec))))))

(defun cfchk:set-color (ent color / ed old)
  (setq ed  (entget ent)
        old (assoc 62 ed))
  (entmod (if old
            (subst (cons 62 color) old ed)
            (append ed (list (cons 62 color)))))
  (entupd ent))

(defun cfchk:make-xline (p1 p2 / len)
  ;; infinite construction line through p1-p2 on the check layer
  (setq len (distance p1 p2))
  (if (> len *cfchk-same-pt*)
    (entmake (list '(0 . "XLINE")
                   '(100 . "AcDbEntity")
                   (cons 8 *cfchk-constr-layer*)
                   '(100 . "AcDbXline")
                   (cons 10 p1)
                   (cons 11 (mapcar '(lambda (x) (/ x len)) (mapcar '- p2 p1)))))))

(defun cfchk:closest-on (ent pt / res)
  ;; closest point on ent to pt; nil when ent is not curve-like
  (setq res (vl-catch-all-apply 'vlax-curve-getClosestPointTo (list ent pt)))
  (if (vl-catch-all-error-p res) nil res))

(defun cfchk:nearest-curve (pt exclude cands / best bestd cp d)
  ;; (ent closest-point distance) for the candidate closest to pt
  (foreach e cands
    (if (and (not (eq e exclude)) (setq cp (cfchk:closest-on e pt)))
      (progn
        (setq d (distance pt cp))
        (if (or (null bestd) (< d bestd))
          (setq bestd d
                best  (list e cp d))))))
  best)

(defun cfchk:curve-ends (ent / cl sp ep)
  ;; the curve's two endpoints; nil when closed (or not a curve)
  (setq cl (vl-catch-all-apply 'vlax-curve-isClosed (list ent)))
  (if (or (vl-catch-all-error-p cl) cl)
    nil
    (progn
      (setq sp (vl-catch-all-apply 'vlax-curve-getStartPoint (list ent))
            ep (vl-catch-all-apply 'vlax-curve-getEndPoint (list ent)))
      (if (or (vl-catch-all-error-p sp) (vl-catch-all-error-p ep))
        nil
        (list sp ep)))))

(defun cfchk:closest-of (pt pts / best bestd d)
  (foreach q pts
    (setq d (distance pt q))
    (if (or (null bestd) (< d bestd)) (setq bestd d best q)))
  best)

(defun cfchk:nearest-end (pt exclude cands / best bestd d)
  ;; closest endpoint over every open candidate curve
  (foreach e cands
    (if (not (eq e exclude))
      (foreach q (cfchk:curve-ends e)
        (setq d (distance pt q))
        (if (or (null bestd) (< d bestd)) (setq bestd d best q)))))
  best)

;; --- geometry ------------------------------------------------------

(defun cfchk:planar-arc-p (ed / n)
  ;; only arcs drawn in the world XY plane are handled
  (setq n (cdr (assoc 210 ed)))
  (or (null n)
      (and (< (abs (car n)) *cfchk-planar-eps*)
           (< (abs (cadr n)) *cfchk-planar-eps*)
           (> (caddr n) 0.0))))

(defun cfchk:rebuild-arc (ent which fixed mid target / c r a1 a2 am tmp ed)
  ;; re-fit the arc through its fixed end, its old midpoint and the
  ;; target point; returns T on success, 'refused when the arc is on a
  ;; locked layer (or entmod turns the write down), nil when no arc
  ;; fits
  (if (and (> (distance target fixed) *cfchk-same-pt*)
           (setq c (cal:circumcenter fixed mid target)))
    (progn
      (setq r  (distance c target)
            a1 (angle c (if (eq which 'start) target fixed))
            a2 (angle c (if (eq which 'start) fixed target))
            am (angle c mid))
      ;; ARC entities always sweep counter-clockwise from start to
      ;; end; keep the sweep that contains the old midpoint
      (if (> (cal:angnorm (- am a1)) (cal:angnorm (- a2 a1)))
        (setq tmp a1
              a1  a2
              a2  tmp))
      (setq ed (entget ent))
      (foreach pair (list (cons 10 c) (cons 40 r) (cons 50 a1) (cons 51 a2))
        (setq ed (subst pair (assoc (car pair) ed) ed)))
      (if (and (not (cfchk:locked-p ent)) (entmod ed))
        (progn (entupd ent) T)
        'refused))))

;; --- audit 1: dimension attachment ---------------------------------

(defun cfchk:dim-def-pts (ent / ed dtype p13 p14)
  ;; the two definition points of a linear/aligned dimension (the ones
  ;; CHECK shifts); nil for every other kind of dimension
  (setq ed    (entget ent)
        dtype (logand 7 (cdr (assoc 70 ed))))
  (if (member dtype *cfchk-dim-types*)
    (progn
      (setq p13 (cdr (assoc 13 ed))
            p14 (cdr (assoc 14 ed)))
      (append (if p13 (list p13)) (if p14 (list p14))))))

(defun cfchk:shared-anchors (dims / recs r e p found out tl)
  ;; Every spot where *cfchk-anchor-min* or more DIMENSIONS put a
  ;; definition point.  Dimensioning twice to the same spot is how a
  ;; drafter says that spot matters -- the usual case is the pair of
  ;; dims that pin down a hypotenuse corner, which is a point in space
  ;; with no line running through it.  CHECK shifts points without
  ;; asking first, so this is the rule that stops it walking such a
  ;; corner onto the nearest wall.
  ;; Returns the anchor points (WCS).
  (foreach e dims
    (foreach p (cfchk:dim-def-pts e)
      ;; the FIRST rec within tol, and stop there: the rest of recs
      ;; cannot change which one that is
      (setq found nil
            tl    recs)
      (while (and tl (null found))
        (if (<= (distance p (caar tl)) *cfchk-anchor-tol*)
          (setq found (car tl)))
        (setq tl (cdr tl)))
      (cond
        ((null found) (setq recs (cons (list p e) recs)))
        ;; a dimension's own two points landing together is one
        ;; dimension, not two -- it takes two to make an anchor
        ((not (member e (cdr found)))
         (setq recs (subst (cons (car found) (cons e (cdr found)))
                           found recs))))))
  (foreach r recs
    (if (>= (length (cdr r)) *cfchk-anchor-min*)
      (setq out (cons (car r) out))))
  out)

(defun cfchk:fix-defpoint (ent gcode cands anchors
                           / ed pt near anch dnear danch sugg dsug)
  ;; shift one definition point onto the closest object when it is
  ;; not already on one; returns the shift distance, nil when it needed
  ;; no shift, 'refused when it did and its layer would not take it.
  ;; A point another dimension also measures to is an ANCHOR and is
  ;; never shifted; an anchor nearer than any object is where a stray
  ;; point goes.
  (setq ed (entget ent)
        pt (cdr (assoc gcode ed)))
  (if pt
    (progn
      (setq near  (cfchk:nearest-curve pt nil cands)
            dnear (if near (caddr near))
            anch  (cfchk:closest-of pt anchors)
            danch (if anch (distance pt anch)))
      (cond
        ((and dnear (<= dnear *cfchk-tol*)) nil)          ; on an object
        ((and danch (<= danch *cfchk-anchor-tol*)) nil)   ; on an anchor
        (t
         (cond
           ((and danch (or (null dnear) (< danch dnear)))
            (setq sugg anch  dsug danch))
           (near
            (setq sugg (cadr near)  dsug dnear)))
         (if (and sugg (> dsug *cfchk-tol*))
           (if (and (not (cfchk:locked-p ent))
                    (entmod (subst (cons gcode sugg) (assoc gcode ed) ed)))
             dsug
             'refused)))))))

(defun cfchk:check-dim (ent cands anchors / ed dtype p13 p14 d1 d2)
  (setq ed    (entget ent)
        dtype (logand 7 (cdr (assoc 70 ed))))
  (if (member dtype *cfchk-dim-types*)      ; rotated/linear or aligned
    (progn
      (setq p13 (cdr (assoc 13 ed))         ; the two dimmed points
            p14 (cdr (assoc 14 ed))
            d1  (cfchk:fix-defpoint ent 13 cands anchors)
            d2  (cfchk:fix-defpoint ent 14 cands anchors))
      (cond
        ;; a stray point CHECK could not move is a fault it found, not a
        ;; clean dimension: named here and counted apart in the summary
        ((or (eq d1 'refused) (eq d2 'refused))
         (princ (strcat "\n  Dimension " (cdr (assoc 5 ed))
                        ": a definition point is off every object, but layer "
                        (cond ((cdr (assoc 8 ed))) ("0")) " is locked - NOT shifted."))
         'locked)
        ((or d1 d2)
         (cfchk:make-xline p13 p14)        ; through the ORIGINAL points
         (cfchk:set-color ent *cfchk-dim-color*)
         (entupd ent)
         (princ (strcat "\n  Dimension " (cdr (assoc 5 ed)) ":"
                        (if d1 (strcat " point 1 shifted " (cfchk:dist d1)) "")
                        (if d2 (strcat " point 2 shifted " (cfchk:dist d2)) "")
                        " onto the nearest object or anchor; recolored "
                        (cfchk:color-name *cfchk-dim-color*) "."))
         'fixed)
        (t 'ok)))
    'skipped))

;; --- audit 2: arc endpoint attachment ------------------------------

(defun cfchk:snap-end (ent which other mid p target / r)
  ;; re-fit the arc so its end lands on target: the snap distance when
  ;; it did, 'refused when the arc's layer is locked, nil when no arc fits
  (setq r (cfchk:rebuild-arc ent which other mid target))
  (cond ((eq r 'refused) 'refused)
        (r (distance p target))))

(defun cfchk:fix-arc-end (ent which cands / p other mid near ends target)
  ;; returns the snap distance when the endpoint was moved, 'refused
  ;; when it needed moving and its layer is locked, else nil
  (setq mid   (vlax-curve-getPointAtDist
                ent
                (/ (vlax-curve-getDistAtParam ent (vlax-curve-getEndParam ent)) 2.0))
        p     (if (eq which 'start)
                (vlax-curve-getStartPoint ent)
                (vlax-curve-getEndPoint ent))
        other (if (eq which 'start)
                (vlax-curve-getEndPoint ent)
                (vlax-curve-getStartPoint ent))
        near  (cfchk:nearest-curve p ent cands))
  (cond
    ((null near) nil)                       ; nothing to attach to at all
    ((<= (caddr near) *cfchk-tol*)          ; endpoint sits on an object...
     (setq ends (cfchk:curve-ends (car near)))
     ;; never snap onto the arc's own other endpoint
     (setq ends (vl-remove-if '(lambda (q) (< (distance q other) *cfchk-same-pt*))
                              ends))
     (cond
       ((null ends) nil)                    ; closed curve: no ends to demand
       ((vl-some '(lambda (q) (<= (distance p q) *cfchk-tol*)) ends)
        nil)                                ; ...and at one of its ends: OK
       (t                                   ; ...but mid-object: closest end of that object
        (setq target (cfchk:closest-of p ends))
        (cfchk:snap-end ent which other mid p target))))
    (t                                      ; floating: closest end anywhere,
     (setq target (cfchk:nearest-end p ent cands))
     (if (or (null target) (< (distance target other) *cfchk-same-pt*))
       (setq target (cadr near)))           ; else closest point on closest object
     (cfchk:snap-end ent which other mid p target))))

(defun cfchk:check-arc (ent cands / ed d1 d2)
  (setq ed (entget ent))
  (if (cfchk:planar-arc-p ed)
    (progn
      (setq d1 (cfchk:fix-arc-end ent 'start cands)
            d2 (cfchk:fix-arc-end ent 'end cands))
      (cond
        ((or (eq d1 'refused) (eq d2 'refused))
         (princ (strcat "\n  Arc " (cdr (assoc 5 ed))
                        ": an end is not at the end of any object, but layer "
                        (cond ((cdr (assoc 8 ed))) ("0")) " is locked - NOT snapped."))
         'locked)
        ((or d1 d2)
         (cfchk:set-color ent *cfchk-arc-color*)
         (princ (strcat "\n  Arc " (cdr (assoc 5 ed)) ":"
                        (if d1 (strcat " start snapped " (cfchk:dist d1)) "")
                        (if d2 (strcat " end snapped " (cfchk:dist d2)) "")
                        " to nearest object end; recolored "
                        (cfchk:color-name *cfchk-arc-color*) "."))
         'fixed)
        (t 'ok)))
    'skipped))

;; --- command -------------------------------------------------------

(defun c:CHECK ( / *error* oldecho undo-open ss i e et cands dims arcs res
                   anchors ndf ndo nds ndl naf nao nas nal)
  (defun *error* (msg)
    (if undo-open
      (progn (setvar "CMDECHO" 0) (vl-catch-all-apply 'command-s (list "_.UNDO" "_End"))))
    (if oldecho (setvar "CMDECHO" oldecho))
    (if (and msg (not (wcmatch (strcase msg) "*BREAK*,*CANCEL*,*QUIT*,*EXIT*")))
      (princ (strcat "\nCHECK error: " msg)))
    (if lzd:report (lzd:report "CHECK" *checkdrawing-version* msg))
    (princ))
  (if lzd:begin (lzd:begin "CHECK" *checkdrawing-version*))

  ;; a pickfirst selection if there is one, otherwise ask for it
  (setq ss (ssget "_I"))
  (if lzd:watch (lzd:watch ss) ss)
  (if (null ss)
    (progn
      (prompt "\nHighlight the drawing to CHECK: ")
      (setq ss (ssget))
      (if lzd:watch (lzd:watch ss) ss)))
  (cond
    ((null ss)
     (prompt "\nNothing selected - CHECK cancelled."))
    (t
     (setq cands nil dims nil arcs nil i 0
           ndf 0 ndo 0 nds 0 ndl 0 naf 0 nao 0 nas 0 nal 0)
     (repeat (sslength ss)
       (setq e  (ssname ss i)
             i  (1+ i)
             et (cdr (assoc 0 (entget e))))
       (if (= et "DIMENSION") (setq dims (cons e dims)))
       (if (= et "ARC") (setq arcs (cons e arcs)))
       (if (member et *cfchk-curve-types*) (setq cands (cons e cands))))
     (setq dims  (reverse dims)
           arcs  (reverse arcs)
           cands (reverse cands))
     (cond
       ((and (null dims) (null arcs))
        (prompt "\nSelection holds no dimensions or arcs - nothing to check."))
       ((null cands)
        (prompt "\nSelection holds no lines/arcs/curves to attach to - nothing to check against."))
       (t
        (setq oldecho (getvar "CMDECHO"))
        (setvar "CMDECHO" 0)
        ;; only when undo is recording - _Begin in a drawing with UNDO
        ;; off (bit 1 of UNDOCTL clear) errors out of the command
        (if (= 1 (logand 1 (getvar "UNDOCTL")))
          (progn
            (command "_.UNDO" "_Begin")
            (setq undo-open T)))
        (cal:ensure-layer *cfchk-constr-layer* *cfchk-constr-color*)
        ;; spots two or more dimensions measure to are anchors: a
        ;; hypotenuse corner is dimmed twice precisely because there is
        ;; no line through it, so those points are objects as far as
        ;; this audit is concerned and nothing shifts off them
        (setq anchors (cfchk:shared-anchors dims))
        (if anchors
          (princ (strcat "\n" (itoa (length anchors))
                         " point(s) carry " (itoa *cfchk-anchor-min*)
                         " or more dimensions - treated"
                         " as anchors and left alone.")))
        (foreach e dims
          (setq res (cfchk:check-dim e cands anchors))
          (cond ((eq res 'fixed)   (setq ndf (1+ ndf)))
                ((eq res 'skipped) (setq nds (1+ nds)))
                ((eq res 'locked)  (setq ndl (1+ ndl)))
                (t                 (setq ndo (1+ ndo)))))
        (foreach e arcs
          (setq res (cfchk:check-arc e cands))
          (cond ((eq res 'fixed)   (setq naf (1+ naf)))
                ((eq res 'skipped) (setq nas (1+ nas)))
                ((eq res 'locked)  (setq nal (1+ nal)))
                (t                 (setq nao (1+ nao)))))
        ;; closed only if one was opened -- the same guard the handler
        ;; above makes.  With undo recording off (UNDOCTL bit 1 clear)
        ;; there is no group of this run's, and an _End on nothing is an
        ;; error of its own: it would land here, with every dimension
        ;; and arc already fixed and the CMDECHO putback below it
        (if undo-open
          (progn
            (command "_.UNDO" "_End")
            (setq undo-open nil)))
        (setvar "CMDECHO" oldecho)
        (princ (strcat "\n--- CHECK complete (attachment tolerance "
                       (rtos *cfchk-tol* *cfchk-dist-mode* *cfchk-tol-prec*)
                       ") ---"
                       "\nDimensions: " (itoa (+ ndf ndo ndl)) " checked, "
                       (itoa ndf) " shifted onto nearest object ("
                       (cfchk:color-name *cfchk-dim-color*) ")"
                       (if (> ndl 0)
                         (strcat ", " (itoa ndl)
                                 " stray on a locked layer - NOT shifted")
                         "")
                       (if (> nds 0)
                         (strcat ", " (itoa nds) " unsupported type skipped")
                         "")
                       "\nArcs: " (itoa (+ naf nao nal)) " checked, "
                       (itoa naf) " with endpoint(s) snapped ("
                       (cfchk:color-name *cfchk-arc-color*) ")"
                       (if (> nal 0)
                         (strcat ", " (itoa nal)
                                 " loose on a locked layer - NOT snapped")
                         "")
                       (if (> nas 0)
                         (strcat ", " (itoa nas) " non-planar skipped")
                         "")
                       (if (> ndf 0)
                         (strcat "\nConstruction lines through the shifted dimensions' points are on layer "
                                 *cfchk-constr-layer* ".")
                         "")
                       (if (> (+ ndl nal) 0)
                         "\nUnlock those layers and run CHECK again to fix them."
                         "")
                       "\nOne UNDO reverts everything CHECK changed."))))))
  (if lzd:end (lzd:end "CHECK"))
  (princ))

(defun c:DIMARCCHECK () (c:CHECK))

(defun c:CHECKVER ()
  (princ (strcat "\nCHECK " *checkdrawing-version*))
  (princ))

;; -------------------- self tests ---------------------------------------
;; What LAZDIAG runs on the drafter's machine after this tool fails, and
;; writes into the report: the tool's own helpers on inputs whose answers
;; are KNOWN, so the report says whether the arithmetic was sound where
;; it ran.  (label expression expected) passes when the value is equal
;; to expected (to 1e-6); (label expression) passes when it is not nil,
;; and the value is written down either way.  Nothing here may prompt,
;; draw or (command): it is evaluated from inside *error*.
;; tests/test_selftests.py runs every entry in the VM at both tiers.
(defun cfchk:selftests ()
  (list
    (list "angnorm folds -90 into [0, 2pi)"
          '(cal:angnorm (- (* 0.5 pi)))                       (* 1.5 pi))
    (list "angnorm brings a full turn to 0"
          '(cal:angnorm (* 2.0 pi))                           0.0)
    (list "circumcenter of a right angle is the hypotenuse's midpoint"
          '(cal:circumcenter '(0 0 0) '(4 0 0) '(0 4 0))      '(2.0 2.0 0))
    (list "circumcenter takes z from the first point"
          '(caddr (cal:circumcenter '(0 0 5) '(4 0 0) '(0 4 0)))  5)
    (list "circumcenter refuses three collinear points"
          '(cal:circumcenter '(0 0 0) '(1 1 0) '(2 2 0))      nil)
    (list "color-name has a word for red"
          '(cfchk:color-name 1)                                 "red")
    (list "color-name spells an ACI it has no word for"
          '(cfchk:color-name 141)                               "colour 141")
    (list "planar-arc-p takes an arc with no normal as world XY"
          '(cfchk:planar-arc-p '((0 . "ARC")))                  T)
    (list "planar-arc-p refuses a mirrored (0 0 -1) arc"
          '(cfchk:planar-arc-p '((0 . "ARC") (210 0.0 0.0 -1.0)))  nil)
    (list "closest-of picks the nearest of a list"
          '(cfchk:closest-of '(0 0) '((3 0) (1 1) (5 5)))       '(1 1))))

(foreach c '("CHECK")
  (setq *calofin-selftests*
        (cons (cons c 'cfchk:selftests) *calofin-selftests*)))

;; Quiet inside the whole build: LAZPASS.lsp and
;; CALOFIN-LOADER.lsp set the flag while they load their members,
;; because one file's greeting is a greeting and sixty-three of
;; them is a wall the drafter scrolls past in every drawing they
;; open.  APPLOADed alone the flag is nil and this prints, which
;; is the one time somebody wants to be told.  CALVER reports the
;; whole roster whenever it is asked.
(if (not *calofin-quiet*)
  (princ (strcat "\ncheck_drawing.lsp " *checkdrawing-version*
                 " loaded - type CHECK to audit dimension & arc attachment.")))
(princ)
