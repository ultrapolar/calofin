;;; ======================================================================
;;; TYLERDRONE.lsp  --  the whole calofin build, plus one button
;;; ----------------------------------------------------------------------
;;; Built 2026-08-31 by tools/build_drone_edition.py -- DO NOT EDIT.
;;; Edit the files under lisp/ and rebuild.
;;;
;;; APPLOAD this one file.  Two things land on the toolbar strip:
;;;
;;;   the orange HEXAGON   opens the LazPanel roster, as ever
;;;   the orange TRIANGLE  runs TYLERDRONESUITE on one click
;;;
;;; The triangle is the only thing this build adds to LAZPASS.lsp,
;;; which is otherwise carried here whole.  LAZPASS itself puts up
;;; one external button on purpose -- there the suite rides the
;;; panel like every other tool -- and that is unchanged; this is
;;; the build for someone who runs the drone job all day and wants
;;; it under the cursor.
;;; ======================================================================
;;; ======================================================================
;;; LAZPASS.lsp  --  calofin v3.0, the whole shared build in one file
;;; ----------------------------------------------------------------------
;;; GENERATED - do not edit.  Rebuild it with:
;;;     python3 tools/build_shared_bundle.py
;;;
;;; APPLOAD this ONE file and every command below comes with it.
;;; Nothing else needs loading, and it does not matter what folder
;;; you run it from - there are no sibling files to find.
;;;
;;; 52 files, 128 commands:
;;;
;;;   ABCDEF  ABCDEFVER  ABCURCHECK  ABCURCHECKRESCUE  ABCURCHECKSCAN  ABCURCHECKVER
;;;   ABFIND  ABFINDVER  ABHD  ABHDCOVER  ABMOVE  ADAB
;;;   ALTABCDEF  AUTOBEAD  AUTOBEADVER  AUTODIM  AUTODIMSIDEPOV  BPCALLOUT
;;;   CABHD  CABHDVER  CALVER  CCPRECHECK  CDCALLOUT  CDCREATE
;;;   CDCREATEVER  CHECK  CONSTELLATION  CONSTELLATIONVER  CORNERSTP  COVERCHECK
;;;   COVERCHECKRESCUE  COVERCHECKVER  COVERCHECKVERSION  COVERSCAN  CPERPPTS  CUSTBLOCK
;;;   CUSTBLOCKVER  DCE  DDALT  DDCAL  DDELEV  DDFIX
;;;   DDGPS  DDINFO  DDSET  DDTEST  DIMARCCHECK  DIMCHECK
;;;   DIMCHECKRESCUE  DIMCHECKVER  DIMCONTEND  DIMSCAN  DRONE  FITABHD
;;;   FITABHDCOVER  FITABHDVER  FLOORDIM  HEMISTEP  LAZASCII  LAZBUTTON
;;;   LAZFORM  LAZFORMCOVER  LAZFORMVER  LAZICON  LAZPANEL  LAZPANELVER
;;;   LAZPIN  LAZSPA  LAZSPAVER  LAZSTEP  LAZSTEPVER  LAZTXT
;;;   LHD  LINCHECK  LINFINCHECK  LINFINCHECKRESCUE  LINFINCHECKVER  LINFINSCAN
;;;   LINTXTCHK  LITECOVERSCAN  LITELINFINSCAN  LITESPACHECKSCAN  NORMIESTEP  OASIS
;;;   OASISVER  PADDLE  PERPPTS  POOL  POOLCOVER  POOLDEMO
;;;   POOLVER  SMARTFILLET  SMARTFILLETVER  SPA  SPACHECK  SPACHECKRESCUE
;;;   SPACHECKSCAN  SPACHECKVER  SPAVER  STAIRDIM  STOCKCOVER  STOCKCOVER-CFG
;;;   STOCKLIST  TUTORIALABHD  TUTORIALADAB  TUTORIALAUTOBEAD  TUTORIALCORNERSTP  TUTORIALCOVERCHECK
;;;   TUTORIALCOVERCHECKCLEAN  TUTORIALCPERPPTS  TUTORIALDIMCHECK  TUTORIALDIMSCAN  TUTORIALHEMISTEP  TUTORIALLINFINCHECK
;;;   TUTORIALLINFINSCAN  TUTORIALNORMIESTEP  TUTORIALPADDLE  TUTORIALPERPPTS  TUTORIALPOOL  TUTORIALSPA
;;;   TUTORIALSPACHECK  TYDRN  TYLERDRONESUITE  WCALST  XFTCONV  XFTCONV-SETUP
;;;   XYPLOT  XYPLOTVER
;;;
;;; Included verbatim, in CALOFIN-LOADER.lsp's order, library first.
;;;
;;; Deliberately NOT in this build (see cal:*held-back* in
;;; CALOFIN-LOADER.lsp):
;;;
;;;   LISPLAB.lsp          OMITTED
;;; ======================================================================

;; tells CALOFIN-LIB.lsp it is arriving as part of the whole build
(setq cal:*build-loading* T)


;;; ======================================================================
;;; >>> CALOFIN-LIB.lsp
;;; ======================================================================

;;; ======================================================================
;;; CALOFIN-LIB.lsp  --  the shared helper library for the calofin tools
;;; ----------------------------------------------------------------------
;;; For AutoCAD 2018 and later (plain AutoLISP + ActiveX for bboxes).
;;;
;;; Every routine in shared/ calls these helpers instead of embedding its
;;; own copy, so this file must be loaded FIRST -- APPLOAD LOADER.lsp and
;;; the order is handled for you.  The standalone builds in lisp/ do not
;;; use this file; they embed their own copies and load alone.
;;;
;;; Namespace: cal: for every function, cal:*name* for every global.
;;; The Back sentinel returned by the ask helpers is the symbol CAL-BACK.
;;;
;;; Each helper is the proven implementation lifted from the tool named
;;; beside it, behavior-identical unless a comment says otherwise.  The
;;; divergent variants deliberately NOT absorbed here (POOL/SPA's unit
;;; that returns (0.0 0.0), abhd/lhd's 2-element circumcenter, the
;;; tutorials' pause polarity, ...) stay in their own tools -- see
;;; STANDARDS.md section 6.
;;;
;;; Command:  CALVER   print the loaded library version
;;; ======================================================================

(vl-load-com)

(setq cal:*version* "v1.3")

(defun c:CALVER ()
  (princ (strcat "\nCALOFIN-LIB " cal:*version*))
  (princ))

;;; -------------------- ask layer ---------------------------------------
;;; From pool:askkw / spa:askkw (POOL.LSP:557, byte-identical twins).
;;; kws is the initget string, shown the bracketed list, dflt the Enter
;;; answer (nil = an answer is required).  Returns the keyword or CAL-BACK.
;;; Undo is accepted everywhere Back is, as a hidden synonym.

(defun cal:askkw (msg kws shown dflt back / v)
  (initget (if dflt 0 (if back 0 1))
           (if back (strcat kws " Back Undo") kws))
  (setq v (getkword (strcat "\n" msg " [" shown
                            (if back "/Back" "") "]"
                            (if dflt (strcat " <" dflt ">") "") ": ")))
  (cond ((member v '("Back" "Undo")) 'CAL-BACK)
        ((null v) (if dflt dflt (cal:askkw msg kws shown dflt back)))
        (t v)))

;; Yes/No that can be backed out of.  Returns T, nil or CAL-BACK.
;; From pool:askyn (POOL.LSP:568).
(defun cal:askyn (msg dflt back / v)
  (setq v (cal:askkw msg "Yes No" "Yes/No" dflt back))
  (if (eq v 'CAL-BACK) v (= v "Yes")))

;; Distance entry with the kind system of STANDARDS.md section 3:
;; REQ required, NAX accepts NA, ZER accepts NA and zero, SUG offers a
;; default that Enter takes.  Returns the number, nil for NA, or
;; CAL-BACK.  (From pool:asks / spa:asks, POOL.LSP:522, with the
;; order-sheet highlighting left behind in POOL -- a generated drawing
;; has no entity to light up.)
(defun cal:askdist (kind msg dflt back / v kw)
  ;; Undo is accepted everywhere Back is, as a hidden synonym
  (setq kw (cond ((eq kind 'REQ) (if back "Back Undo" nil))
                 (back "NA Back Undo")
                 (t "NA")))
  ;; REQ always rejects zero - offering Back must not loosen what
  ;; counts as a valid measurement; ZER alone admits 0
  (if kw
      (initget (cond ((eq kind 'ZER) 5)
                     ((and (eq kind 'SUG) dflt) 6)
                     (t 7))
               kw)
      (initget 7))
  (setq v (getdist
            (strcat "\n" msg
                    (cond ((eq kind 'REQ) "")
                          ((eq kind 'SUG)
                           (if dflt (strcat " <" (rtos dflt) "> (or NA)")
                               " (or NA)"))
                          (t " (or NA if not measured)"))
                    (if back " [Back]" "")
                    ": ")))
  (cond ((and (= (type v) 'STR) (member v '("Back" "Undo"))) 'CAL-BACK)
        ((= (type v) 'STR) nil)               ; NA
        ((and (null v) (eq kind 'SUG)) dflt)  ; Enter took the suggestion
        (t v)))

;; The Treatment question of STANDARDS.md section 2: "How should
;; <subject> be treated?"  Returns "Square", "Radius", "Cut" or
;; "NotGiven" -- the legacy words and NG are accepted typed in full and
;; normalized HERE, never downstream -- or CAL-BACK.
(defun cal:asktreat (subject dflt back / v kws)
  ;; the bracket is DERIVED from the visible words (section 1 rule 1),
  ;; so it cannot drift from the initget list; the hidden aliases go on
  ;; the initget list only
  (setq kws "Square Radius Cut NotGiven")
  (setq v (cal:askkw (strcat "How should " subject " be treated?")
                     (strcat kws " NG 90 ROUNDED DIAG DIAGONAL")
                     (vl-string-translate " " "/" kws)
                     dflt back))
  (cond ((eq v 'CAL-BACK) v)
        ((= v "NG") "NotGiven")
        ((= v "90") "Square")
        ((= v "ROUNDED") "Radius")
        ((member v '("DIAG" "DIAGONAL")) "Cut")
        (t v)))

;; Yes/No with the default baked into the prompt and no Back -- the
;; review-loop form.  From cchk:ask-yn / cchk:ask-ny (covercheck.lsp:489,
;; 495; dchk:/lfc: identical) with the default as an argument: pass
;; "Yes" for the old ask-yn, "No" for the cautious ask-ny.  The caller
;; supplies any leading \n in msg, as the originals did.
(defun cal:ask-yn (msg dflt / ans)
  (initget "Yes No")
  (setq ans (getkword (strcat msg " [Yes/No] <" dflt ">: ")))
  (if (null ans) (setq ans dflt))
  (= ans "Yes"))

;; The reviewing question, with a way out of a mis-press.  Returns the
;; symbols yes / no / back / skip.  From cchk:ask-yn-nav
;; (covercheck.lsp:501; dchk:/lfc: byte-identical).
(defun cal:ask-yn-nav (msg / ans)
  (initget "Yes No Back Skip Undo")   ; Undo = hidden synonym for Back
  ;; the bracket is exactly the keyword list (STANDARDS section 1 rule
  ;; 1): a click sends the bracket text, and "Skip rest" was a click
  ;; the initget list could not accept
  (setq ans (getkword (strcat msg " [Yes/No/Back/Skip] <Yes>: ")))
  (cond ((null ans)      'yes)
        ((= ans "Yes")   'yes)
        ((= ans "No")    'no)
        ((= ans "Back")  'back)
        ((= ans "Undo")  'back)
        (t               'skip)))

;; Typed prompts cannot take keywords, so Back is typed like a value.
;; The shared predicate (pf:back-word, lin:back-word, chk:back-word,
;; cdo:backp, dd-back-word -- all byte-identical).
(defun cal:back-word-p (s)
  (member (strcase s) '("B" "BACK" "U" "UNDO")))

;; Free-text entry (notes, feet-inch dimensions).  Returns the string
;; (Enter = dflt when one is given) or CAL-BACK.
(defun cal:askstr (msg dflt back / v)
  (setq v (getstring T (strcat "\n" msg
                               (if dflt (strcat " <" dflt ">") "")
                               (if back " (B = back)" "") ": ")))
  (cond ((and back (cal:back-word-p v)) 'CAL-BACK)
        ((= v "") (if dflt dflt v))
        (t v)))

;; The one pause wording of STANDARDS.md section 3, for new code.  The
;; POOL/SPA tutorials keep their own pauses -- theirs can stop the
;; tutorial, and the two disagree about which answer means stop.
(defun cal:pause ()
  (getstring "\n--- press Enter to continue ---")
  (princ))

;;; -------------------- system variables --------------------------------
;;; The snapshot lives in a GLOBAL and is taken only when no snapshot is
;;; already pending: if a previous run died before restoring, the stale
;;; snapshot still holds the user's TRUE settings.  Saving again at that
;;; point would capture the zeroed OSMODE and every later run would
;;; faithfully "restore" 0.  (From pool:/spa:syssave, POOL.LSP:5504.)
;;; Restore runs in the saved order, so put OSMODE first in the list --
;;; object snaps are the setting the user misses most if a run is ever
;;; cut short partway.

(defun cal:syssave (vars / v)
  (if (not cal:*sysold*)
      (foreach v vars
        (if (/= nil (getvar v))
            (setq cal:*sysold*
                  (append cal:*sysold* (list (cons v (getvar v)))))))))

(defun cal:sysrestore ( / p)
  (foreach p cal:*sysold* (setvar (car p) (cdr p)))
  (setq cal:*sysold* nil))

;; The current dimension style is read-only to setvar, so it has its own
;; snapshot pair and restores via a command.  (From spa:syssave/:restore.)
(defun cal:dimstysave ()
  (if (not cal:*odstyle*) (setq cal:*odstyle* (getvar "DIMSTYLE"))))

(defun cal:dimstyrestore ()
  ;; called from *error* handlers, where a bare (command ...) can itself
  ;; fail -- so command-s under vl-catch-all-apply (STANDARDS section 5)
  (if (and cal:*odstyle* (tblsearch "DIMSTYLE" cal:*odstyle*))
      (vl-catch-all-apply 'command-s
        (list "_.-DIMSTYLE" "_Restore" cal:*odstyle*)))
  (setq cal:*odstyle* nil))

;; T when MSG is the message of a plain cancel (Esc, quit) rather than
;; a real error.  The canonical test of STANDARDS section 5 -- ten
;; hand-copied variants of it existed, two with the same typo, which is
;; why it is a helper now.
(defun cal:error-cancel-p (msg)
  (and msg (wcmatch (strcase msg) "*BREAK*,*CANCEL*,*QUIT*,*EXIT*")))

;; One undo group per command, in the one casing (STANDARDS section 5).
;; Track the open group in a local and close it from *error* too:
;;   (setq undo-open (cal:undobegin))
;;   ... (if undo-open (cal:undoend)) ...
(defun cal:undobegin ()
  (command "_.UNDO" "_Begin")
  T)

(defun cal:undoend ()
  (command "_.UNDO" "_End")
  nil)

;; The user's own object snaps stay LIVE during every measurement
;; prompt; OSMODE is zeroed only while a routine feeds points to
;; commands, where a snap would grab the wrong geometry.  Coupled to
;; the cal:syssave snapshot.  (From pool:/spa:osup, POOL.LSP:480.)
(defun cal:osup ( / p)
  (setq p (assoc "OSMODE" cal:*sysold*))
  (if p (setvar "OSMODE" (cdr p))))

(defun cal:osdown () (setvar "OSMODE" 0))

;;; -------------------- layers ------------------------------------------

;; Create the output layer, or - when it already exists - make sure it
;; is on, thawed and unlocked.  Without this a successful run onto a
;; frozen or switched-off layer looks like the command did nothing.
;; Returns the layer NAME in every case (WCALST draws on the return
;; value).  (From pf:ensure-layer, abhd.lsp:1402; announcement kept,
;; tool prefix dropped.)  Point it at OUTPUT layers only -- the review
;; tools' consent-based unlock of SELECTION layers is a different job.
(defun cal:ensure-layer (name color / rec ed flags col fixed)
  (if (not (tblsearch "LAYER" name))
    (entmakex (list '(0 . "LAYER") '(100 . "AcDbSymbolTableRecord")
                    '(100 . "AcDbLayerTableRecord")
                    (cons 2 name) '(70 . 0) (cons 62 color)
                    '(6 . "Continuous")))
    (progn
      (setq rec   (tblobjname "LAYER" name)
            ed    (entget rec)
            flags (cdr (assoc 70 ed))
            col   (cdr (assoc 62 ed))
            fixed nil)
      (if (/= 0 (logand 5 flags))          ; frozen (1) or locked (4)
        (setq ed    (subst (cons 70 (- flags (logand 5 flags)))
                           (assoc 70 ed) ed)
              fixed T))
      (if (< col 0)                        ; layer switched off
        (setq ed    (subst (cons 62 (abs col)) (assoc 62 ed) ed)
              fixed T))
      (if fixed
        (progn
          (entmod ed)
          (princ (strcat "\nLayer " name
                         " was off, frozen or locked - restored so the"
                         " result is visible."))))))
  name)

;; T when layer NAME exists and can be drawn on right now.  A read-only
;; test -- it repairs nothing.  (From cs-layerok, CORNERSTP.lsp:308.)
(defun cal:layer-usable-p (name / ld f cl)
  (if (setq ld (tblsearch "LAYER" name))
    (progn
      (setq f  (cond ((cdr (assoc 70 ld))) (0))
            cl (cond ((cdr (assoc 62 ld))) (7)))
      (and (zerop (logand 1 f))                  ; not frozen
           (zerop (logand 4 f))                  ; not locked
           (> cl 0)))))                          ; not off

;;; -------------------- 2-D vector helpers ------------------------------
;;; Strictly 2-element results; inputs may be 2- or 3-element (the Z is
;;; dropped).  From the pf:/lh: set (abhd.lsp:330), the most defensive
;;; of the nine copies.  POOL/SPA keep their own unit -- theirs returns
;;; (0.0 0.0) for a zero vector where this one returns nil, and callers
;;; branch on that.  AutoDim keeps its mapcar 3-D set (cal:dotn/midn).

(defun cal:2d (p) (list (car p) (cadr p)))
(defun cal:dist (a b) (distance (cal:2d a) (cal:2d b)))
(defun cal:v- (a b) (mapcar '- (cal:2d a) (cal:2d b)))
(defun cal:v+ (a b) (mapcar '+ (cal:2d a) (cal:2d b)))
(defun cal:v* (v s) (list (* (car v) s) (* (cadr v) s)))
(defun cal:dot (a b) (+ (* (car a) (car b)) (* (cadr a) (cadr b))))
(defun cal:mid (a b) (cal:v* (cal:v+ a b) 0.5))
(defun cal:perp (v) (list (- (cadr v)) (car v))) ; rotate 90 deg CCW
(defun cal:vlen (v) (sqrt (cal:dot v v)))
(defun cal:d2 (a b / dx dy)                      ; squared 2-D distance
  (setq dx (- (car a) (car b)) dy (- (cadr a) (cadr b)))
  (+ (* dx dx) (* dy dy)))
(defun cal:cross (a b)                           ; 2-D scalar cross
  (- (* (car a) (cadr b)) (* (cadr a) (car b))))

;; v scaled to length 1; nil for a (near-)zero vector.
(defun cal:unit (v / l)
  (setq v (cal:2d v)
        l (cal:vlen v))
  (if (> l 1e-12) (cal:v* v (/ 1.0 l))))

;;; Length-preserving (N-element) variants, for the tools whose vectors
;;; carry their Z: the check family's overlap machinery and AutoDim.
;;; mapcar is strict -- both arguments must be the same length.

;; From cchk:unit (covercheck.lsp:638; dchk:/lfc: byte-identical).
(defun cal:unitn (v / l)
  (setq l (distance '(0.0 0.0 0.0) v))
  (if (> l 1e-12)
    (mapcar '(lambda (x) (/ x l)) v)))

(defun cal:dotn (p q) (apply '+ (mapcar '* p q)))          ; ad:dot
(defun cal:midn (p1 p2)                                    ; ad:mid
  (mapcar '(lambda (a b) (* 0.5 (+ a b))) p1 p2))

;; signed distance of p along the axis through a with unit dir u
;; (cchk:proj-param, covercheck.lsp:644)
(defun cal:proj-param (p a u)
  (apply '+ (mapcar '* (mapcar '- p a) u)))

;; the point at parameter s on that axis (cchk:axis-pt)
(defun cal:axis-pt (a u s)
  (mapcar '+ a (mapcar '(lambda (x) (* x s)) u)))

;; distance from p to the infinite line through a with unit dir u
;; (cchk:pt-line-dist)
(defun cal:pt-line-dist (p a u / s)
  (setq s (cal:proj-param p a u))
  (distance p (cal:axis-pt a u s)))

;;; -------------------- angles ------------------------------------------

;; normalize an angle into [0, 2pi).  (Eight tools agree on this range;
;; acady-norm-ang folds into (-pi, pi] instead and keeps its own name.)
(defun cal:angnorm (a)
  (while (< a 0.0) (setq a (+ a pi pi)))
  (while (>= a (+ pi pi)) (setq a (- a pi pi)))
  a)

;; smallest signed angular difference (to - from), in (-pi, pi]
;; (pf:signed-dang, abhd.lsp:375)
(defun cal:signed-dang (from to / d)
  (setq d (cal:angnorm (- to from)))
  (if (> d pi) (- d (* 2.0 pi)) d))

;; distance between two folded directions, in [0, pi/2]
;; (cchk:ang-diff, covercheck.lsp:844)
(defun cal:ang-diff (a b / d)
  (setq d (abs (- a b)))
  (min d (- pi d)))

;;; -------------------- circle / arc geometry ---------------------------

;; center of the circle through three points (plan view, z taken from
;; p1); nil when the points are collinear.  (cchk:circumcenter,
;; covercheck.lsp:580; the check family's 4-way-identical form.  abhd
;; and lhd keep their 2-element, looser-gated pf:/lh:circumcenter.)
(defun cal:circumcenter (p1 p2 p3 / ax ay bx by cx cy d)
  (setq ax (car p1) ay (cadr p1)
        bx (car p2) by (cadr p2)
        cx (car p3) cy (cadr p3)
        d  (* 2.0 (+ (* ax (- by cy)) (* bx (- cy ay)) (* cx (- ay by)))))
  (if (> (abs d) 1e-12)
    (list (/ (+ (* (+ (* ax ax) (* ay ay)) (- by cy))
                (* (+ (* bx bx) (* by by)) (- cy ay))
                (* (+ (* cx cx) (* cy cy)) (- ay by)))
             d)
          (/ (+ (* (+ (* ax ax) (* ay ay)) (- cx bx))
                (* (+ (* bx bx) (* by by)) (- ax cx))
                (* (+ (* cx cx) (* cy cy)) (- bx ax)))
             d)
          (caddr p1))))

;;; -------------------- bounding boxes ----------------------------------
;;; Nested-point form ((minx miny minz) (maxx maxy maxz)) throughout.
;;; abhd/lhd keep their flat 4-tuple point-list pf:/lh:bbox -- their
;;; label layout reads it with caddr/cadddr.

;; one entity, or nil when it has no box (cchk:bbox, covercheck.lsp:421)
(defun cal:bbox-ent (ent / obj ll ur)
  (setq obj (vlax-ename->vla-object ent))
  (if (not (vl-catch-all-error-p
             (vl-catch-all-apply 'vla-getboundingbox (list obj 'll 'ur))))
    (list (vlax-safearray->list ll) (vlax-safearray->list ur))))

;; a whole selection set, nil-safe (ad:ssbox, AutoDim.lsp:191)
(defun cal:bbox-ss (ss / i obj ll ur mn mx)
  (setq i 0)
  (if ss
    (repeat (sslength ss)
      (setq obj (vlax-ename->vla-object (ssname ss i))
            i   (1+ i))
      (if (not (vl-catch-all-error-p
                 (vl-catch-all-apply 'vla-getboundingbox (list obj 'll 'ur))))
        (progn
          (setq ll (vlax-safearray->list ll)
                ur (vlax-safearray->list ur)
                mn (if mn (mapcar 'min mn ll) ll)
                mx (if mx (mapcar 'max mx ur) ur))))))
  (if mn (list mn mx)))

;;; -------------------- lists -------------------------------------------

;; the list from index K on (pf:nthcdr, abhd.lsp:357)
(defun cal:nthcdr (k lst)
  (while (> k 0) (setq lst (cdr lst) k (1- k)))
  lst)

;; COUNT elements of LST starting at index K (pf:sublist).  Running
;; past the end conses nils, exactly as the original does.
(defun cal:sublist (lst k count / out)
  (setq lst (cal:nthcdr k lst))
  (while (> count 0)
    (setq out   (cons (car lst) out)
          lst   (cdr lst)
          count (1- count)))
  (reverse out))

;; drop every point within EPS of a kept one, order preserved
;; (pf:dedupe, abhd.lsp:826, with the epsilon as an argument.
;; perp_points keeps its own consecutive-only dedupe -- different
;; algorithm, different results.)
(defun cal:dedupe (pts eps / out q p dup)
  (foreach q pts
    (setq dup nil)
    (foreach p out
      (if (< (cal:dist p q) eps) (setq dup T)))
    (if (not dup) (setq out (cons q out))))
  (reverse out))

;;; -------------------- numbers -----------------------------------------

;; smallest integer >= X (X non-negative)  (pf:ceil, abhd.lsp:352)
(defun cal:ceil (x / f)
  (setq f (fix x))
  (if (> x f) (1+ f) f))

;; Tangent with the angle clamped just short of +/-90 degrees, so a
;; degenerate half-turn bulge yields a huge but finite number instead
;; of dividing by zero.  (pf:tan, abhd.lsp:347.)
(defun cal:tan (x)
  (cond ((> x  1.5697) (setq x  1.5697))    ; 89.94 deg
        ((< x -1.5697) (setq x -1.5697)))
  (/ (sin x) (cos x)))

;;; -------------------- strings -----------------------------------------

;; Trim leading / trailing blanks (spaces, tabs); nil-safe.
;; (abcdef:trim, abcdef.lsp:50 -- the strongest of the four string
;; trims.  chk:trim / lin:trim / stock:trim are different functions
;; and keep their own names.)
(defun cal:trim (s / i n)
  (if (null s) (setq s ""))
  (setq n (strlen s) i 1)
  (while (and (<= i n) (member (substr s i 1) '(" " "\t")))
    (setq i (1+ i)))
  (setq s (substr s i))
  (setq n (strlen s))
  (while (and (> n 0) (member (substr s n 1) '(" " "\t")))
    (setq s (substr s 1 (1- n)) n (1- n)))
  s)

;; Pad S with spaces to width W (pf:pad, five byte-identical copies)
(defun cal:pad (s w)
  (while (< (strlen s) w) (setq s (strcat s " ")))
  s)

;; zero-pad an integer to two digits (cchk:pad2)
(defun cal:zeropad2 (n)
  (if (< n 10) (strcat "0" (itoa n)) (itoa n)))

;; "YYYY-MM-DD HH:MM" -- CDATE decoded arithmetically so DIMZIN (which
;; trims rtos output) cannot mangle it (cchk:datestr, three-way
;; byte-identical)
(defun cal:datestr (/ d dd tt)
  (setq d  (getvar "CDATE")
        dd (fix d)
        tt (- d dd))
  (strcat (itoa (fix (/ dd 10000))) "-"
          (cal:zeropad2 (rem (fix (/ dd 100)) 100)) "-"
          (cal:zeropad2 (rem dd 100)) " "
          (cal:zeropad2 (fix (+ (* tt 100) 1e-6))) ":"
          (cal:zeropad2 (rem (fix (+ (* tt 10000) 1e-4)) 100))))

;;; -------------------- entity creation ---------------------------------

;; plain TEXT at pt (wc:text, wcalst.lsp:396).  POOL/SPA keep their own
;; text helpers -- theirs run the point through the insertion-base
;; offset first.
(defun cal:text (pt hgt str lay)
  (entmake
    (list '(0 . "TEXT") (cons 8 lay)
          (list 10 (car pt) (cadr pt) 0.0)
          (cons 40 hgt) (cons 1 str))))

;; entmake an MTEXT, splitting into 250-char DXF chunks; returns the
;; new ename, or nil.  (cchk:mtext body, covercheck.lsp:541, minus the
;; per-tool xdata tag -- the check tools tag the returned ename
;; themselves.)
(defun cal:mtext (ins hgt wid str lay / dxf)
  (setq dxf (list '(0 . "MTEXT")
                  '(100 . "AcDbEntity")
                  (cons 8 lay)
                  '(100 . "AcDbMText")
                  (cons 10 ins)
                  (cons 40 hgt)
                  (cons 41 wid)
                  '(71 . 1)))                  ; attachment: top-left
  (while (> (strlen str) 250)
    (setq dxf (append dxf (list (cons 3 (substr str 1 250))))
          str (substr str 251)))
  (if (entmake (append dxf (list (cons 1 str))))
    (entlast)))

;;; -------------------- point blocks ------------------------------------

;; The name carried by a point block, read from its TAG attribute; when
;; the block has no such attribute, the first attribute whose value
;; reads as a number is taken instead (survey exports do not all use
;; the ab_pt tag).  nil when neither exists.  (lh:block-number,
;; lhd.lsp:671, with the tag as an argument.)
(defun cal:block-number (en tag / sub ed val fall v)
  (setq sub (entnext en) val nil fall nil)
  (while (and sub
              (setq ed (entget sub))
              (= "ATTRIB" (cdr (assoc 0 ed))))
    (setq v (cdr (assoc 1 ed)))
    (if (and (null val)
             (cdr (assoc 2 ed))
             (= (strcase (cdr (assoc 2 ed))) (strcase tag)))
      (setq val v))
    (if (and (null fall) v (distof v 2))
      (setq fall v))
    (setq sub (entnext sub)))
  (if val val fall))

;;; ----------------------------------------------------------------------
(princ (strcat "\nCALOFIN-LIB " cal:*version*
               " loaded.  Shared helpers under the cal: prefix."))
;; On its own this file defines helpers and exactly one command
;; (CALVER) -- no tools at all.  LAZPASS.lsp and CALOFIN-LOADER.lsp
;; both set the flag below before loading it, so this only ever fires
;; when someone APPLOADs the library by itself and would otherwise be
;; left wondering why not one command exists.
(if (not cal:*build-loading*)
  (progn
    (princ "\n[calofin] That is the helper library ONLY - it defines no tools.")
    (princ "\n[calofin] APPLOAD LAZPASS.lsp for the whole build instead.")))
(princ)


;;; ======================================================================
;;; >>> POOL.lsp
;;; ======================================================================

;;; ====================================================================
;;;  POOL.LSP -- Swimming-pool as-built layout tool
;;;
;;;  Commands:  POOL     - lay out a pool from field measurements
;;;             POOLVER  - report which revision is loaded
;;;
;;; SHARED BUILD: requires CALOFIN-LIB.lsp (load via CALOFIN-LOADER.lsp).
;;; Generic helpers live there under cal: - see STANDARDS.md.
;;;
;;;  Draws a pool plan (Rectangle, Oval, Grecian, L or Lazy L) from
;;;  field measurements.
;;;
;;;  First asks whether the pool is IN-SQUARE or OUT-OF-SQUARE.  An
;;;  in-square pool is built true to the side/end measurements and no
;;;  cross dims (diagonals) are asked for or drawn.  An out-of-square
;;;  pool takes the full cross-dim route described below.
;;;
;;;  Rectangle corners may be Square, Radius, Cut (a chamfer, sized
;;;  by its face length) or NotGiven -- not recorded on the order
;;;  sheet, so drawn square and flagged.  Side lengths are always to
;;;  the TRUE corner; the treatment cuts inward.  In-square assumes all
;;;  four corners identical; out-of-square asks per corner (Enter
;;;  reuses the previous corner).  When corners are cut and the pool is
;;;  out-of-square, the cross dims are measured from one of: the true
;;;  Corner, the Middle of the cut/arc, or its Ends (both endpoints of
;;;  each diagonal).  Square corners -> cross dims from the true corner.
;;;
;;;  Out-of-square details:
;;;
;;;    * A gray "guide" pool appears as soon as the shape is chosen;
;;;      while each measurement is prompted for, the matching element
;;;      of the guide turns red so you can see which dimension is
;;;      being asked for.  The guide is LIVE: every answer reshapes it
;;;      on the spot (the way an OASIS preview redraws before every
;;;      question), so the pool on screen grows out of the numbers as
;;;      they are typed instead of sitting at a fixed nominal size.
;;;      Once every dimension is in, the guide deletes itself and is
;;;      replaced by the true out-of-square pool.
;;;    * The full pool PERIMETER on layer POOL -- around the whole
;;;      shape including the Grecian corner cuts and oval end arcs
;;;      (drawn as individual lines/arcs, i.e. an exploded polyline).
;;;      Field measurements carry human error, so side lengths may be
;;;      held within +/-1" and cross dimensions within +/-2" of the
;;;      given values.
;;;    * Reference lines that are not part of the perimeter (the body
;;;      end lines under oval/Grecian ends, the oval radius
;;;      construction lines) go on POOL-NOTES with a DASHED linetype
;;;      (when acad.lin / acadiso.lin can be found).
;;;    * An exact as-measured two-triangle check (each triangle uses
;;;      one side, one end and the shared A-C cross dimension -- held
;;;      EXACTLY, no tolerance) is computed and reported as the
;;;      TRI CHECK B-D report row; the check figure itself is not
;;;      drawn, so out-of-square pools leave a clean drawing.
;;;    * Aligned dimensions for all sides and cross dims on layer
;;;      DIMENSION.  The two cross dims are drawn in the "CROSS
;;;      DIMENSION" dimension style when the drawing has one.
;;;    * A target / actual / delta report table to the right of the
;;;      drawing on POOL-NOTES.  When the cross dimensions cannot be
;;;      met within tolerance the sides are held true, the cross dims
;;;      get as close as possible, and "CROSS DIMS FAILED" is written
;;;      under the table.
;;;
;;;  Corner naming (plan view):   D ---------- C
;;;                               |            |     cross dims:
;;;                               |            |     A-C and B-D
;;;                               A ---------- B
;;;
;;;  Oval:    adds a radius line perpendicular to each end and a
;;;           three-point arc (end corner -> radius tip -> other end
;;;           corner) on both ends, plus a total-length check.  A SIDE
;;;           length that was not taped may be answered NA: the
;;;           overall spends its length on the two end bulges and the
;;;           straight body, so the side reads back off it.  An end
;;;           radius that was not given either is taken TANGENT to the
;;;           box around the pool -- the semicircle a true oval has --
;;;           which makes the side the overall less the width.
;;;  Grecian: 8-corner pool (body A/B/C/D plus angled-end tips
;;;           LT/LB left and RT/RB right).  Prompts for the six body
;;;           sides/ends, the four end diagonals and two end widths,
;;;           then cross dims at one of three detail levels:
;;;             Simple  = A-C, B-D            (2)
;;;             Center  = + LB-RT, LT-RB      (4, long tip-to-tip X)
;;;             Complex = every diagonal      (18, all pairs; NA any)
;;;           All 8 corners are best-fit against every provided cross
;;;           dim, so more cross dims pin the out-of-square shape down
;;;           more tightly.
;;;  L/LazyL: six-corner pools with one wing (square step joint for
;;;           the true L, angled joint for the lazy L); six sides plus
;;;           up to six cross dims, best-fit the same way.  An
;;;           IN-SQUARE lazy L is built rather than fitted: the main
;;;           section A-B / E-F / F-A (the deep end, where the hopper
;;;           is measured from) is held EXACTLY and comes out a true
;;;           rectangle, the 45-degree bends B-C and D-E stay
;;;           parallel, and whatever the six measurements fail to
;;;           close by is spread over the three WING sides.  Past the
;;;           1" side tolerance that is a bad tape, so those sides are
;;;           dimensioned red, listed red in the report and called out
;;;           as "SIDES DO NOT CLOSE" under it.
;;;
;;;  Every cross-dim prompt also accepts NA when that measurement was
;;;  not taken in the field: the fitter skips it and the report shows
;;;  N/A for its target and delta.
;;;
;;;  Drawing units are assumed to be INCHES (tolerances: 1" sides,
;;;  2" cross dims, 1/2" max Grecian diagonal adjustment in 1/8"
;;;  steps).  Values may be typed in the current drawing units, e.g.
;;;  20'6-1/2" when units are set to Architectural.
;;;
;;;  Written in plain AutoLISP (entmake + classic commands, no
;;;  ActiveX/VLA), so it loads in AutoCAD 2018 as well as older
;;;  releases.
;;; ====================================================================

;;; -------------------- version ---------------------------------------
;;;
;;;  This file is distributed under two names with IDENTICAL contents:
;;;
;;;      POOL.LSP                 the static name, for the APPLOAD stack
;;;      POOL_MMDDYY_REV##.LSP    the same file, named for its revision
;;;
;;;  Load either one.  The version below travels inside both, so a
;;;  stack that loaded the static name can still say which revision it
;;;  holds: type POOLVER.  Regenerate the pair with
;;;  tools/release_lisp.py.

(setq pool:*version* "082726 REV17")

;;; -------------------- adjustable constants --------------------------

(setq pool:*side-tol*  1.0)     ; side length tolerance (drawing units)
(setq pool:*cross-tol* 2.0)     ; cross dimension tolerance
(setq pool:*grec-step* 0.125)   ; Grecian diagonal adjustment increment
(setq pool:*grec-max*  4)       ; max increments each way (4 * 1/8 = 1/2)
(setq pool:*base*      (list 0.0 0.0))
(setq pool:*dashlt*    "CONTINUOUS")  ; resolved to DASHED per run
(setq pool:*dotlt*     "CONTINUOUS")  ; resolved to POOLDOT per run
(setq pool:*lts*       1.0)           ; (legacy, unused: see pool:ltsc)
(setq pool:*mlkoff*    30.0)          ; M/L/K dim line offset right of the hopper
(setq pool:*pvents*    nil)           ; live guide-preview entities
(setq pool:*insq*      nil)           ; T = in-square pool (no cross dims)
;; Entities making up the side profile (section) and its depth dims.
;; An L pool's mirror flips the PLAN top-to-bottom; a longitudinal
;; section is unchanged by that, so these are held out of it.
(setq pool:*profents*  nil)

;; Bottom-type keywords, shared by the rectangle / oval / grecian
;; dispatchers.  Normal and the four special bottoms all run through
;; pool:hopnormal (they are the same plan chain with G and/or E
;; pinned); Sport is the symmetric full-width bottom.  L / Lazy L
;; pools take the standard hopper only and are not asked.
(setq pool:*btypes*   "Normal Sport Wedge SLope MOdflat SHallow")
(setq pool:*btshown* "Normal/Sport/Wedge/SLope/MOdflat/SHallow")
(setq pool:*sq4* (list (list "Square" 0.0) (list "Square" 0.0)
                       (list "Square" 0.0) (list "Square" 0.0)))
;; How far off 90 a corner may sit and still be marked "90%%d" on the
;; sheet.  This separates two POPULATIONS, so it wants to sit between
;; them rather than hug either: a pool the crew still calls a
;; rectangle can fit several degrees off square (240x120 with cross
;; dims 12" apart fits at 86.8 / 93.2), while the corners this gate
;; exists to refuse -- a grecian's cut corners and an L's bend -- are
;; 135, a full 45 degrees away.  20 degrees clears any real rectangle
;; and still leaves more than twice that margin to 135.
(setq pool:*sq90-tol* (* pi (/ 20.0 180.0)))
(setq pool:*valnotes* nil)            ; validation problems for the report
(setq pool:*undogrp*  nil)            ; an UNDO group of ours is open

;; Measurements under pool:*smalldim* are dimensioned in the drawing's
;; "STANDARD INCHES" dim style (see pool:dimsbegin); the missing-style
;; note is printed at most once per run.  Cross dims (the diagonal
;; block, any shape) use pool:*crossstyle* instead -- see pool:dimxbegin.
;;
;; The SECONDARY perimeter letters -- the ones the field sheets stack
;; against an overall (S, S1, T, V, the end radii, an L's wing/step
;; sides, the six-sided hopper's W/L1/X) -- go in pool:*sidestyle*
;; ("SIDE STANDARD"), per the reference drawings.  A dim inside a
;; SIDE STANDARD block keeps that style even under 24 inches: the
;; reference sheets show a 19" S1 in SIDE STANDARD, not inches.
;; The cut-off is "UNDER 24 inches": a 2 ft corner is a STANDARD dim,
;; not an inches one.  It has to be read with a hair of tolerance,
;; because most of these lengths are not the number the crew typed --
;; they are measured back off geometry the routine built from it, and a
;; 24" radius corner comes back as 23.99999999999913 as readily as
;; 24.000000000001137 (a three-point arc's circumcentre, a treated
;; corner's two end points).  Compared raw, the same 2 ft corner draws
;; in inches or not depending on which way the last bit fell.  The
;; tolerance is float noise only -- a MILLIONTH of an inch, a million
;; times the noise it absorbs and orders below the 1/16" a tape can
;; read, so every real measurement under 2 ft is still an inches dim.
(setq pool:*smalldim*    24.0)
(setq pool:*smallfuzz*   1.0e-6)
(setq pool:*smallstyle*  "STANDARD INCHES")
(setq pool:*smallwarned* nil)
(setq pool:*crossstyle*  "CROSS DIMENSIONS")
(setq pool:*sidestyle*   "SIDE STANDARD")
(setq pool:*sideon*      nil)         ; a SIDE STANDARD block is open
(setq pool:*dimstyle0*   nil)         ; dim style current when POOL started
;; T = report lengths in feet-inches; set per run from the units the
;; DRAWING was in before POOL switched to architectural for its
;; prompts (getdist keeps only the value, never how it was typed, so
;; the drawing's own units are the crew's declared preference).
(setq pool:*ftin*        nil)

;;; -------------------- small vector helpers --------------------------

(defun pool:d2r (a) (* pi (/ a 180.0)))

(defun pool:unit (p / d)
  (setq d (sqrt (cal:dot p p)))
  (if (> d 1.0e-12) (cal:v* p (/ 1.0 d)) (list 0.0 0.0)))

;; local 2D point -> world 3D point (applies the insertion base)
(defun pool:wp (p)
  (list (+ (car p) (car pool:*base*))
        (+ (cadr p) (cadr pool:*base*))
        0.0))

;;; -------------------- geometry ---------------------------------------

;; Intersection of circle (c1 r1) with circle (c2 r2).
;; side = 1.0 -> point on the left of the c1->c2 direction, -1.0 -> right.
;; Returns a 2D point or nil when the circles do not intersect.
(defun pool:circint (c1 r1 c2 r2 side / d ux uy a h2 h bx by)
  (setq d (distance c1 c2))
  (if (> d 1.0e-9)
      (progn
        (setq ux (/ (- (car c2) (car c1)) d)
              uy (/ (- (cadr c2) (cadr c1)) d)
              a  (/ (+ (* d d) (* r1 r1) (- (* r2 r2))) (* 2.0 d))
              h2 (- (* r1 r1) (* a a)))
        (if (> h2 -1.0e-6)
            (progn
              (setq h  (sqrt (max h2 0.0))
                    bx (+ (car c1) (* a ux))
                    by (+ (cadr c1) (* a uy)))
              (list (+ bx (* side h (- uy)))
                    (+ by (* side h ux))))))))

;; Circumcenter of three points, or nil when collinear.
(defun pool:circum (p1 p2 p3 / ax ay bx by cx cy dd)
  (setq ax (car p1) ay (cadr p1)
        bx (car p2) by (cadr p2)
        cx (car p3) cy (cadr p3)
        dd (* 2.0 (+ (* ax (- by cy)) (* bx (- cy ay)) (* cx (- ay by)))))
  (if (> (abs dd) 1.0e-9)
      (list (/ (+ (* (+ (* ax ax) (* ay ay)) (- by cy))
                  (* (+ (* bx bx) (* by by)) (- cy ay))
                  (* (+ (* cx cx) (* cy cy)) (- ay by)))
               dd)
            (/ (+ (* (+ (* ax ax) (* ay ay)) (- cx bx))
                  (* (+ (* bx bx) (* by by)) (- ax cx))
                  (* (+ (* cx cx) (* cy cy)) (- bx ax)))
               dd))))

;;; -------------------- entity makers ----------------------------------

;; Create the output layer, or - when it already exists - make sure it
;; is on, thawed and unlocked (STANDARDS section 5).  Without the repair
;; a run onto a frozen or switched-off DIMENSION layer looks like the
;; command drew nothing.
(defun pool:layer (name color / rec ed flags col fixed)
  (if (not (tblsearch "LAYER" name))
      (entmake (list '(0 . "LAYER")
                     '(100 . "AcDbSymbolTableRecord")
                     '(100 . "AcDbLayerTableRecord")
                     (cons 2 name)
                     '(70 . 0)
                     (cons 62 color)
                     '(6 . "Continuous")))
      (progn
        (setq rec   (tblobjname "LAYER" name)
              ed    (entget rec)
              flags (cdr (assoc 70 ed))
              col   (cdr (assoc 62 ed))
              fixed nil)
        (if (/= 0 (logand 5 flags))          ; frozen (1) or locked (4)
            (setq ed    (subst (cons 70 (- flags (logand 5 flags)))
                               (assoc 70 ed) ed)
                  fixed T))
        (if (< col 0)                        ; layer switched off
            (setq ed    (subst (cons 62 (abs col)) (assoc 62 ed) ed)
                  fixed T))
        (if fixed
            (progn
              (entmod ed)
              (princ (strcat "\nPOOL: layer " name
                             " was off, frozen or locked - restored so"
                             " the result is visible."))))))
  name)

(defun pool:line (p1 p2 lay)
  (entmake (list '(0 . "LINE")
                 (cons 8 lay)
                 (cons 10 (pool:wp p1))
                 (cons 11 (pool:wp p2)))))

;; Build a linetype from an explicit pattern (positive = dash length,
;; 0 = dot, negative = gap), all in drawing units (inches).  Done with
;; entmake rather than loading acad.lin: a failed load used to fall
;; back to CONTINUOUS silently, which is why dashes could vanish.
;; Returns the linetype name.
(defun pool:ltmake (name descr pat / lst x)
  (if (not (tblsearch "LTYPE" name))
      (progn
        (setq lst (list '(0 . "LTYPE")
                        '(100 . "AcDbSymbolTableRecord")
                        '(100 . "AcDbLinetypeTableRecord")
                        (cons 2 name)
                        '(70 . 0)
                        (cons 3 descr)
                        '(72 . 65)
                        (cons 73 (length pat))
                        (cons 40 (apply '+ (mapcar 'abs pat)))))
        (foreach x pat
          (setq lst (append lst (list (cons 49 x) '(74 . 0)))))
        (entmake lst)))
  (if (tblsearch "LTYPE" name) name "CONTINUOUS"))

;; Per-entity linetype scale that cancels the drawing's LTSCALE, so a
;; pattern defined in inches always plots at that size no matter how
;; the host drawing is set up.
(defun pool:ltsc ( / s)
  (setq s (getvar "LTSCALE"))
  (if (or (null s) (<= s 0.0)) 1.0 (/ 1.0 s)))

;; Kept for compatibility: our patterns are self-defined now.
(defun pool:ltload (name)
  (if (= name "DOT")
      (pool:ltmake "POOLDOT" "Pool guide dot . . . . . . . ." '(0.0 -1.0))
      (pool:ltmake "POOLDASH" "Pool dashed __ __ __ __" '(12.0 -12.0))))

;; Dashed reference line on POOL-NOTES.
(defun pool:lined (p1 p2)
  (entmake (append (list '(0 . "LINE")
                         (cons 8 "POOL-NOTES")
                         (cons 10 (pool:wp p1))
                         (cons 11 (pool:wp p2)))
                   (if (/= pool:*dashlt* "CONTINUOUS")
                       (list (cons 6 pool:*dashlt*)
                             (cons 48 (pool:ltsc)))))))

;; Dotted WHITE guide line -- the cross dims and other measuring lines
;; on the input screen, so they read clearly over the pool outline.
(defun pool:linedot (p1 p2)
  (entmake (append (list '(0 . "LINE")
                         (cons 8 "POOL-NOTES")
                         (cons 62 pool:*pvx-col*)
                         (cons 10 (pool:wp p1))
                         (cons 11 (pool:wp p2)))
                   (if (/= pool:*dotlt* "CONTINUOUS")
                       (list (cons 6 pool:*dotlt*)
                             (cons 48 (pool:ltsc)))))))

(defun pool:text (pt h str lay)
  (entmake (list '(0 . "TEXT")
                 (cons 8 lay)
                 (cons 10 (pool:wp pt))
                 (cons 40 h)
                 (cons 1 str))))

(defun pool:textc (pt h str lay col)
  (entmake (list '(0 . "TEXT")
                 (cons 8 lay)
                 (cons 62 col)
                 (cons 10 (pool:wp pt))
                 (cons 40 h)
                 (cons 1 str))))

;; Three-point arc through p1 -> p2 -> p3 (falls back to a line when
;; the points are collinear).
(defun pool:arc3p (p1 p2 p3 lay / o r a1 a2 a3 da2 da3 s e)
  (setq o (pool:circum p1 p2 p3))
  (if o
      (progn
        (setq r  (distance o p1)
              a1 (angle o p1)
              a2 (angle o p2)
              a3 (angle o p3)
              da2 (cal:angnorm (- a2 a1))
              da3 (cal:angnorm (- a3 a1)))
        (if (< da2 da3)
            (setq s a1 e a3)
            (setq s a3 e a1))
        (entmake (list '(0 . "ARC")
                       (cons 8 lay)
                       (cons 10 (pool:wp o))
                       (cons 40 r)
                       (cons 50 s)
                       (cons 51 e))))
      (pool:line p1 p3 lay)))

;;; Small dimensions read in inches.  Any measurement under 24" is
;;; drawn in the "STANDARD INCHES" dim style when the drawing has one
;;; -- under, so a 2 ft corner is a STANDARD dim (pool:*smallfuzz*
;;; keeps that true when the 24 is measured back off the geometry),
;;; and the previous style comes straight back afterwards.  Every
;;; dimension the routine draws goes through pool:dimalg / pool:dimrot
;;; / pool:dimrad / pool:dimcorner1, so switching in those four covers
;;; plan dims, hopper chain dims, corner treatments, radii and the
;;; side-profile depths alike.  (Angular corner dims measure degrees,
;;; not inches, so they are left alone.)

(defun pool:dimsbegin (d / odim)
  ;; inside a SIDE STANDARD block the letter keeps that style however
  ;; small it is -- the reference sheets show a 19" S1 in SIDE
  ;; STANDARD, not in inches
  (if (and (< d (- pool:*smalldim* pool:*smallfuzz*)) (not pool:*sideon*))
      (if (tblsearch "DIMSTYLE" pool:*smallstyle*)
          (progn
            (setq odim (getvar "DIMSTYLE"))
            ;; already current -> nothing to switch, nothing to undo
            (if (= (strcase odim) (strcase pool:*smallstyle*))
                (setq odim nil)
                (command "_.-DIMSTYLE" "_Restore" pool:*smallstyle*))
            odim)
          (progn
            (if (not pool:*smallwarned*)
                (progn
                  (princ (strcat "\n(no \"" pool:*smallstyle*
                                 "\" dim style in this drawing -- dims under "
                                 (rtos pool:*smalldim*)
                                 " drawn in the current style)"))
                  (setq pool:*smallwarned* t)))
            nil))))

(defun pool:dimsend (odim)
  (if (and odim (tblsearch "DIMSTYLE" odim))
      (command "_.-DIMSTYLE" "_Restore" odim)))

;; One dimension between two drawn points.  A horizontal or vertical
;; pair comes out as a true linear dimension (DIMLINEAR, orientation
;; forced so the placement point can't flip it); only a genuinely
;; skewed edge -- an out-of-square wall, a grecian chord -- still needs
;; DIMALIGNED.
(defun pool:dimalg (p1 p2 pt / od)
  (setq od (pool:dimsbegin (distance p1 p2)))
  (cond
    ((< (abs (- (cadr p1) (cadr p2))) 1.0e-6)
     (command "_.DIMLINEAR" (pool:wp p1) (pool:wp p2) "_H" (pool:wp pt)))
    ((< (abs (- (car p1) (car p2))) 1.0e-6)
     (command "_.DIMLINEAR" (pool:wp p1) (pool:wp p2) "_V" (pool:wp pt)))
    (t
     (command "_.DIMALIGNED" (pool:wp p1) (pool:wp p2) (pool:wp pt))))
  (pool:dimsend od))

;; Radius dimension ON the arc, read from OUTSIDE it: the arc is picked
;; at its far point and the dimension line is dragged further out along
;; the same direction, so the leader comes in from outside instead of
;; running back to the circle centre.
(defun pool:dimrad (ent tip outd doff / od)
  (if (and ent (entget ent) (= "ARC" (cdr (assoc 0 (entget ent)))))
      (progn
        (setq od (pool:dimsbegin (cdr (assoc 40 (entget ent)))))
        (command "_.DIMRADIUS" (list ent (pool:wp tip))
                 (pool:wp (cal:v+ tip (cal:v* outd (* 0.9 doff)))))
        (pool:dimsend od))
      ;; a degenerate end (bulge ~ 0) drew a straight line instead
      (princ "\n(radius dim skipped -- the end came out flat, no arc)")))

;; Rotated linear dimension hooked to two OBJECT points: the ext-line
;; origins land on drawn geometry (wall endpoints / arc tangents), and
;; the rotation makes it read the full run regardless of the hooks.
(defun pool:dimrot (p1 p2 ang loc / od)
  ;; a rotated linear dim measures the RUN along ang, not p1->p2
  (setq od (pool:dimsbegin (abs (cal:dot (cal:v- p2 p1)
                                          (list (cos ang) (sin ang))))))
  (command "_.DIMLINEAR" (pool:wp p1) (pool:wp p2)
           "_R" (angtos ang 0 6) (pool:wp loc))
  (pool:dimsend od))

;; Switch to the CROSS DIMENSIONS dim style when the drawing has one.
;; Cross dims are drawn ByLayer (no per-entity color/linetype/lineweight
;; override) -- their look (dashed or otherwise) comes entirely from
;; that dim style and the DIMENSION layer, same as every other dim.
;; Returns the previous style name (for pool:dimxend), or nil.
(defun pool:dimxbegin ( / odim)
  (if (tblsearch "DIMSTYLE" pool:*crossstyle*)
      (progn
        (setq odim (getvar "DIMSTYLE"))
        (command "_.-DIMSTYLE" "_Restore" pool:*crossstyle*)
        odim)))

(defun pool:dimxend (odim)
  (if (and odim (tblsearch "DIMSTYLE" odim))
      (command "_.-DIMSTYLE" "_Restore" odim)))

;; Switch to the SIDE STANDARD dim style (the secondary sheet
;; letters) when the drawing has one -- see the note above
;; pool:*sidestyle*.  While the block is open, the under-24" switch is
;; suppressed (pool:*sideon*).  Missing style -> current style, and
;; the under-24" rule stays live.
(defun pool:dimsdbeg ( / odim)
  (if (tblsearch "DIMSTYLE" pool:*sidestyle*)
      (progn
        (setq odim (getvar "DIMSTYLE"))
        (if (= (strcase odim) (strcase pool:*sidestyle*))
            (setq odim nil)
            (command "_.-DIMSTYLE" "_Restore" pool:*sidestyle*))
        (setq pool:*sideon* t)
        odim)))

(defun pool:dimsdend (odim)
  (setq pool:*sideon* nil)
  (if (and odim (tblsearch "DIMSTYLE" odim))
      (command "_.-DIMSTYLE" "_Restore" odim)))

;; One aligned dim / radius dim in the SIDE STANDARD style.
(defun pool:dimalgs (p1 p2 pt / od)
  (setq od (pool:dimsdbeg))
  (pool:dimalg p1 p2 pt)
  (pool:dimsdend od))

(defun pool:dimrads (ent tip outd doff / od)
  (setq od (pool:dimsdbeg))
  (pool:dimrad ent tip outd doff)
  (pool:dimsdend od))

;; Point offset outward (away from cen) from the midpoint of p->q.
;; A negative dist offsets inward instead.
(defun pool:outoff (p q cen dist / m n)
  (setq m (cal:mid p q)
        n (pool:unit (cal:perp (cal:v- q p))))
  (if (< (cal:dot (cal:v- m cen) n) 0.0)
      (setq n (cal:v* n -1.0)))
  (cal:v+ m (cal:v* n dist)))

;;; -------------------- user input -------------------------------------

(defun pool:ask (msg / v)
  (cal:osup)
  (initget 7)                           ; no null, no zero, no negative
  (setq v (getdist (strcat "\n" msg ": ")))
  (cal:osdown)
  v)

;;; -------------------- measurement sequences (Back) -------------------
;;;
;;;  A block of related measurements runs through pool:askseq so every
;;;  prompt after the first also offers *Back*, which re-asks the
;;;  previous question -- a typo no longer means Esc and start over.
;;;  Each item: (key kind msg ents dflt skip skipmsg sug)
;;;    key   symbol the answer is stored under
;;;    kind  REQ  a value is required
;;;          NAX  NA accepted (returns nil)
;;;          ZER  NA accepted, zero accepted
;;;          SUG  NA accepted, suggested default (Enter takes it)
;;;    ents  guide entities highlighted while prompted
;;;    dflt  for SUG: a number, or a list of keys -- the first of those
;;;          keys with a non-nil answer supplies the suggestion
;;;    skip  optional quoted expression; non-nil -> answered 0.0 unasked
;;;    sug   optional quoted expression, evaluated just before asking
;;;          (it sees the answers so far, in ans): a number from it is
;;;          the suggestion -- one WORKED OUT from what has been given
;;;          rather than copied off another letter, e.g. the last
;;;          member of a chain, which is whatever the total has left.
;;;          It beats dflt, and it turns a plain NA question into one
;;;          Enter can answer.  A REQ or ZER question keeps its kind:
;;;          those two mean something about what is a valid answer,
;;;          not about what is offered.

(defun pool:sq (ans key) (cdr (assoc key ans)))

(defun pool:sqput (ans key v / out p)
  (foreach p ans (if (not (eq (car p) key)) (setq out (cons p out))))
  (reverse (cons (cons key v) out)))

(defun pool:sqfirst (ans keys / out k)
  (foreach k keys
    (if (and (not out) (pool:sq ans k)) (setq out (pool:sq ans k))))
  out)

;; What a chain has LEFT for its last member: the total less every
;; other member, once all of them have been answered.  This is the
;; suggestion a crew gets when the second-to-last letter of a loop
;; goes in -- H, G and F given means E can only be one number, so it
;; is offered rather than asked for cold (Enter takes it, NA still
;; leaves it to pool:chainfix, and typing over it still wins).
;;
;; nil unless every named key carries a real answer and what is left
;; is a length that could be built: a chain already over its total
;; must not suggest a negative offset, and one that lands on the total
;; exactly has nothing left to suggest.
(defun pool:chainrest (ans keys total / out k v)
  (setq out total)
  (foreach k keys
    (if out
        (if (setq v (pool:sq ans k))
            (setq out (- out v))
            (setq out nil))))
  (if (and out (> out 1.0e-6)) out))

;; M answered the same as H is the crew saying the deep end sits
;; SQUARE in the pool -- the same offset off every wall -- so the
;; hopper width is what is left with that offset taken off both sides:
;; 2M + L = A.  Suggest it; anything else (M measured different from
;; H, or either one not given) has nothing to say about L and asks.
(defun pool:sugsym (ans total / m h rest)
  (setq m (pool:sq ans 'm)
        h (pool:sq ans 'h))
  (if (and m h (equal m h 0.5))
      (progn
        (setq rest (- total (* 2.0 m)))
        (if (> rest 1.0e-6) rest))))

;;; -------------------- form answers -----------------------------------
;;;
;;;  A form -- the LAZFORM dialog, or the VB palette -- can answer some
;;;  or all of POOL's questions before the run starts.  It leaves them
;;;  in pool:*form* as (key . value) and the ask helpers below look
;;;  there first, so a filled-in sheet drives the whole run and a
;;;  half-filled one simply shortens it.
;;;
;;;  Three states, and the difference between the last two IS the
;;;  feature:
;;;
;;;    key absent      the form did not answer it   -> ask, as usual
;;;    (key . nil)     the form answered NA         -> nil, no prompt
;;;    (key . 84.0)    the form answered it         -> 84.0, no prompt
;;;
;;;  (assoc key ...) tells those apart; (cdr (assoc ...)) alone cannot.
;;;  Get it backwards and a half-filled form is either impossible or
;;;  silent, and the half-filled form is the whole point.
;;;
;;;  AN ANSWER IS REMOVED AS IT IS USED.  Not marked used -- removed.
;;;  Otherwise Back deadlocks: step back onto a form-answered question,
;;;  it answers itself instantly and walks forward again, and there is
;;;  no key the user can press to get out.  Consuming also gives the
;;;  range checks their way out: pool:askdeep re-asks through pool:askh
;;;  when a depth fails its check, and the second pass finds the store
;;;  empty and lets the user type the correction -- rather than being
;;;  re-fed the same bad number for ever.

(setq pool:*form* nil)

;; Cover mode: no pool bottom, so the gate in pool:askbottom answers No
;; and the whole depth interrogation behind it never runs.  Set by
;; POOLCOVER (and by LAZFORM's cover twin), cleared on both exits from
;; c:POOL.  nil for a typed POOL, always.
(setq pool:*nobottom* nil)

;; Did the form answer KEY at all?  This is the absent/nil distinction
;; that (cdr (assoc ...)) throws away.
(defun pool:fhas (key) (if (assoc key pool:*form*) t nil))

;; The form's answer for KEY, removed from the store as it is read.
(defun pool:ftake (key / p)
  (setq p (assoc key pool:*form*))
  (setq pool:*form* (vl-remove p pool:*form*))
  (cdr p))

(defun pool:fclear () (setq pool:*form* nil))

;; The letter a prompt leads with, as a form key.  The depth questions
;; are asked through pool:askh, which carries no key of its own, but
;; their prompts all read "<letter> - <what it is>": "C - wall height
;; (shallow depth)" is 'c, "C2 - depth where the shallow floor meets
;; the break" is 'c2, and both spellings of D are 'd.  ONLY that exact
;; shape counts -- "Total pool length (arc tip to arc tip)" leads with
;; no letter and must come back nil so it prompts, rather than eating
;; whatever answer happens to be under that name in the store.
(defun pool:fkeyof (msg / n s out)
  (setq n 1)
  (while (and (not out) (<= n 2))
    (if (= (substr msg (1+ n) 3) " - ")
        (progn
          (setq s (strcase (substr msg 1 n) t))
          (if (wcmatch s "@,@#") (setq out (read s)))))
    (setq n (1+ n)))
  out)

;; The form-key stem for a corner question, from the subject string
;; every flow already passes pool:askcorner -- "Corner A" is cornera,
;; and the collective questions get names of their own.  A subject no
;; form addresses comes back nil and the corner is asked as always.
(defun pool:fckey (subject / s)
  (setq s (strcase subject t))
  (cond
    ((= s "all four corners") "corners")
    ((= s "the outer corners") "outercorners")
    ((= s "the inner corner e") "innercorner")
    ((= s "the body corners a, b, c and d") "bodycorners")
    ((= s "the end-tip corners lt, lb, rt and rb") "endcorners")
    ((and (> (strlen s) 7) (= (substr s 1 7) "corner "))
     (strcat "corner" (substr s 8)))))

;; The shape, from the form when it named one the dispatch knows, else
;; asked.  Checked against the same list the prompt offers: an unknown
;; shape would fall through the cond at the foot of c:POOL into the
;; rectangle branch and draw the wrong pool without saying so.
(defun pool:fshape ( / v)
  (if (pool:fhas 'shape) (setq v (pool:ftake 'shape)))
  (if (and v (= (type v) 'STR)
           (member v '("Rectangle" "Grecian" "ROman" "L" "LAzyl"
                       "Oval" "OCtagon" "ROUnd" "MUtt")))
      v
      (progn
        (initget 1 "Rectangle Grecian ROman L LAzyl Oval OCtagon ROUnd MUtt")
        (getkword
          (strcat "\nPool shape [Rectangle/Grecian/ROman/L/LAzyl/Oval/"
                  "OCtagon/ROUnd/MUtt]: ")))))

;; Run POOL with a form's answers already in hand.  Nothing happens
;; here that the direct path misses: a caller may equally set
;; pool:*form* itself and call c:POOL, which is what the tests do.
(defun pool:run-with-answers (answers)
  (setq pool:*form* answers)
  (c:POOL)
  (pool:fclear)
  (princ))

;; One prompt of a sequence.  Returns the value, nil for NA, or the
;; symbol CAL-BACK.
(defun pool:asks (kind msg ents dflt back / v cols kw)
  (setq cols (mapcar 'pool:getcol ents))
  (foreach e ents (pool:setcol e pool:*hi-col*))
  (cal:osup)
  ;; Undo is accepted everywhere Back is, as a hidden synonym
  (setq kw (cond ((eq kind 'REQ) (if back "Back Undo" nil))
                 (back "NA Back Undo")
                 (t "NA")))
  (if kw
      ;; REQ always rejects zero (bit 7) - offering Back must not
      ;; loosen what counts as a valid measurement; ZER alone admits 0
      (initget (cond ((eq kind 'ZER) 5)
                     ((and (eq kind 'SUG) dflt) 6)
                     (t 7))
               kw)
      (initget 7))
  (setq v (getdist
            (strcat "\n" msg
                    (cond ((eq kind 'REQ) "")
                          ((eq kind 'SUG)
                           (if dflt (strcat " <" (rtos dflt) "> (or NA)")
                               " (or NA)"))
                          (t " (or NA if not measured)"))
                    (if back " [Back]" "")
                    ": ")))
  (cal:osdown)
  (mapcar '(lambda (e c) (pool:setcol e c)) ents cols)
  (cond ((and (= (type v) 'STR) (member v '("Back" "Undo"))) 'CAL-BACK)
        ((= (type v) 'STR) nil)               ; NA
        ((and (null v) (eq kind 'SUG)) dflt)  ; Enter took the suggestion
        (t v)))

;; The keyword question a form can answer.  Deliberately a WRAPPER and
;; not a sixth argument on pool:askkw: the grouped build swaps that
;; helper out for cal:askkw, which takes five, so widening it here
;; would have the twin call the library with an argument it does not
;; accept -- a build that loads cleanly and dies at the first keyword
;; question.  The mirror leaves this defun alone, while the pool:askkw
;; call inside it is rewritten like any other call site.
(defun pool:askkwf (key msg kws shown dflt back / v)
  (if (and (pool:fhas key)
           (setq v (pool:ftake key))
           (= (type v) 'STR)
           (setq v (pool:fkword v kws)))
      v
      (cal:askkw msg kws shown dflt back)))

;; V as the question would spell it, or nil when the question does not
;; accept it at all.  Two jobs in one walk of the keyword list:
;;
;;   - an answer the question does not offer falls through to the
;;     prompt instead of being handed on to fail later.  The shape
;;     charts show bottoms POOL cannot draw, and a form built from a
;;     chart will offer them;
;;   - the canonical SPELLING comes back, not the caller's.  Every test
;;     downstream is (= btype "Wedge"), so a form that said "wedge"
;;     would sail through a case-insensitive check and then match
;;     nothing at all.
(defun pool:fkword (v kws / i n c w out)
  (setq i 1 n (strlen kws) w "" v (strcase v))
  (while (<= i (1+ n))
    (setq c (if (<= i n) (substr kws i 1) " "))
    (if (= c " ")
        (progn
          (if (and (/= w "") (= (strcase w) v)) (setq out w))
          (setq w ""))
        (setq w (strcat w c)))
    (setq i (1+ i)))
  out)

;; The Yes/No question a form can answer.  A wrapper over pool:askkwf
;; for pool:askkwf's own reason: pool:askyn is swapped for the library's
;; in the grouped build, so neither may grow an argument.  The form
;; answers "Yes" or "No" -- the same words a click on the bracket would
;; send -- and pool:fkword holds it to exactly those, so anything else
;; in the box falls through to the prompt.  Returns T, nil or
;; CAL-BACK, like pool:askyn.
(defun pool:askynf (key msg dflt back / v)
  (setq v (pool:askkwf key msg "Yes No" "Yes/No" dflt back))
  (if (eq v 'CAL-BACK) v (= v "Yes")))

;; THE POOL-BOTTOM GATE.  The same question in five places, one per
;; shape family, and everything behind it -- the wall height C, the
;; break depth C2, the deep end D, the hopper type and its corner
;; method -- is asked only if the answer is Yes.
;;
;; A cover sheet records no floor work at all, so there is nothing on
;; the other side of this question worth asking for: POOLCOVER sets
;; pool:*nobottom* and the gate answers No without appearing.  That is
;; the whole of "cover mode" -- one gate, closed.
;;
;; It is a run flag rather than an entry in pool:*form* on purpose.
;; The store is consume-once (an answer is removed as it is read, so a
;; range check can escape to the keyboard and Back cannot deadlock),
;; which is right for a measurement asked once and wrong for a gate
;; that five different shape paths may reach.  A flag answers wherever
;; the run happens to land.
;;
;; Like the store, it is cleared on the way out of c:POOL -- both exits
;; -- so a cover run can never leave the next POOL silently bottomless.
(defun pool:askbottom ()
  (if pool:*nobottom*
      nil
      (cal:askyn "Add pool bottom (hopper) detail?" "Yes" nil)))

;; Does this treatment cut real geometry off the corner?  NotGiven
;; does NOT: its corner is built square, so everything that asks
;; "is there a cut here" -- the setback caps, the cross-dim reference
;; modes, the hopper ties -- must answer no.  Only the report and the
;; corner marks care that it is not a plain Square.
;; The same question with the two SIZED answers withheld, for a corner
;; whose walls leave no room for a cut at all.  Square and NotGiven are
;; the only truthful answers there, and both take no size.
(defun pool:asktreatng (subject dflt back / v kws)
  (setq kws "Square NotGiven")
  (setq v (cal:askkw (strcat "How should " subject " be treated?")
                      (strcat kws " NG 90")
                      (vl-string-translate " " "/" kws)
                      dflt back))
  (cond ((eq v 'CAL-BACK) v)
        ((= v "NG") "NotGiven")
        ((= v "90") "Square")
        (t v)))

(defun pool:cutp (ty) (member ty '("Radius" "Cut")))

;; Does any corner carry something the SHEET must record -- a cut, or
;; a NotGiven?  The wider question pool:cutp deliberately does not
;; answer, for the report rows and the corner marks.
(defun pool:anytreat (corners / out c)
  (foreach c corners (if (/= (car c) "Square") (setq out t)))
  out)

;; Run a list of input stages with Back between them: a stage that
;; returns CAL-BACK sends the user to the previous stage, which is
;; re-asked from scratch.  Each stage is a function of no arguments
;; and must be safely re-runnable (it recomputes from its own answers).
;; Stage 1 has nowhere to go back to, so its Back is suppressed.
(defun pool:stages (fns / i n v)
  (setq i 0 n (length fns))
  (while (< i n)
    (setq v (apply (nth i fns) nil))
    (if (eq v 'CAL-BACK)
        ;; the first stage has nowhere to go back to, so it re-asks
        ;; rather than falling forward past its own question
        (if (> i 0) (setq i (1- i)))
        (setq i (1+ i))))
  (princ))

;; Run a whole block; returns the answers as an assoc list, or the
;; symbol CAL-BACK when the user backed out of its FIRST question
;; (only offered when bk is non-nil).
(defun pool:askseq (items / ans i n it v dflt asked)
  (setq ans (pool:askseqb items nil))
  ans)

(defun pool:askseqb (items bk / ans i n it v dflt asked out kind sg)
  (setq ans nil i 0 n (length items) asked nil out nil)
  (while (and (< i n) (not out))
    (setq it (nth i items))
    (if (and (nth 5 it) (eval (nth 5 it)))    ; auto-skip -> 0, unasked
        (progn
          (if (nth 6 it) (princ (nth 6 it)))
          (setq ans (pool:sqput ans (car it) 0.0)
                i (1+ i))
          ;; a skipped answer is still an answer: the live guide gets
          ;; the 0 too, so a spanned-out E collapses exactly
          (pool:pvnote (car it) 0.0))
        (progn
          (setq dflt (nth 4 it)
                kind (cadr it))
          (if (and dflt (listp dflt))
              (setq dflt (pool:sqfirst ans dflt)))
          ;; a suggestion WORKED OUT from the answers so far -- the one
          ;; member a chain has left, say -- beats one copied off
          ;; another letter, and lets a plain NA question be answered
          ;; with Enter
          (if (and (nth 7 it) (setq sg (eval (nth 7 it))))
              (setq dflt sg
                    kind (if (eq kind 'NAX) 'SUG kind)))
          ;; the form answers first, and its answer is consumed --
          ;; see "form answers" above for why removing beats marking
          (setq v (if (pool:fhas (car it))
                      (pool:ftake (car it))
                      (pool:asks kind (caddr it) (cadddr it) dflt
                                 (if (or asked bk) t nil))))
          (if (eq v 'CAL-BACK)
              (if asked
                  (setq i (car asked) asked (cdr asked))
                  (setq out t))             ; backed out of the block
              (progn
                (setq ans (pool:sqput ans (car it) v)
                      asked (cons i asked)
                      i (1+ i))
                ;; the live guide reshapes to every accepted answer --
                ;; including a re-answer after Back, which overwrites
                (pool:pvnote (car it) v))))))
  (if out 'CAL-BACK ans))

;;; -------------------- guide preview ----------------------------------
;;; A gray pool of the chosen shape is drawn as soon as the shape is
;;; picked.  While each measurement is prompted for, the matching
;;; element of the guide turns red so the user can see exactly which
;;; dimension is being asked for -- and the guide is LIVE: every
;;; accepted answer reshapes it in place (see "live guide reshaping"
;;; below), so it starts at a familiar nominal size and turns into the
;;; actual pool as the numbers come in.  Once all inputs are in, the
;;; guide deletes itself and is replaced by the true out-of-square pool.

(setq pool:*pv-col* 8)                  ; guide outline color (dark gray)
(setq pool:*pvx-col* 7)                 ; cross-dim / measuring line color (white)
(setq pool:*hi-col* 1)                  ; highlight color (red)

;; Override (or set) the color of an entity, refresh it, return it.
(defun pool:setcol (e col / ed old)
  (if (and e (setq ed (entget e)))
      (progn
        (setq old (assoc 62 ed))
        (if old
            (setq ed (subst (cons 62 col) old ed))
            (setq ed (append ed (list (cons 62 col)))))
        (entmod ed)
        (entupd e)))
  e)

;; Read an entity's current color (defaults to the outline gray).
(defun pool:getcol (e / ed)
  (if (and e (setq ed (entget e)) (assoc 62 ed))
      (cdr (assoc 62 ed))
      pool:*pv-col*))

;; Guide entities for a list of corner-label keys, e.g. '(lA lB), so a
;; prompt can light up the letters it names as well as the line.
(defun pool:lbl (pv keys / out k)
  (foreach k keys (setq out (append out (cdr (assoc k pv)))))
  out)

;; The guide's corner-label key for a letter string ("A" -> 'lA).
(defun pool:lblkey (s) (read (strcat "l" s)))

(defun pool:pvline (p1 p2)
  (pool:line p1 p2 "POOL-NOTES")
  (pool:setcol (entlast) pool:*pv-col*))

;; Guide measuring line -- the cross dims and other ties, drawn WHITE
;; and DOTTED so they stand out from the gray pool outline.
(defun pool:pvlined (p1 p2)
  (pool:linedot p1 p2)
  (entlast))

;; Ask for a distance while the matching guide elements glow red, then
;; restore each element to the color it had (outline vs cross-dim gray).
(defun pool:askh (msg ents / v cols k)
  ;; A form answer for this letter skips the prompt and the highlight
  ;; with it -- there is nothing to look at while nothing is being
  ;; asked.  Only a real measurement is taken: every caller here range
  ;; checks what it gets and none of them can do anything with nil, so
  ;; an NA in the store falls through to the keyboard (having been
  ;; consumed, so it cannot come back round again).
  (setq k (pool:fkeyof msg))
  (if (and k (pool:fhas k) (numberp (setq v (pool:ftake k))))
      v
      (progn
        (setq cols (mapcar 'pool:getcol ents))
        (foreach e ents (pool:setcol e pool:*hi-col*))
        (setq v (pool:ask msg))
        (mapcar '(lambda (e c) (pool:setcol e c)) ents cols)
        v)))

;; Delete all guide entities (tracked globally so the *error* handler
;; can clean up after a cancel mid-prompt).  The live-reshape engine is
;; disarmed with them: a dead guide must never be morphed again.
(defun pool:pvkill ()
  (foreach e pool:*pvents*
    (if (and e (entget e)) (entdel e)))
  (setq pool:*pvents* nil
        pool:*pvgeo* nil
        pool:*pvments* nil
        pool:*pvmore* nil
        pool:*pvbox* nil))

;; Remove an item (by equality) from a list.
(defun pool:lremove (x lst / out i)
  (foreach i lst (if (not (equal i x)) (setq out (cons i out))))
  (reverse out))

;; Track a freshly made guide entity so pool:pvkill / *error* find it.
(defun pool:pvadd (e)
  (setq pool:*pvents* (cons e pool:*pvents*))
  e)

;; Delete specific guide entities mid-flow and untrack them (used when
;; part of the guide is redrawn, e.g. corner treatments).
(defun pool:pvdel (ents / e)
  (foreach e ents
    (if (and e (entget e)) (entdel e))
    (setq pool:*pvents* (pool:lremove e pool:*pvents*))))

;;; -------------------- live guide reshaping ---------------------------
;;; What makes the guide LIVE.  Each flow describes its guide as a SPEC
;;; -- an ordered list of primitives --
;;;
;;;     ("LINE" p1 p2)     gray outline segment
;;;     ("LINED" p1 p2)    white dotted measuring line
;;;     ("TEXT" pt h str)  gray label
;;;     ("ARC" p1 p2 p3)   gray three-point arc
;;;     ("ELL" cen b a)    gray axis-aligned ellipse (b across, a up)
;;;
;;; -- produced by a small geometry function the flow registers in
;;; pool:*pvgeo*.  That function reads the answers given SO FAR out of
;;; pool:*pvdims* and fills every gap with the nominal proportions, so
;;; the first paint is the familiar nominal pool and each answer after
;;; it snaps the guide closer to the real one.  pool:askseqb records
;;; every accepted answer through pool:pvnote, which re-runs the
;;; geometry and MOVES the existing entities onto it with entmod.
;;;
;;; Moving (never remaking) the entities is the point of the design:
;;; the pending ask items hold the guide entities they highlight, and
;;; those references stay valid only while the entities live.  The one
;;; exception is a three-point arc whose points go collinear (or come
;;; back apart) -- the entity type has to change, so it is remade and
;;; that single highlight reference is written off.
;;;
;;; The geometry function returns (spec keymap box): keymap maps each
;;; highlight key to the spec indices it lights up (consumed once, at
;;; build time), box is the window the guide wants on screen -- the
;;; view follows the reshape, so a pool bigger than the nominal guide
;;; never grows out of sight.

(setq pool:*pvdims* nil)                ; assoc: answer key -> value so far
(setq pool:*pvgeo* nil)                 ; the flow's geometry fn (a symbol)
(setq pool:*pvments* nil)               ; entities to morph, in spec order
(setq pool:*pvmore* nil)                ; per-flow extra morph fn (a symbol)
(setq pool:*pvbox* nil)                 ; the view box last zoomed to

;; One answered dimension, or nil while it has not been given (NA and
;; not-yet-asked read the same: the nominal proportion fills in).
(defun pool:pvdim (key) (cdr (assoc key pool:*pvdims*)))

;; Axis-aligned guide ellipse.  Always an ELLIPSE, even with equal
;; axes, so the entity type never changes as the two overalls come in.
(defun pool:pvell (cen b a / mj rt)
  (if (>= b a)
      (setq mj (list (* 0.5 b) 0.0 0.0) rt (/ a b))
      (setq mj (list 0.0 (* 0.5 a) 0.0) rt (/ b a)))
  (entmake (list '(0 . "ELLIPSE")
                 '(100 . "AcDbEntity")
                 (cons 8 "POOL-NOTES")
                 '(100 . "AcDbEllipse")
                 (cons 10 (pool:wp cen))
                 (cons 11 mj)                  ; major semi-axis, relative
                 (cons 210 '(0.0 0.0 1.0))
                 (cons 40 rt)                  ; minor / major
                 (cons 41 0.0)
                 (cons 42 (* 2.0 pi)))))

;; Make one primitive's entity, tracked for pool:pvkill.  LINE / TEXT /
;; ARC draw gray on POOL-NOTES exactly as the fixed guides always did;
;; LINED is the white dotted measuring line.
(defun pool:pvmk (pr / ty)
  (setq ty (car pr))
  (cond
    ((= ty "LINE") (pool:pvadd (pool:pvline (cadr pr) (caddr pr))))
    ((= ty "LINED") (pool:pvadd (pool:pvlined (cadr pr) (caddr pr))))
    ((= ty "TEXT")
     (pool:text (cadr pr) (caddr pr) (cadddr pr) "POOL-NOTES")
     (pool:pvadd (pool:setcol (entlast) pool:*pv-col*)))
    ((= ty "ARC")
     (pool:arc3p (cadr pr) (caddr pr) (cadddr pr) "POOL-NOTES")
     (pool:pvadd (pool:setcol (entlast) pool:*pv-col*)))
    ((= ty "ELL")
     (pool:pvell (cadr pr) (caddr pr) (cadddr pr))
     (pool:pvadd (pool:setcol (entlast) pool:*pv-col*)))))

;; The two primitives of one field-sheet tie -- the dotted measuring
;; line and its letter beside the midpoint.
(defun pool:pvtiespec (p q lbl th)
  (list (list "LINED" p q)
        (list "TEXT" (cal:v+ (cal:mid p q) (list (* 0.5 th) (* 0.5 th)))
              (* 1.2 th) lbl)))

;; The window a spec wants on screen: its extents plus a margin.
(defun pool:pvspecbox (spec / pts pr hx hy px py qx qy m)
  (setq pts nil)
  (foreach pr spec
    (cond
      ((member (car pr) '("LINE" "LINED"))
       (setq pts (cons (cadr pr) (cons (caddr pr) pts))))
      ((= (car pr) "TEXT")
       (setq pts (cons (cadr pr) pts)))
      ((= (car pr) "ARC")
       (setq pts (cons (cadr pr) (cons (caddr pr) (cons (cadddr pr) pts)))))
      ((= (car pr) "ELL")
       (setq hx (* 0.5 (caddr pr)) hy (* 0.5 (cadddr pr))
             pts (cons (cal:v+ (cadr pr) (list hx hy))
                       (cons (cal:v- (cadr pr) (list hx hy)) pts))))))
  (setq px (apply 'min (mapcar 'car pts))
        qx (apply 'max (mapcar 'car pts))
        py (apply 'min (mapcar 'cadr pts))
        qy (apply 'max (mapcar 'cadr pts))
        m (max 30.0 (* 0.10 (max (- qx px) (- qy py)))))
  (list (list (- px m) (- py m)) (list (+ qx m) (+ qy m))))

;; Follow the reshaped guide with the view -- but only when the box
;; really moved, so answers that barely change the shape do not churn
;; the screen.
(defun pool:pvzoom (box / o)
  (setq o pool:*pvbox*)
  (if (and box
           (or (null o)
               (> (+ (distance (car box) (car o))
                     (distance (cadr box) (cadr o)))
                  (* 0.05 (distance (car box) (cadr box))))))
      (progn
        (setq pool:*pvbox* box)
        (command "_.ZOOM" "_Window"
                 (pool:wp (car box)) (pool:wp (cadr box))))))

;; Move one guide entity onto its recomputed primitive.  An entity that
;; no longer exists (the corner redraw retires the plain sides) is left
;; dead; a three-point arc whose kind changed is remade.  Returns the
;; entity holding the primitive now.
(defun pool:pvmod (e pr / ed ty o r a1 a2 a3 da2 da3 s en mj rt)
  (setq ed (if e (entget e)))
  (cond
    ((null ed) e)
    ((member (car pr) '("LINE" "LINED"))
     (entmod (subst (cons 11 (pool:wp (caddr pr))) (assoc 11 ed)
                    (subst (cons 10 (pool:wp (cadr pr))) (assoc 10 ed) ed)))
     (entupd e)
     e)
    ((= (car pr) "TEXT")
     (entmod (subst (cons 1 (cadddr pr)) (assoc 1 ed)
                    (subst (cons 40 (caddr pr)) (assoc 40 ed)
                           (subst (cons 10 (pool:wp (cadr pr)))
                                  (assoc 10 ed) ed))))
     (entupd e)
     e)
    ((= (car pr) "ARC")
     (setq o (pool:circum (cadr pr) (caddr pr) (cadddr pr))
           ty (cdr (assoc 0 ed)))
     (if (and o (= ty "ARC"))
         (progn
           (setq r (distance o (cadr pr))
                 a1 (angle o (cadr pr))
                 a2 (angle o (caddr pr))
                 a3 (angle o (cadddr pr))
                 da2 (cal:angnorm (- a2 a1))
                 da3 (cal:angnorm (- a3 a1)))
           (if (< da2 da3)
               (setq s a1 en a3)
               (setq s a3 en a1))
           (entmod (subst (cons 51 en) (assoc 51 ed)
                          (subst (cons 50 s) (assoc 50 ed)
                                 (subst (cons 40 r) (assoc 40 ed)
                                        (subst (cons 10 (pool:wp o))
                                               (assoc 10 ed) ed)))))
           (entupd e)
           e)
         ;; the kind changed (arc went collinear, or a line-fallback
         ;; arc came back apart) -- remade, references written off
         (progn (pool:pvdel (list e)) (pool:pvmk pr))))
    ((= (car pr) "ELL")
     (if (>= (caddr pr) (cadddr pr))
         (setq mj (list (* 0.5 (caddr pr)) 0.0 0.0)
               rt (/ (cadddr pr) (caddr pr)))
         (setq mj (list 0.0 (* 0.5 (cadddr pr)) 0.0)
               rt (/ (caddr pr) (cadddr pr))))
     (entmod (subst (cons 40 rt) (assoc 40 ed)
                    (subst (cons 11 mj) (assoc 11 ed)
                           (subst (cons 10 (pool:wp (cadr pr)))
                                  (assoc 10 ed) ed))))
     (entupd e)
     e)
    (t e)))

;; Reshape the live guide from the answers recorded so far: re-run the
;; flow's geometry, move every entity onto it, follow with the view,
;; then let the flow move what the generic pass cannot see (the corner
;; treatments and cross-dim lines it added after the build).
(defun pool:pvreshape ( / g)
  (if (and pool:*pvgeo* pool:*pvments*)
      (progn
        (setq g (apply pool:*pvgeo* nil))
        (setq pool:*pvments* (mapcar 'pool:pvmod pool:*pvments* (car g)))
        (pool:pvzoom (caddr g))
        (if pool:*pvmore* (apply pool:*pvmore* nil)))))

;; Record one accepted answer and reshape the guide to it.  Harmless
;; once the guide is gone -- pool:pvkill disarms the engine, so the
;; interior (hopper) questions record into the void.
(defun pool:pvnote (key v)
  (setq pool:*pvdims* (pool:sqput pool:*pvdims* key v))
  (pool:pvreshape))

;; Build a live guide from the flow's geometry function: draw the spec,
;; register the function for reshaping, zoom to it, and hand back the
;; highlight assoc the ask items index by key.
(defun pool:pvlive (geofn / g ents)
  (setq pool:*pvdims* nil
        pool:*pvmore* nil
        pool:*pvbox* nil
        pool:*pvgeo* geofn
        g (apply geofn nil)
        ents (mapcar 'pool:pvmk (car g))
        pool:*pvments* ents)
  (pool:pvzoom (caddr g))
  (mapcar '(lambda (km)
             (cons (car km)
                   (mapcar '(lambda (i) (nth i ents)) (cdr km))))
          (cadr g)))

;;; The BOTTOM-phase guides (the floor dims: the H/G/F/E/M/L/K hopper
;;; chains and the section depths) ride the same engine through a
;;; COLLECTOR.  The hopper draw routines (pool:hgl / pool:hga /
;;; pool:profdraw) have always had a pvflag preview path; arming the
;;; collector makes that same path EMIT primitives instead of drawing,
;;; so the existing compute-and-draw code doubles as the geometry
;;; function and the hopper reshapes with every letter answered.

(setq pool:*pvcoll* nil)                ; T while a spec is being collected
(setq pool:*pvcsp* nil)                 ; collected primitives, reversed
(setq pool:*pvckm* nil)                 ; collected keymap entries

;; Arm the collector (a bottom geometry function's first act).
(defun pool:pvcopen ()
  (setq pool:*pvcoll* t
        pool:*pvcsp* nil
        pool:*pvckm* nil))

;; One primitive into the collector.
(defun pool:pvcput (pr)
  (setq pool:*pvcsp* (cons pr pool:*pvcsp*))
  nil)

;; One keyed field-sheet tie into the collector -- the live counterpart
;; of the old pool:pvtie: the dotted line and its letter, highlighted
;; together while that letter is prompted.
(defun pool:pvctie (p q lbl th / n pr)
  (setq n (length pool:*pvcsp*))
  (foreach pr (pool:pvtiespec p q lbl th) (pool:pvcput pr))
  (setq pool:*pvckm* (cons (list lbl n (1+ n)) pool:*pvckm*))
  nil)

;; Close the collector into the (spec keymap box) a geometry function
;; returns.  pts joins the view box without being drawn, so the pool
;; the bottom guide sits inside stays on screen however the guide
;; moves.
(defun pool:pvcout (pts / spec km box p px py qx qy)
  (setq spec (reverse pool:*pvcsp*)
        km (reverse pool:*pvckm*)
        box (pool:pvspecbox spec)
        pool:*pvcoll* nil
        px (car (car box)) py (cadr (car box))
        qx (car (cadr box)) qy (cadr (cadr box)))
  (foreach p pts
    (setq px (min px (- (car p) 20.0)) py (min py (- (cadr p) 20.0))
          qx (max qx (+ (car p) 20.0)) qy (max qy (+ (cadr p) 20.0))))
  (list spec km (list (list px py) (list qx qy))))

;; Live fill-in for a measurement chain: answered members are held,
;; open ones share whatever the total has left in proportion to their
;; nominals -- so the chain closes against the pool at every step, and
;; once all but one member is in, the last shows exactly the remainder
;; the resolver will hand it.  An overspent chain squeezes the open
;; members toward zero instead of going negative.
(defun pool:pvchain (vals noms total / sum nsum s out k v)
  (setq sum 0.0 nsum 0.0 k 0)
  (foreach v vals
    (if v (setq sum (+ sum v)) (setq nsum (+ nsum (nth k noms))))
    (setq k (1+ k)))
  (setq s (if (> nsum 1.0e-6) (max 0.05 (/ (- total sum) nsum)) 0.0)
        out nil k 0)
  (foreach v vals
    (setq out (cons (if v v (* s (nth k noms))) out)
          k (1+ k)))
  (reverse out))

;; Mirror everything drawn after `after` about the HORIZONTAL line
;; y = y0 -- a top-to-bottom flip.
;;
;; L and Lazy L pools flip this way rather than left-to-right, because
;; the deep end is always the end AWAY from the wing: flipping
;; left-to-right would swing the wing across and carry the hopper over
;; to the right-hand side of the sheet with it.  Flipping top-to-bottom
;; swaps which way the wing points instead and leaves the deep end --
;; and so the hopper -- on the left, where the convention wants it.
;;
;; The side profile is held out of it (pool:*profents*): that is a
;; LONGITUDINAL section, and turning the plan upside down does not
;; change it.  Text is mirrored with MIRRTEXT off so it stays readable.
(defun pool:mirrory (after y0 / ss e mt)
  (setq ss (ssadd)
        e (if after (entnext after) (entnext)))
  (while e
    (if (not (member e pool:*profents*)) (ssadd e ss))
    (setq e (entnext e)))
  (if (> (sslength ss) 0)
      (progn
        (setq mt (getvar "MIRRTEXT"))
        (setvar "MIRRTEXT" 0)
        (command "_.MIRROR" ss "" (list 0.0 y0 0.0) (list 1.0 y0 0.0) "_Y")
        (setvar "MIRRTEXT" mt)))
  (princ))

;; The rectangle / oval guide is built by qf:geo inside pool:quadflow
;; -- a live-guide geometry function fed to pool:pvlive, so the box
;; reshapes as its sides come in.  Every other flow has its own such
;; function (gr:geo, hx:geo, rd:geo, rm:geo, mu:geo).

;;; -------------------- quadrilateral fitting --------------------------

;; Measured lengths of quad (A B C D):
;; (bottom top left right crossAC crossBD)
(defun pool:quadmeas (q / a b c d)
  (setq a (car q) b (cadr q) c (caddr q) d (cadddr q))
  (list (distance a b) (distance d c) (distance a d) (distance b c)
        (distance a c) (distance b d)))

;; Cross-dim error of a quad; a nil target (NA) contributes nothing.
(defun pool:diagerr (q dac dbd / e1 e2)
  (setq e1 (if dac (- (distance (car q) (caddr q)) dac) 0.0)
        e2 (if dbd (- (distance (cadr q) (cadddr q)) dbd) 0.0))
  (+ (* e1 e1) (* e2 e2)))

;; Quad with all four sides EXACT, parameterised by the interior angle
;; at corner A (four-bar linkage).  Returns (A B C D) or nil.
(defun pool:4bar (bo tp le ri alfa / a b d c1 c2)
  (setq a (list 0.0 0.0)
        b (list bo 0.0)
        d (list (* le (cos alfa)) (* le (sin alfa)))
        c1 (pool:circint b ri d tp 1.0)
        c2 (pool:circint b ri d tp -1.0))
  (cond
    ((and c1 c2)
     (list a b (if (> (distance a c1) (distance a c2)) c1 c2) d))
    (c1 (list a b c1 d))
    (c2 (list a b c2 d))
    (t nil)))

;; Scan the angle at A over [a0 a1], returning (quad alfa) with the
;; smallest cross-dim error, or nil.
(defun pool:scanalfa (bo tp le ri dac dbd a0 a1 step / alfa q e best bestq)
  (setq alfa a0 best 1.0e30 bestq nil)
  (while (<= alfa a1)
    (setq q (pool:4bar bo tp le ri alfa))
    (if q
        (progn
          (setq e (pool:diagerr q dac dbd))
          (if (< e best) (setq best e bestq (list q alfa)))))
    (setq alfa (+ alfa step)))
  bestq)

;; Best quad with sides held EXACTLY true, cross dims as close as
;; possible.  Coarse scan then fine refine.  Returns quad or nil.
;; With both cross dims NA there is nothing to skew for: square up.
(defun pool:fitsides (bo tp le ri dac dbd / r1 r2 alfa)
  (if (and (null dac) (null dbd))
      (pool:4bar bo tp le ri (pool:d2r 90.0))
      (progn
        (setq r1 (pool:scanalfa bo tp le ri dac dbd
                                (pool:d2r 15.0) (pool:d2r 165.0) (pool:d2r 0.25)))
        (if r1
            (progn
              (setq alfa (cadr r1)
                    r2 (pool:scanalfa bo tp le ri dac dbd
                                      (- alfa (pool:d2r 0.3)) (+ alfa (pool:d2r 0.3))
                                      (pool:d2r 0.005)))
              (car (if r2 r2 r1)))))))

(defun pool:setnth (lst i val / k out)
  (setq k 0 out nil)
  (foreach x lst
    (setq out (cons (if (= k i) val x) out)
          k (1+ k)))
  (reverse out))

;; One distance-constraint relaxation step: pull points i and j of pts
;; so their distance moves into [lo hi] (lo = hi -> exact pull).
(defun pool:relax1 (pts i j lo hi w / p q d des err ux uy e2)
  (setq p (nth i pts)
        q (nth j pts)
        d (distance p q))
  (if (> d 1.0e-9)
      (progn
        (setq des (min (max d lo) hi)
              err (- d des))
        (if (/= err 0.0)
            (progn
              (setq ux (/ (- (car q) (car p)) d)
                    uy (/ (- (cadr q) (cadr p)) d)
                    e2 (* 0.5 w err))
              (setq pts (pool:setnth pts i
                          (list (+ (car p) (* e2 ux)) (+ (cadr p) (* e2 uy)))))
              (setq pts (pool:setnth pts j
                          (list (- (car q) (* e2 ux)) (- (cadr q) (* e2 uy)))))))))
  pts)

(defun pool:rot (p ang)
  (list (- (* (car p) (cos ang)) (* (cadr p) (sin ang)))
        (+ (* (car p) (sin ang)) (* (cadr p) (cos ang)))))

;; Re-gauge a polygon: first point at the origin, second on the +X
;; axis, bulk of the shape above the axis.  Works for any point count.
(defun pool:normpoly (pts / a ang my)
  (setq a (car pts)
        pts (mapcar '(lambda (p) (cal:v- p a)) pts)
        ang (- (angle (list 0.0 0.0) (cadr pts)))
        pts (mapcar '(lambda (p) (pool:rot p ang)) pts)
        my 0.0)
  (foreach a pts (setq my (+ my (cadr a))))
  (if (< my 0.0)
      (setq pts (mapcar '(lambda (p) (list (car p) (- (cadr p)))) pts)))
  pts)

;; Iterative relaxation of an arbitrary point list against distance
;; constraints (i j lo hi weight); lo = hi -> exact pull.
(defun pool:relaxn (pts conlst niter / k c)
  (setq k 0)
  (while (< k niter)
    (foreach c conlst
      (setq pts (pool:relax1 pts (car c) (cadr c) (caddr c) (cadddr c) (nth 4 c))))
    (setq k (1+ k)))
  (pool:normpoly pts))

;; Quad relaxation: sides banded to +/-stol, provided cross dims
;; pulled to their exact targets.  Cross dims pull first, side bands
;; clamp last so each sweep ends with the sides inside their band.
(defun pool:relaxquad (pts bo tp le ri dac dbd stol niter / conlst)
  (setq conlst nil)
  (if dbd (setq conlst (cons (list 1 3 dbd dbd 0.5) conlst)))
  (if dac (setq conlst (cons (list 0 2 dac dac 0.5) conlst)))
  (setq conlst (append conlst
                       (list (list 0 1 (- bo stol) (+ bo stol) 1.0)
                             (list 3 2 (- tp stol) (+ tp stol) 1.0)
                             (list 0 3 (- le stol) (+ le stol) 1.0)
                             (list 1 2 (- ri stol) (+ ri stol) 1.0))))
  (pool:relaxn pts conlst niter))

;; Fit the parametric quad.  Returns (quad failedflag):
;;  1. hold sides exact, pick the angle whose cross dims are closest;
;;     if both cross dims land inside xtol -> done, no failure.
;;  2. otherwise let the sides flex inside +/-stol and pull the cross
;;     dims to their targets; if everything then fits -> done.
;;  3. otherwise: sides held true (result of step 1), cross dims as
;;     close as possible, failure flag set.
(defun pool:fitquad (bo tp le ri dac dbd stol xtol / q1 m1 q2 m2 sok xok)
  (setq q1 (pool:fitsides bo tp le ri dac dbd))
  (if (null q1)                         ; degenerate input fallback
      (setq q1 (list (list 0.0 0.0) (list bo 0.0)
                     (list bo (* 0.5 (+ le ri))) (list 0.0 le))))
  (setq m1 (pool:quadmeas q1))
  (if (and (or (null dac) (<= (abs (- (nth 4 m1) dac)) xtol))
           (or (null dbd) (<= (abs (- (nth 5 m1) dbd)) xtol)))
      (list q1 nil)
      (progn
        (setq q2 (pool:relaxquad q1 bo tp le ri dac dbd stol 2000)
              m2 (pool:quadmeas q2)
              sok (and (<= (abs (- (car m2) bo)) (+ stol 0.05))
                       (<= (abs (- (cadr m2) tp)) (+ stol 0.05))
                       (<= (abs (- (caddr m2) le)) (+ stol 0.05))
                       (<= (abs (- (cadddr m2) ri)) (+ stol 0.05)))
              xok (and (or (null dac) (<= (abs (- (nth 4 m2) dac)) (+ xtol 0.05)))
                       (or (null dbd) (<= (abs (- (nth 5 m2) dbd)) (+ xtol 0.05)))))
        (if (and sok xok)
            (list q2 nil)
            (list q1 t)))))

;; Exact two-triangle check (report only, nothing is drawn from it):
;;   triangle 1 = A B C  (bottom side, right end, cross A-C)
;;   triangle 2 = A C D  (top side, left end, shared cross A-C)
;; All lengths held exactly.  Returns (A B C D) or nil when the given
;; lengths cannot form the triangles.
(defun pool:triquad (bo tp le ri dac / a b c d)
  (setq a (list 0.0 0.0)
        b (list bo 0.0)
        c (pool:circint a dac b ri 1.0))
  (if c (setq d (pool:circint a le c tp 1.0)))
  (if (and c d) (list a b c d)))

;;; -------------------- grecian ends -----------------------------------

;; Distance between the two diagonal end points for end width w,
;; diagonal lengths lt/lb and diagonal angle th (from the end line's
;; outward normal).
(defun pool:grecf (w lt lb th)
  (sqrt (+ (expt (- w (* (+ lt lb) (sin th))) 2)
           (expt (* (- lt lb) (cos th)) 2))))

;; Best diagonal angle for target end width e: scan 1..89 degrees.
;; Returns (theta err).
(defun pool:grecth (w lt lb e / th best berr dd)
  (setq th 0.0175 best 0.7854 berr 1.0e30)
  (while (< th 1.5533)
    (setq dd (abs (- (pool:grecf w lt lb th) e)))
    (if (< dd berr) (setq berr dd best th))
    (setq th (+ th 0.00087)))           ; ~ 0.05 degree steps
  (list best berr))

;; Try to fit the end width by adjusting the angle; when that is not
;; enough, adjust the diagonal lengths in 1/8" increments (smallest
;; total adjustment first) up to +/-1/2".
;; Returns (ltUsed lbUsed theta) or nil.
(defun pool:grecfit (w lt lb e / s i j lt2 lb2 r out n)
  (setq n pool:*grec-max* s 0 out nil)
  (while (and (null out) (<= s (* 2 n)))
    (setq i (- n))
    (while (and (null out) (<= i n))
      (setq j (- n))
      (while (and (null out) (<= j n))
        (if (= (+ (abs i) (abs j)) s)
            (progn
              (setq lt2 (+ lt (* pool:*grec-step* i))
                    lb2 (+ lb (* pool:*grec-step* j)))
              (if (and (> lt2 0.0) (> lb2 0.0))
                  (progn
                    (setq r (pool:grecth w lt2 lb2 e))
                    (if (<= (cadr r) 0.0625)   ; within 1/16"
                        (setq out (list lt2 lb2 (car r))))))))
        (setq j (1+ j)))
      (setq i (1+ i)))
    (setq s (1+ s)))
  out)

;; Compute one Grecian end (no drawing).  pbot/ptop = end line
;; corners, mdir = unit normal pointing away from the pool body.
;; Returns (p1 p2 ltUsed lbUsed theta okflag); p1 joins ptop, p2 joins
;; pbot.  When the fit fails the end falls back to 45 degrees with the
;; given lengths, okflag nil.
(defun pool:grecendp (pbot ptop mdir lt lb e / u fit lt2 lb2 th ok dtop dbot)
  (setq u (pool:unit (cal:v- ptop pbot))
        fit (pool:grecfit (distance pbot ptop) lt lb e))
  (if fit
      (setq lt2 (car fit) lb2 (cadr fit) th (caddr fit) ok t)
      (setq lt2 lt lb2 lb th (pool:d2r 45.0) ok nil))
  (setq dtop (cal:v- (cal:v* mdir (cos th)) (cal:v* u (sin th)))
        dbot (cal:v+ (cal:v* mdir (cos th)) (cal:v* u (sin th))))
  (list (cal:v+ ptop (cal:v* dtop lt2))
        (cal:v+ pbot (cal:v* dbot lb2))
        lt2 lb2 th ok))

;;; -------------------- grecian cross-dim modes -------------------------
;;;
;;;  A Grecian pool has 8 corners; from the bottom-left, clockwise:
;;;
;;;         D ------------------ C          body:  A B C D
;;;        /                      \         left tips:  LT (off D), LB (off A)
;;;      LT                        RT       right tips: RT (off C), RB (off B)
;;;        \                      /
;;;         LB                  RB          index order used below:
;;;           \                /             0=A 1=B 2=RB 3=RT 4=C 5=D 6=LT 7=LB
;;;            A ------------ B
;;;
;;;  Cross-dim modes (how many diagonals the user is asked for):
;;;    Simple  = A-C, B-D                       (2, the body diagonals)
;;;    Center  = Simple + LB-RT, LT-RB          (4, adds the long tip X)
;;;    Complex = every possible diagonal        (18, all pairs; NA any)
;;;  More provided cross dims -> the out-of-square shape is pinned down
;;;  more tightly.  Any cross dim may be answered NA.

(setq pool:*grecnames*
      (list "A" "B" "RB" "RT" "C" "D" "LT" "LB"))

;; perimeter edges + the two body-end chords as (i j prompt-key band):
;; body sides loose (1"), end diagonals held near the given 1/2", end
;; widths near-exact.  The prompt-key ties each edge to its guide
;; highlight and prompt.
(setq pool:*grecedges*
      (list '(0 1 ab  1.0)     ; A-B  bottom side
            '(1 2 rbd 0.5)     ; B-RB right diag bottom
            '(2 3 rew 0.1)     ; RB-RT right end width
            '(3 4 rtd 0.5)     ; RT-C right diag top
            '(4 5 cd  1.0)     ; C-D  top side
            '(5 6 ltd 0.5)     ; D-LT left diag top
            '(6 7 lew 0.1)     ; LT-LB left end width
            '(7 0 lbd 0.5)     ; LB-A left diag bottom
            '(0 5 ad  1.0)     ; A-D  left end (internal chord)
            '(1 4 bc  1.0)))   ; B-C  right end (internal chord)

;; The 8 corners in the two families a treatment is answered by: the
;; BODY corners, where a long wall runs into a cut face, and the END
;; TIPS, where that cut face lands on the end wall.  With them, the
;; walls a tip treatment has to share -- the four cut faces (one body
;; corner and one tip on each) and the two end walls (two tips each).
(setq pool:*grecbody* '(0 1 4 5))               ; A B C D
(setq pool:*grectips* '(2 3 6 7))               ; RB RT LT LB
(setq pool:*greccuts* '((1 2) (3 4) (5 6) (7 0)))
(setq pool:*grecwalls* '((2 3) (6 7)))          ; RB-RT and LT-LB

(setq pool:*grec-simple*
      (list '(0 4 "A-C") '(1 5 "B-D")))
(setq pool:*grec-center*
      (list '(0 4 "A-C") '(1 5 "B-D") '(7 3 "LB-RT") '(6 2 "LT-RB")
            ;; tip to tip along the top and along the bottom -- the two
            ;; tapes a crew can run straight down the pool's own edges
            '(6 3 "LT-RT") '(7 2 "LB-RB")
            ;; the X over each end cut (tip to the near body corner)...
            '(5 7 "D-LB") '(0 6 "A-LT")
            '(2 4 "RB-C") '(1 3 "B-RT")
            ;; ...and each tip to the far bottom/top body corner
            '(1 6 "B-LT") '(4 7 "C-LB")
            '(0 3 "A-RT") '(2 5 "RB-D")))
(setq pool:*grec-complex*
      (list '(0 2 "A-RB") '(0 3 "A-RT") '(0 4 "A-C")  '(0 6 "A-LT")
            '(1 3 "B-RT") '(1 5 "B-D")  '(1 6 "B-LT") '(1 7 "B-LB")
            '(2 4 "RB-C") '(2 5 "RB-D") '(2 6 "RB-LT") '(2 7 "RB-LB")
            '(3 5 "RT-D") '(3 6 "RT-LT") '(3 7 "RT-LB")
            '(4 6 "C-LT") '(4 7 "C-LB")
            '(5 7 "D-LB")))

(defun pool:grecmode (m)
  (cond ((= m "Center")  pool:*grec-center*)
        ((= m "Complex") pool:*grec-complex*)
        (t               pool:*grec-simple*)))

;; Worst cross-dim miss over the provided (non-nil) targets.
(defun pool:crossmax (pts crosscons / mx d)
  (setq mx 0.0)
  (foreach c crosscons
    (if (caddr c)
        (setq d (abs (- (distance (nth (car c) pts) (nth (cadr c) pts)) (caddr c)))
              mx (max mx d))))
  mx)

;; Worst amount any edge sits OUTSIDE its band (<=0 means all in band).
(defun pool:edgemax (pts edgecons / mx d)
  (setq mx -1.0e30)
  (foreach e edgecons
    (setq d (- (abs (- (distance (nth (car e) pts) (nth (cadr e) pts)) (caddr e)))
               (cadddr e))
          mx (max mx d)))
  mx)

;; Generic two-phase best fit of a point list:
;;   edgecons  = (i j target band)   crosscons = (i j target)
;;   1. pull crosses while holding edges EXACT; if crosses land inside
;;      xtol -> done, no failure.
;;   2. let edges flex within their bands and pull crosses; if edges
;;      stay in band and crosses land inside xtol -> done.
;;   3. otherwise edges held true (step-1 result), crosses as close as
;;      possible, failure flag set.
;; Returns (pts failed).
(defun pool:fitpoly (seed edgecons crosscons xtol / xcon e0 eb p1 p2)
  (setq xcon nil)
  (foreach c crosscons                  ; provided (non-NA) crosses only
    (if (caddr c)
        (setq xcon (cons (list (car c) (cadr c) (caddr c) (caddr c) 0.5) xcon))))
  (setq e0 (mapcar '(lambda (e) (list (car e) (cadr e) (caddr e) (caddr e) 1.0))
                   edgecons)
        eb (mapcar '(lambda (e) (list (car e) (cadr e)
                                      (- (caddr e) (cadddr e))
                                      (+ (caddr e) (cadddr e)) 1.0))
                   edgecons))
  (setq p1 (pool:relaxn seed (append xcon e0) 3000)
        p1 (pool:relaxn p1 e0 400))
  (if (<= (pool:crossmax p1 crosscons) xtol)
      (list p1 nil)
      (progn
        (setq p2 (pool:relaxn p1 (append xcon eb) 3000))
        (if (and (<= (pool:edgemax p2 edgecons) 0.05)
                 (<= (pool:crossmax p2 crosscons) (+ xtol 0.05)))
            (list p2 nil)
            (list p1 t)))))

;; The tip-to-tip widths LT-RT and LB-RB, in either corner order.
(defun pool:tippair (i j)
  (or (and (= i 6) (= j 3)) (and (= i 3) (= j 6))
      (and (= i 7) (= j 2)) (and (= i 2) (= j 7))))

;; Look up a provided cross target for corner pair (i j); nil if NA or
;; not in the active set.
(defun pool:crossget (crosscons i j / out)
  (foreach c crosscons
    (if (or (and (= (car c) i) (= (cadr c) j))
            (and (= (car c) j) (= (cadr c) i)))
        (setq out (caddr c))))
  out)

(defun pool:grecnm (i j)
  (strcat (nth i pool:*grecnames*) "-" (nth j pool:*grecnames*)))

;; Gray guide for a Grecian: 8-corner nominal body (solid perimeter,
;; dashed internal end chords), corner labels clear of the linework,
;; and the active mode's cross diagonals (dashed).  Returns the
;; highlight assoc (edge prompt-keys + one entry per cross name).
(setq pool:*grecnpts* (list (list 0.0 0.0) (list 360.0 0.0) (list 410.0 55.0)
                            (list 410.0 125.0) (list 360.0 180.0)
                            (list 0.0 180.0) (list -50.0 125.0)
                            (list -50.0 55.0)))

;; An OCTAGON is the same eight-corner shape with the same edge list --
;; only the proportions differ: its cuts run at 45 degrees (S = S1) and
;; its short flats match the cut faces, where a grecian's ends are long
;; and shallow.
;;
;; The guide is a REGULAR octagon -- 300 square, cut c = 300/(2+root 2)
;; = 87.87, so all eight sides come out 124.26 -- because that is what
;; the shape being measured looks like.  (An elongated guide made the
;; sheet read like a grecian's.)
(setq pool:*octnpts* (list (list 87.87 0.0) (list 212.13 0.0)
                           (list 300.0 87.87) (list 300.0 212.13)
                           (list 212.13 300.0) (list 87.87 300.0)
                           (list 0.0 212.13) (list 0.0 87.87)))

;; The Grecian / Octagon guide is built by gr:geo inside pool:grecflow
;; (a live-guide geometry function fed to pool:pvlive), so the ring
;; reshapes as the overalls and letters -- or the measured edges --
;; come in.  gr:geo keeps the flow's npts on the live ring, which is
;; what pool:greccross later draws the diagonals against.

;; Add the chosen mode's cross diagonals to the Grecian guide once the
;; perimeter is measured.  Returns the extended highlight assoc.
(defun pool:greccross (crosses pv npts / c ent)
  (foreach c crosses
    (setq ent (pool:pvadd (pool:pvlined (nth (car c) npts) (nth (cadr c) npts)))
          pv (cons (cons (caddr c) (list ent)) pv)))
  pv)

;; Full guided flow for a Grecian pool (all three cross-dim modes).
;; Caller handles sysvars / undo / zoom-extents.
;; Resolve the overall-sheet letters against the overalls: S/T close
;; against B (T absorbs any difference), S1/V against A (V absorbs);
;; NA entries are derived, and with a whole pair NA a nominal split is
;; used.  Returns (S T S1 V).
;; WALLS BEAT CORNERS.  T and V run along a wall, so a tape can be
;; held flat against them and they come back reliable.  S and S1 only
;; locate the VIRTUAL sharp corner out past the cut -- on a real pool
;; there is nothing there to measure to, so they are the softer
;; numbers.  When both are given, the wall wins and its partner is
;; re-derived from the overall (S = (B - T)/2, S1 = (A - V)/2); the
;; taped S / S1 still show in the report against what was drawn.
;; Only when the wall was NOT measured does S / S1 drive the shape.
(defun pool:grecov (aov bov sraw traw s1raw vraw / s tv s1 v)
  (cond
    (traw (setq s (/ (- bov traw) 2.0) tv traw))
    (sraw (setq s sraw tv (- bov (* 2.0 sraw))))
    (t (setq s (/ bov 8.0) tv (* 0.75 bov))))
  (cond
    (vraw (setq s1 (/ (- aov vraw) 2.0) v vraw))
    (s1raw (setq s1 s1raw v (- aov (* 2.0 s1raw))))
    (t (setq s1 (/ aov 6.0) v (* aov (/ 2.0 3.0)))))
  (list s tv s1 v))

;; Octagon overall sheet.  With the letters unmeasured the shape is
;; derived from A and B alone, per the sheet: the four corners are cut
;; at 45 degrees (so S = S1 = c) and the SHORT flats equal the cut
;; faces, i.e. every side of a square octagon is the same length.
;;   c = min(A,B) / (2 + sqrt 2)   ->   T = B - 2c,  V = A - 2c
;; A measured letter wins over the derivation, and -- exactly like the
;; grecian sheet -- the WALL letters (T, V) win over the corner ones
;; (S, S1) when both were taped.  Returns (S T S1 V).
(defun pool:octov (aov bov sraw traw s1raw vraw / c s tv s1 v)
  (setq c (/ (min aov bov) 3.41421356237))
  (cond
    (traw (setq s (/ (- bov traw) 2.0) tv traw))
    (sraw (setq s sraw tv (- bov (* 2.0 sraw))))
    (t (setq s c tv (- bov (* 2.0 c)))))
  (cond
    (vraw (setq s1 (/ (- aov vraw) 2.0) v vraw))
    (s1raw (setq s1 s1raw v (- aov (* 2.0 s1raw))))
    ;; an unmeasured vertical cut matches the horizontal one (45 deg)
    (t (setq s1 s v (- aov (* 2.0 s)))))
  (list s tv s1 v))

;; The overall-sheet ties (B T S A S1 V S2) are part of gr:geo's spec
;; when the Overall input method is chosen, laid around the live ring
;; the way pool:grecovties once laid them around the nominal one.

(defun pool:grecflow (oct / oldclay mode crosses pv imeth pvo ovbad ans xitems
                       nm2 npts grback
                       braw araw traw sraw s1raw vraw s2raw
                       ovres sv tv s1v vov hyp u2 vv2 bact aact sact s1act
                       tp bo le ri ltd lbd lew rtd rbd rew
                       evals edgecons crosscons dac dbd fq q
                       a b c d cen0 ml mr lend rend seed
                       res pts failed notes gcs gce gcarcs
                       xmin xmax ymin ymax w hh doff th cen odim
                       e p qq cc nm tgt act rows k fedge fcross
                       rbox mprims mlbls)
  (setq oldclay (getvar "CLAYER"))

  ;; perimeter input method first: measure every edge, or the overall
  ;; sheet (A/B overalls with the sides assumed symmetric).  The
  ;; cross-dim detail level is asked later, once the perimeter is in.
  ;; An octagon defaults to Overall -- knowing A and B is enough to
  ;; draw it, since its sides are all the same.
  (setq nm2 (if oct "Octagon" "Grecian")
        npts (if oct pool:*octnpts* pool:*grecnpts*))
  (defun gr:method ()
    ;; a form built from a sheet answers the LETTERS, which only the
    ;; Overall path asks for -- so this has to be form-answerable too,
    ;; or every letter it filled in would go unread
    (setq imeth (pool:askkwf 'imeth (strcat nm2 " perimeter input")
                             "Measured Overall" "Measured/Overall"
                             (if oct "Overall" nil) nil))
    nil)
  ;; The live guide geometry (see "live guide reshaping").  Both input
  ;; methods produce the same eight-corner ring in the index order the
  ;; whole flow reads, every unanswered value filled by the sheet's own
  ;; derivations -- so the first paint is the familiar nominal shape
  ;; and each answer reshapes it.  npts is left on the live ring, which
  ;; is what pool:greccross hangs the mode's diagonals on later.
  (defun gr:geo ( / bov aov ovr sv tvv s1v vov bo2 tp2 le2 ri2 qd
                    a2 b2 c2 d2 cenl ml mr u2 m0 cl ewd dy dg px
                    lt2 lb2 rt2 rb2 sc th spec km k p q e yt yb xa x2
                    tp1 tq1 nrm)
    (if (= imeth "Overall")
        (progn
          (setq bov (cond ((pool:pvdim 'b)) ((if oct 300.0 460.0)))
                aov (cond ((pool:pvdim 'a)) ((pool:pvdim 'b))
                          ((if oct 300.0 180.0)))
                ovr (if oct
                        (pool:octov aov bov (pool:pvdim 'ss) (pool:pvdim 'tt)
                                    (pool:pvdim 's1) (pool:pvdim 'vv))
                        (pool:grecov aov bov (pool:pvdim 'ss) (pool:pvdim 'tt)
                                     (pool:pvdim 's1) (pool:pvdim 'vv)))
                sv (max 1.0 (car ovr)) tvv (max 1.0 (cadr ovr))
                s1v (max 1.0 (caddr ovr)) vov (max 1.0 (cadddr ovr)))
          ;; the two frames the two nominal guides always used: the
          ;; grecian keeps A at the origin with the tips outboard, the
          ;; octagon keeps the tips on x = 0
          (if oct
              (setq npts (list (list sv 0.0) (list (+ sv tvv) 0.0)
                               (list bov s1v) (list bov (- aov s1v))
                               (list (+ sv tvv) aov) (list sv aov)
                               (list 0.0 (- aov s1v)) (list 0.0 s1v)))
              (setq npts (list (list 0.0 0.0) (list tvv 0.0)
                               (list (+ tvv sv) s1v)
                               (list (+ tvv sv) (- aov s1v))
                               (list tvv aov) (list 0.0 aov)
                               (list (- 0.0 sv) (- aov s1v))
                               (list (- 0.0 sv) s1v)))))
        (progn
          ;; measured edges: the body quad true to its four sides, each
          ;; end's tips projected off its chord -- the measured width
          ;; and diagonals where given, nominal proportions where not
          (setq bo2 (cond ((pool:pvdim 'bo)) ((pool:pvdim 'tp)) (360.0))
                tp2 (cond ((pool:pvdim 'tp)) ((pool:pvdim 'bo)) (bo2))
                le2 (cond ((pool:pvdim 'le)) ((pool:pvdim 'ri)) ((* 0.5 bo2)))
                ri2 (cond ((pool:pvdim 'ri)) ((pool:pvdim 'le)) (le2))
                qd (pool:fitsides bo2 tp2 le2 ri2 nil nil))
          (if (null qd)
              (setq qd (list (list 0.0 0.0) (list bo2 0.0)
                             (list bo2 (* 0.5 (+ le2 ri2))) (list 0.0 le2))))
          (setq a2 (car qd) b2 (cadr qd) c2 (caddr qd) d2 (cadddr qd)
                cenl (cal:v* (cal:v+ (cal:v+ a2 b2) (cal:v+ c2 d2)) 0.25)
                ml (pool:unit (cal:perp (cal:v- d2 a2))))
          (if (< (cal:dot (cal:v- (cal:mid a2 d2) cenl) ml) 0.0)
              (setq ml (cal:v* ml -1.0)))
          (setq mr (pool:unit (cal:perp (cal:v- c2 b2))))
          (if (< (cal:dot (cal:v- (cal:mid b2 c2) cenl) mr) 0.0)
              (setq mr (cal:v* mr -1.0)))
          ;; left end, centred on its chord
          (setq u2 (pool:unit (cal:v- d2 a2))
                m0 (cal:mid a2 d2)
                cl (distance a2 d2)
                ewd (min (cond ((pool:pvdim 'lew)) ((* 0.39 cl))) (* 0.95 cl))
                dy (* 0.5 (- cl ewd))
                dg (cond ((and (pool:pvdim 'ltd) (pool:pvdim 'lbd))
                          (* 0.5 (+ (pool:pvdim 'ltd) (pool:pvdim 'lbd))))
                         ((pool:pvdim 'ltd)) ((pool:pvdim 'lbd))
                         ((* 1.4142 dy)))
                px (sqrt (max (- (* dg dg) (* dy dy)) (* 0.01 cl cl)))
                lt2 (cal:v+ (cal:v+ m0 (cal:v* u2 (* 0.5 ewd)))
                             (cal:v* ml px))
                lb2 (cal:v+ (cal:v- m0 (cal:v* u2 (* 0.5 ewd)))
                             (cal:v* ml px)))
          ;; right end the same way
          (setq u2 (pool:unit (cal:v- c2 b2))
                m0 (cal:mid b2 c2)
                cl (distance b2 c2)
                ewd (min (cond ((pool:pvdim 'rew)) ((* 0.39 cl))) (* 0.95 cl))
                dy (* 0.5 (- cl ewd))
                dg (cond ((and (pool:pvdim 'rtd) (pool:pvdim 'rbd))
                          (* 0.5 (+ (pool:pvdim 'rtd) (pool:pvdim 'rbd))))
                         ((pool:pvdim 'rtd)) ((pool:pvdim 'rbd))
                         ((* 1.4142 dy)))
                px (sqrt (max (- (* dg dg) (* dy dy)) (* 0.01 cl cl)))
                rt2 (cal:v+ (cal:v+ m0 (cal:v* u2 (* 0.5 ewd)))
                             (cal:v* mr px))
                rb2 (cal:v+ (cal:v- m0 (cal:v* u2 (* 0.5 ewd)))
                             (cal:v* mr px))
                npts (list a2 b2 rb2 rt2 c2 d2 lt2 lb2))))
    ;; the ring, its labels, and (Overall only) the sheet ties
    (setq cenl (list 0.0 0.0))
    (foreach p npts (setq cenl (cal:v+ cenl p)))
    (setq cenl (cal:v* cenl 0.125)
          sc (/ (max (- (apply 'max (mapcar 'car npts))
                        (apply 'min (mapcar 'car npts)))
                     (- (apply 'max (mapcar 'cadr npts))
                        (apply 'min (mapcar 'cadr npts))))
                420.0)
          th (* 10.0 sc)
          spec nil km nil k 0)
    (foreach e pool:*grecedges*
      (setq p (nth (car e) npts) q (nth (cadr e) npts)
            spec (append spec
                         (list (list (if (member (caddr e) '(ad bc))
                                         "LINED" "LINE")
                                     p q)))
            km (cons (list (caddr e) k) km)
            k (1+ k)))
    (foreach p npts
      (setq spec (append spec
                         (list (list "TEXT"
                                     (pool:lbloff p cenl npts (* 22.0 sc))
                                     (* 12.0 sc)
                                     (nth (- k 10) pool:*grecnames*))))
            km (cons (list (pool:lblkey (nth (- k 10) pool:*grecnames*)) k) km)
            k (1+ k)))
    (if (= imeth "Overall")
        (progn
          ;; B/T/S across the top, A/S1/V down the left, S2 on the
          ;; bottom-right cut, like the field sheet
          (setq yt (+ aov (* 35.0 sc))
                yb (+ aov (* 62.0 sc)))
          (if oct
              (setq xa (- 0.0 (* 60.0 sc)) x2 (- 0.0 (* 30.0 sc))
                    tp1 (list 0.0 yb) tq1 (list bov yb))
              (setq xa (- 0.0 sv (* 45.0 sc)) x2 (- 0.0 sv (* 22.0 sc))
                    tp1 (list (- 0.0 sv) yb) tq1 (list (+ tvv sv) yb)))
          (setq nrm (pool:unit (cal:perp (cal:v- (nth 2 npts)
                                                   (nth 1 npts)))))
          (if (pool:inpoly (cal:v+ (cal:mid (nth 1 npts) (nth 2 npts)) nrm)
                           npts)
              (setq nrm (cal:v* nrm -1.0)))
          (setq spec (append spec
                       (pool:pvtiespec tp1 tq1 "B" th)
                       (pool:pvtiespec (list (if oct sv 0.0) yt)
                                       (list (if oct (+ sv tvv) tvv) yt)
                                       "T" th)
                       (pool:pvtiespec (list (if oct 0.0 (- 0.0 sv)) yt)
                                       (list (if oct sv 0.0) yt) "S" th)
                       (pool:pvtiespec (list xa 0.0) (list xa aov) "A" th)
                       (pool:pvtiespec (list x2 (- aov s1v)) (list x2 aov)
                                       "S1" th)
                       (pool:pvtiespec (list x2 s1v) (list x2 (- aov s1v))
                                       "V" th)
                       (pool:pvtiespec (cal:v+ (nth 1 npts)
                                                (cal:v* nrm (* 22.0 sc)))
                                       (cal:v+ (nth 2 npts)
                                                (cal:v* nrm (* 22.0 sc)))
                                       "S2" th)))
          (foreach p '("B" "T" "S" "A" "S1" "V" "S2")
            (setq km (cons (list p k (1+ k)) km)
                  k (+ k 2)))))
    (list spec km (pool:pvspecbox spec)))

  ;; the guide depends on the method, so it is (re)built by the stage
  ;; that follows it -- backing into the method question and out again
  ;; therefore always leaves a guide matching the chosen method
  (defun gr:guide ()
    (pool:pvkill)
    (setq mode "Simple" crosses nil
          pv (pool:pvlive 'gr:geo)
          pvo pv)
    nil)
  (princ "\nA gray guide pool is shown -- the RED element is the dimension being asked for.")
  (princ "\nCorners: A/B bottom, C/D top, LT/LB left tips, RT/RB right tips.")

  ;; -------- body + ends: measured edges, or the overall sheet
  (defun gr:perim ( / ans)
   (setq grback nil)
   (if (= imeth "Overall")
      (progn
        (princ (strcat "\nOverall sheet -- symmetric " (strcase nm2 t)
                       "; the RED tie is being asked for."))
        (if oct
            (princ "\nThe cut letters may all be NA: A and B alone draw the octagon."))
        (princ "\n(after the first answer, Back re-asks the previous one)")
        ;; An in-square OCTAGON is square, so its two overalls are one
        ;; measurement, asked once.  A GRECIAN is a long pool -- its A
        ;; and B are never equal -- so it is always asked for both,
        ;; in square or not.
        (setq ans (pool:askseqb
                    (append
                      (if (and oct pool:*insq*)
                          (list (list 'b 'REQ "Overall size (A & B are equal)"
                                      (append (cdr (assoc "B" pvo))
                                              (cdr (assoc "A" pvo)))))
                          (list (list 'b 'REQ "B - overall length" (cdr (assoc "B" pvo)))
                                (list 'a 'REQ "A - overall width" (cdr (assoc "A" pvo)))))
                      (list (list 'tt 'NAX "T - top side length" (cdr (assoc "T" pvo)))
                            (list 'ss 'NAX "S - corner cut along the side" (cdr (assoc "S" pvo)))
                            (list 's1 'NAX "S1 - corner cut down the end" (cdr (assoc "S1" pvo)))
                            (list 'vv 'NAX "V - end width" (cdr (assoc "V" pvo)))
                            (list 's2 'NAX "S2 - corner cut face (check)" (cdr (assoc "S2" pvo)))))
                    t))
        (if (eq ans 'CAL-BACK)
            (setq grback t braw 1.0 araw 1.0 ans nil))
        (setq braw (pool:sq ans 'b)
              araw (if (and oct pool:*insq*) braw (pool:sq ans 'a))
              traw (pool:sq ans 'tt) sraw (pool:sq ans 'ss)
              s1raw (pool:sq ans 's1) vraw (pool:sq ans 'vv)
              s2raw (pool:sq ans 's2)
              ovres (if grback
                        (list 1.0 1.0 1.0 1.0)
                        (if oct
                            (pool:octov araw braw sraw traw s1raw vraw)
                            (pool:grecov araw braw sraw traw s1raw vraw)))
              sv (car ovres) tv (cadr ovres)
              s1v (caddr ovres) vov (cadddr ovres))
        ;; walls beat corners (see pool:grecov): say so when holding a
        ;; taped T / V actually moved the taped S / S1, so the crew can
        ;; see in the report why their corner number came out different
        (if (and traw sraw (> (abs (- sv sraw)) 0.5))
            (princ (strcat "\nT is a wall, so it is held true -- S re-derived "
                           (rtos sraw 2 2) " -> " (rtos sv 2 2) ".")))
        (if (and vraw s1raw (> (abs (- s1v s1raw)) 0.5))
            (princ (strcat "\nV is a wall, so it is held true -- S1 re-derived "
                           (rtos s1raw 2 2) " -> " (rtos s1v 2 2) ".")))
        ;; the sheet letters must close POSITIVE against the overalls;
        ;; a letter that does not fit is adjusted, warned about now,
        ;; and its report rows go red
        (if (<= tv 1.0e-6)
            (progn
              (setq tv (min 12.0 (* 0.25 braw)) sv (/ (- braw tv) 2.0) ovbad t)
              (pool:valnote "OVERALL SHEET FAILED - S + T + S DOES NOT FIT B, ADJUSTED")))
        (if (<= sv 1.0e-6)
            (progn
              (setq sv (min 12.0 (* 0.125 braw)) tv (- braw sv sv) ovbad t)
              (pool:valnote "OVERALL SHEET FAILED - T LONGER THAN B, ADJUSTED")))
        (if (<= vov 1.0e-6)
            (progn
              (setq vov (min 12.0 (* 0.25 araw)) s1v (/ (- araw vov) 2.0) ovbad t)
              (pool:valnote "OVERALL SHEET FAILED - S1 + V + S1 DOES NOT FIT A, ADJUSTED")))
        (if (<= s1v 1.0e-6)
            (progn
              (setq s1v (min 12.0 (* 0.125 araw)) vov (- araw s1v s1v) ovbad t)
              (pool:valnote "OVERALL SHEET FAILED - V LONGER THAN A, ADJUSTED")))
        (setq hyp (sqrt (+ (* sv sv) (* s1v s1v)))
              bo tv tp tv le araw ri araw
              ltd hyp lbd hyp rtd hyp rbd hyp
              lew vov rew vov))
      (progn
        (princ "\n(Back re-asks the previous question)")
        (if pool:*insq*
            (progn
            (setq ans (pool:askseqb
                        (list (list 'bo 'REQ "Side (top & bottom)"
                                    (append (cdr (assoc 'ab pv)) (cdr (assoc 'cd pv))))
                              (list 'le 'REQ "Body end (left & right, A-D / B-C)"
                                    (append (cdr (assoc 'ad pv)) (cdr (assoc 'bc pv))))
                              (list 'ltd 'REQ "LEFT end diagonals (top & bottom)"
                                    (append (cdr (assoc 'ltd pv)) (cdr (assoc 'lbd pv))))
                              (list 'lew 'REQ "LEFT end width (LT-LB)"
                                    (append (cdr (assoc 'lew pv)) (pool:lbl pv '(lLT lLB))))
                              (list 'rtd 'REQ "RIGHT end diagonals (top & bottom)"
                                    (append (cdr (assoc 'rtd pv)) (cdr (assoc 'rbd pv))))
                              (list 'rew 'REQ "RIGHT end width (RT-RB)"
                                    (append (cdr (assoc 'rew pv)) (pool:lbl pv '(lRT lRB)))))
                        t))
            (if (eq ans 'CAL-BACK)
                (setq grback t)
                (setq bo (pool:sq ans 'bo) tp bo
                      le (pool:sq ans 'le) ri le
                      ltd (pool:sq ans 'ltd) lbd ltd
                      lew (pool:sq ans 'lew)
                      rtd (pool:sq ans 'rtd) rbd rtd
                      rew (pool:sq ans 'rew))))
            (progn
            (setq ans (pool:askseqb
                        (list (list 'bo 'REQ "Side BOTTOM (A-B)"
                                    (append (cdr (assoc 'ab pv)) (pool:lbl pv '(lA lB))))
                              (list 'tp 'REQ "Side TOP (D-C)"
                                    (append (cdr (assoc 'cd pv)) (pool:lbl pv '(lD lC))))
                              (list 'le 'REQ "End LEFT (A-D)"
                                    (append (cdr (assoc 'ad pv)) (pool:lbl pv '(lA lD))))
                              (list 'ri 'REQ "End RIGHT (B-C)"
                                    (append (cdr (assoc 'bc pv)) (pool:lbl pv '(lB lC))))
                              (list 'ltd 'REQ "LEFT end diagonal TOP (D-LT)"
                                    (append (cdr (assoc 'ltd pv)) (pool:lbl pv '(lD lLT))))
                              (list 'lbd 'REQ "LEFT end diagonal BOTTOM (A-LB)"
                                    (append (cdr (assoc 'lbd pv)) (pool:lbl pv '(lA lLB))))
                              (list 'lew 'REQ "LEFT end width (LT-LB)"
                                    (append (cdr (assoc 'lew pv)) (pool:lbl pv '(lLT lLB))))
                              (list 'rtd 'REQ "RIGHT end diagonal TOP (C-RT)"
                                    (append (cdr (assoc 'rtd pv)) (pool:lbl pv '(lC lRT))))
                              (list 'rbd 'REQ "RIGHT end diagonal BOTTOM (B-RB)"
                                    (append (cdr (assoc 'rbd pv)) (pool:lbl pv '(lB lRB))))
                              (list 'rew 'REQ "RIGHT end width (RT-RB)"
                                    (append (cdr (assoc 'rew pv)) (pool:lbl pv '(lRT lRB)))))
                        t))
            (if (eq ans 'CAL-BACK)
                (setq grback t)
                (setq bo (pool:sq ans 'bo) tp (pool:sq ans 'tp)
                      le (pool:sq ans 'le) ri (pool:sq ans 'ri)
                      ltd (pool:sq ans 'ltd) lbd (pool:sq ans 'lbd)
                      lew (pool:sq ans 'lew)
                      rtd (pool:sq ans 'rtd) rbd (pool:sq ans 'rbd)
                      rew (pool:sq ans 'rew)))))))
   (if grback 'CAL-BACK nil))

  ;; -------- the perimeter is in: now pick the cross-dim detail level,
  ;; draw those diagonals on the guide, and measure them (NA allowed)
  (defun gr:cross ( / ans xg v)
   (setq crosses nil xg nil)
   (if (not pool:*insq*)
      (progn
        (setq v (pool:askkwf 'gcross (strcat nm2 " cross-dim detail")
                             "Simple Center Complex" "Simple/Center/Complex"
                             nil t))
        (if (eq v 'CAL-BACK) (setq grback t)
            (setq mode v
                  crosses (pool:grecmode mode)
                  xg (mapcar '(lambda (c) (car (cdr (assoc (caddr c) pv))))
                             crosses)
                  pv (pool:greccross crosses pv npts)
                  xg (mapcar '(lambda (c) (car (cdr (assoc (caddr c) pv))))
                             crosses)))))
   (if grback
       'CAL-BACK
       (progn (gr:crossask xg) (if grback 'CAL-BACK nil))))

  (defun gr:crossask (xg / ans)
  (setq crosscons nil xitems nil k 0)
  (foreach e crosses
    (setq xitems (cons (list (read (strcat "x" (itoa k))) 'NAX
                             (strcat "Cross dim " (caddr e))
                             (append (cdr (assoc (caddr e) pv))
                                     (pool:lbl pv
                                       (list (pool:lblkey (nth (car e) pool:*grecnames*))
                                             (pool:lblkey (nth (cadr e) pool:*grecnames*))))))
                       xitems)
          k (1+ k)))
  (setq ans (if xitems (pool:askseqb (reverse xitems) t) nil) k 0)
  (if (eq ans 'CAL-BACK)
      (progn (pool:pvdel xg) (setq grback t crosses nil ans nil)))
  (foreach e crosses
    (setq crosscons (cons (list (car e) (cadr e)
                                (pool:sq ans (read (strcat "x" (itoa k)))))
                          crosscons)
          k (1+ k)))
  (setq crosscons (reverse crosscons))
  (princ))

  ;; -------- seed: fit the body quad, project nominal ends.
  ;; Runs at the top of gr:corners rather than after the input phase,
  ;; because a treatment's setback depends on the corner's real angle
  ;; -- and a grecian's corners are 135 degrees, not 90.  Pure, so
  ;; backing into a measurement and forward again simply re-fits.
  (defun gr:fit ( / )
  (setq evals (list (cons 'ab bo) (cons 'cd tp) (cons 'ad le) (cons 'bc ri)
                    (cons 'rbd rbd) (cons 'rew rew) (cons 'rtd rtd)
                    (cons 'ltd ltd) (cons 'lew lew) (cons 'lbd lbd))
        edgecons (mapcar '(lambda (e)
                            (list (car e) (cadr e) (cdr (assoc (caddr e) evals)) (cadddr e)))
                         pool:*grecedges*)
        dac (pool:crossget crosscons 0 4)
        dbd (pool:crossget crosscons 1 5)
        fq (pool:fitquad bo tp le ri dac dbd pool:*side-tol* pool:*cross-tol*)
        q (car fq)
        a (car q) b (cadr q) c (caddr q) d (cadddr q)
        cen0 (cal:v* (cal:v+ (cal:v+ a b) (cal:v+ c d)) 0.25)
        ml (pool:unit (cal:perp (cal:v- d a))))
  (if (< (cal:dot (cal:v- (cal:mid a d) cen0) ml) 0.0)
      (setq ml (cal:v* ml -1.0)))
  (setq mr (pool:unit (cal:perp (cal:v- c b))))
  (if (< (cal:dot (cal:v- (cal:mid b c) cen0) mr) 0.0)
      (setq mr (cal:v* mr -1.0)))
  (setq lend (pool:grecendp a d ml ltd lbd lew)
        rend (pool:grecendp b c mr rtd rbd rew)
        seed (list a b (cadr rend) (car rend) c d (car lend) (cadr lend))
        notes nil)
  (if (not (nth 5 lend))
      (setq notes (cons "LEFT END: diagonals/width did not fit -- 45 seed used" notes)))
  (if (not (nth 5 rend))
      (setq notes (cons "RIGHT END: diagonals/width did not fit -- 45 seed used" notes)))

  ;; -------- fit: Simple keeps the validated seed; Center/Complex
  ;; best-fit all 8 corners against every provided cross dim.
  ;; The tip-to-tip widths LT-RT and LB-RB are what B WOULD be on an
  ;; ideal grecian, so when measured they are held like WALLS (the
  ;; 1-inch edge band) -- just as the body chords A-D and B-C already
  ;; are -- rather than pulled like cross dims in the 2-inch band.
  ;; They still get their CROSS DIMENSIONS-style dim and report row
  ;; like any tie.
  (if (= mode "Simple")
      (setq pts seed failed (cadr fq))
      (progn
        (setq fedge edgecons fcross nil)
        (foreach cc crosscons
          (if (and (caddr cc) (pool:tippair (car cc) (cadr cc)))
              (setq fedge (append fedge
                                  (list (list (car cc) (cadr cc) (caddr cc)
                                              pool:*side-tol*))))
              (setq fcross (cons cc fcross))))
        (setq res (pool:fitpoly seed fedge (reverse fcross) pool:*cross-tol*)
              pts (car res)
              failed (cadr res))))
  (princ))

  ;; -------- corner treatments.  A grecian's 8 corners come in two
  ;; families: the BODY corners A/B/C/D, where a long wall runs into a
  ;; cut face, and the END TIPS LT/LB/RT/RB, where that cut face lands
  ;; on the end wall.  In square the two families take one answer each
  ;; (the tips default to the body answer, since a pool that rounds
  ;; one usually rounds both); out of square every corner is asked on
  ;; its own, Enter reusing the previous -- the same split the
  ;; rectangle makes.
  ;;
  ;; The shape is FIT at the top of this stage, exactly as the L pool
  ;; fits at the top of its own corner stage: the setback depends on
  ;; the real corner angle, and fitting inside the stage (rather than
  ;; as a stage of its own) keeps Back working -- an always-succeeding
  ;; stage would swallow the Back out of the corner question.
  (defun gr:corners ( / v bc tc bcap tcap bsb v2 k caps angs lbls ents)
    (princ "\nFitting pool body to the measurements ...")
    (gr:fit)
    (setq gcs (list (list "Square" 0.0) (list "Square" 0.0) (list "Square" 0.0)
                    (list "Square" 0.0) (list "Square" 0.0) (list "Square" 0.0)
                    (list "Square" 0.0) (list "Square" 0.0)))
    (setq v (pool:askynf 'crec
                         "Anything to record about the corners (radius / cut / not given)?"
                         "No" t))
    (cond
      ((eq v 'CAL-BACK) 'CAL-BACK)
      ((not v) nil)
      (pool:*insq*
       ;; one answer for the four body corners, one for the four tips.
       ;; The body answer covers the SHARPEST of A/B/C/D, since that is
       ;; the corner whose cut reaches furthest along its walls, and is
       ;; budgeted half the shortest wall it touches -- which leaves
       ;; the other half of every cut face for the tip on its far end.
       (setq bcap (pool:groupcap pts pool:*grecbody*)
             bc (pool:askcorner "the body corners A, B, C and D" nil nil
                                (pool:lbl pv '(lA lB lC lD))
                                (car bcap) (cadr bcap) t))
       (if (eq bc 'CAL-BACK)
           'CAL-BACK
           (progn
             ;; each tip is then capped by what the body cut actually
             ;; LEFT on the cut face they share; the two tips on one
             ;; END wall share that wall with each other, so it halves
             (setq bsb (* (cadr bc) (pool:cornerk (car bc) (cadr bcap)))
                   tcap nil)
             (foreach k pool:*greccuts*
               (setq v2 (- (distance (nth (car k) pts) (nth (cadr k) pts)) bsb)
                     tcap (if tcap (min tcap v2) v2)))
             (foreach k pool:*grecwalls*
               (setq v2 (* 0.5 (distance (nth (car k) pts) (nth (cadr k) pts)))
                     tcap (min tcap v2)))
             (setq tc (pool:askcorner "the end-tip corners LT, LB, RT and RB"
                                      (car bc) (cadr bc)
                                      (pool:lbl pv '(lLT lLB lRT lRB))
                                      (max 0.0 tcap)
                                      (cadr (pool:groupcap pts pool:*grectips*)) t))
             (if (eq tc 'CAL-BACK)
                 'CAL-BACK
                 ;; index order is 0=A 1=B 2=RB 3=RT 4=C 5=D 6=LT 7=LB
                 (progn (setq gcs (list bc bc tc tc bc bc tc tc)) nil)))))
      (t
       ;; out of square: all eight, round the perimeter, Enter reusing
       (princ "\n(per-corner treatment; press Enter to reuse the previous corner)")
       (setq caps nil angs nil lbls nil ents nil k 0)
       (while (< k 8)
         (setq caps (cons (pool:polycap pts k) caps)
               angs (cons (pool:polywedge pts k) angs)
               lbls (cons (strcat "Corner " (nth k pool:*grecnames*)) lbls)
               ents (cons (pool:lbl pv (list (pool:lblkey (nth k pool:*grecnames*))))
                          ents)
               k (1+ k)))
       (setq v (pool:askcorners (reverse lbls) (reverse caps)
                                (reverse angs) (reverse ents)))
       (if (eq v 'CAL-BACK)
           'CAL-BACK
           (progn (setq gcs v) nil)))))

  ;; ---- the input phase, with Back working right across it
  (pool:stages (list 'gr:method 'gr:guide 'gr:perim 'gr:cross 'gr:corners))
  (pool:pvkill)

  ;; pts / failed / notes were fit at the top of gr:corners, so the
  ;; corner questions could be sized against the real corner angles
  (setq gce (pool:ringends pts gcs))

  ;; -------- extents / scale
  (setq xmin (apply 'min (mapcar 'car pts))
        xmax (apply 'max (mapcar 'car pts))
        ymin (apply 'min (mapcar 'cadr pts))
        ymax (apply 'max (mapcar 'cadr pts))
        w (- xmax xmin) hh (- ymax ymin)
        doff (max 12.0 (/ (max w hh) 18.0))
        th (max 3.0 (/ (max w hh) 70.0))
        pool:*dashlt* (pool:ltload "DASHED")
        cen (list 0.0 0.0))
  (foreach p pts (setq cen (cal:v+ cen p)))
  (setq cen (cal:v* cen (/ 1.0 8.0)))

  ;; -------- perimeter (POOL) + internal end chords (dashed,
  ;; POOL-NOTES).  Perimeter walls run between the corner TREATMENT
  ;; ends and the treatment itself closes each corner (a square corner
  ;; degenerates to the plain corner-to-corner wall); the two internal
  ;; chords are not walls, so they stay on the true corners.
  (foreach e pool:*grecedges*
    (setq p (nth (car e) pts) qq (nth (cadr e) pts))
    (if (member (caddr e) '(ad bc))
        (pool:lined p qq)
        (pool:line (cadr (nth (car e) gce))          ; eNext(i)
                   (car (nth (cadr e) gce)) "POOL"))) ; ePrev(j)
  (setq gcarcs (pool:ringarcs gce gcs "POOL"))

  ;; -------- dimensions (DIMENSION)
  ;; In-square: the field-sheet exterior set only -- S+T share a row
  ;; above the top with B outboard of them, S1+V share a column left
  ;; of the pool with A outboard, and S2 reads once on the
  ;; bottom-right cut.  Every corner is the same corner in square, so
  ;; one of each keeps the sheet clean.  Out-of-square: every edge
  ;; differs, so every edge is dimensioned as before.
  ;; Style split per the reference sheet: the letters that SUBDIVIDE
  ;; an overall (S, T, S1, V -- and out of square, every edge) read in
  ;; SIDE STANDARD; the overalls themselves (B, A / the end chords)
  ;; and the S2 corner cut stay in the standard style.
  (setvar "CLAYER" "DIMENSION")
  (if pool:*insq*
      (progn
        ;; S: pool's left extreme to the top side start (row 1)
        (setq p (nth 6 pts) qq (nth 5 pts))              ; LT, D
        (pool:dimalgs (list (car p) ymax) qq
                      (list (* 0.5 (+ (car p) (car qq))) (+ ymax doff)))
        ;; T: the top side D-C (row 1)
        (pool:dimalgs (nth 5 pts) (nth 4 pts)
                      (list (car (cal:mid (nth 5 pts) (nth 4 pts)))
                            (+ ymax doff)))
        ;; B: overall, tip to tip LT-RT (row 2, outboard)
        (pool:dimalg (nth 6 pts) (nth 3 pts)
                     (list (car (cal:mid (nth 6 pts) (nth 3 pts)))
                           (+ ymax (* 1.9 doff))))
        ;; S1: top down to the left tip (column 1)
        (pool:dimalgs (list xmin ymax) (nth 6 pts)
                      (list (- xmin doff)
                            (* 0.5 (+ ymax (cadr (nth 6 pts))))))
        ;; V: the left end LT-LB (column 1)
        (pool:dimalgs (nth 6 pts) (nth 7 pts)
                      (list (- xmin doff)
                            (cadr (cal:mid (nth 6 pts) (nth 7 pts)))))
        ;; A: overall, the A-D chord (column 2, outboard)
        (pool:dimalg (nth 0 pts) (nth 5 pts)
                     (list (- xmin (* 1.9 doff))
                           (cadr (cal:mid (nth 0 pts) (nth 5 pts)))))
        ;; S2: the bottom-right corner cut, once
        (pool:dimalg (nth 1 pts) (nth 2 pts)
                     (pool:outoffp (nth 1 pts) (nth 2 pts) pts doff)))
      (foreach e pool:*grecedges*
        (setq p (nth (car e) pts) qq (nth (cadr e) pts))
        (cond
          ((= (caddr e) 'ad)            ; left end chord -> outboard left
           (pool:dimalg p qq (list (- xmin (* 0.6 doff)) (cadr (cal:mid p qq)))))
          ((= (caddr e) 'bc)            ; right end chord -> outboard right
           (pool:dimalg p qq (list (+ xmax (* 0.6 doff)) (cadr (cal:mid p qq)))))
          (t
           (pool:dimalgs p qq (pool:outoffp p qq pts doff))))))
  ;; provided cross dims, in the CROSS DIMENSIONS style when available
  (setq odim (pool:dimxbegin) k 0)
  (foreach cc crosscons
    (if (caddr cc)
        (pool:dimalg (nth (car cc) pts) (nth (cadr cc) pts)
                     (cal:v+ (cal:mid (nth (car cc) pts) (nth (cadr cc) pts))
                              (cal:v* (pool:unit
                                         (cal:perp (cal:v- (nth (cadr cc) pts)
                                                             (nth (car cc) pts))))
                                       (* (if (= 0 (rem k 2)) 0.12 -0.12) doff)))))
    (setq k (1+ k)))
  (pool:dimxend odim)
  ;; corner treatments: one Typ. per family in square (body / tips),
  ;; each treated corner its own dim out of square (collapsing back to
  ;; Typ. when Enter reused one answer all the way round)
  ;; out of square the eight are their own groups -- but B leads the
  ;; list, as it does in square, so an all-same answer puts its one
  ;; Typ. mark on the same corner either way
  (pool:dimringcorners pts gcs gce gcarcs cen doff
                       (if pool:*insq*
                           (list '(1 0 4 5) '(2 3 6 7))
                           (mapcar 'list '(1 0 2 3 4 5 6 7))))
  (setvar "CLAYER" oldclay)

  ;; corner letters live on the mini-model beside the report, not in
  ;; the corners of the drawing itself -- see the pool:minimap call

  ;; -------- report table
  (setq rows nil)
  (foreach e pool:*grecedges*
    (setq nm (pool:grecnm (car e) (cadr e))
          tgt (cdr (assoc (caddr e) evals))
          act (distance (nth (car e) pts) (nth (cadr e) pts))
          rows (cons (list nm tgt act) rows)))
  (foreach cc crosscons
    (setq nm (pool:grecnm (car cc) (cadr cc))
          act (distance (nth (car cc) pts) (nth (cadr cc) pts))
          rows (cons (list (strcat "X " nm) (caddr cc) act) rows)))
  (setq rows (reverse rows))
  ;; corner treatments: one row per family in square, per corner out
  (setq rows (append rows
    (if pool:*insq*
        (pool:cornerrows (list "BODY CORNER" "END TIP")
                         (list (nth 0 gcs) (nth 2 gcs)))
        (pool:cornerrows (mapcar '(lambda (nm) (strcat "CORNER " nm))
                                 pool:*grecnames*)
                         gcs))))
  ;; overall-sheet letters vs the fitted shape
  (if (= imeth "Overall")
      (progn
        (setq u2 (cal:v- (nth 1 pts) (nth 0 pts))
              vv2 (cal:v- (nth 5 pts) (nth 0 pts))
              bact (distance
                     (pool:linex cen u2 (nth 7 pts) (cal:v- (nth 6 pts) (nth 7 pts)))
                     (pool:linex cen u2 (nth 2 pts) (cal:v- (nth 3 pts) (nth 2 pts))))
              aact (distance
                     (pool:linex cen vv2 (nth 0 pts) u2)
                     (pool:linex cen vv2 (nth 5 pts) (cal:v- (nth 4 pts) (nth 5 pts))))
              sact (abs (cal:dot (cal:v- (nth 6 pts) (nth 5 pts)) (pool:unit u2)))
              s1act (abs (cal:dot (cal:v- (nth 6 pts) (nth 5 pts)) (pool:unit vv2))))
        (setq rows (append rows (list
          (list "OV B" braw bact)
          (list "OV A" araw aact)
          (append (list "OV T" traw (distance (nth 5 pts) (nth 4 pts)))
                  (if ovbad (list t) nil))
          (append (list "OV S" sraw sact) (if ovbad (list t) nil))
          (append (list "OV S1" s1raw s1act) (if ovbad (list t) nil))
          (append (list "OV V" vraw (distance (nth 6 pts) (nth 7 pts)))
                  (if ovbad (list t) nil))
          (list "OV S2" s2raw (distance (nth 5 pts) (nth 6 pts))))))))
  ;; -------- pool bottom (interior pipeline)
  (setq rows (append rows (pool:hopgrecdsp pts doff th)))
  (if failed (setq notes (cons "CROSS DIMS FAILED" notes)))
  (setq notes (append notes pool:*valnotes*))
  (setq rbox (pool:report rows notes (+ xmax (* 2.0 doff)) ymax th "POOL-NOTES"))
  ;; perimeter mini-model with the corner letters, right of the report
  (setq mprims nil k 0)
  (foreach e pool:*grecedges*
    (if (not (member (caddr e) '(ad bc)))
        (setq mprims (cons (list 'l (nth (car e) pts) (nth (cadr e) pts))
                           mprims))))
  (setq mlbls nil)
  (foreach p pts
    (setq mlbls (append mlbls (list (cons p (nth (length mlbls) pool:*grecnames*))))))
  (pool:minimap mprims pts mlbls (+ (car rbox) (* 3.0 th)) (cadr rbox)
                (* 24.0 th) th)
  (if failed
      (princ "\n*** CROSS DIMS FAILED -- sides held true, see report table ***")
      (princ "\nPool layout complete -- see the report table."))
  (princ))

;;; -------------------- L / Lazy L pools --------------------------------
;;;
;;;  Six-corner pools, one wing:      F -------- E
;;;                                   |           \
;;;    True L: joint D-E is a         |            D ------- C
;;;    square step; Lazy L: D-E       |                      |
;;;    is an angled joint.            A -------------------- B
;;;
;;;  Sides A-B, B-C, C-D, D-E, E-F, F-A plus up to six cross dims
;;;  (A-C, B-D, C-E, D-F, A-E, B-F -- any of them may be NA).

(setq pool:*hexsides* (list '(0 1) '(1 2) '(2 3) '(3 4) '(4 5) '(5 0)))
(setq pool:*hexsidenames* (list "A-B" "B-C" "C-D" "D-E" "E-F" "F-A"))
(setq pool:*hexdiags* (list '(0 2) '(1 3) '(2 4) '(3 5) '(0 4) '(1 5)
                            '(0 3) '(1 4) '(2 5)))
(setq pool:*hexdiagnames* (list "A-C" "B-D" "C-E" "D-F" "A-E" "B-F"
                                "A-D" "B-E" "C-F"))

;; Nominal right-angle (or 45-degree jointed) L built from the given
;; side lengths -- the starting shape for the relaxation fit.
(defun pool:hexguess (sides lazy / ab bc cd de fa a b c d e f)
  (setq ab (nth 0 sides) bc (nth 1 sides) cd (nth 2 sides)
        de (nth 3 sides) fa (nth 5 sides)
        a (list 0.0 0.0)
        b (list ab 0.0))
  (if lazy
      ;; constant-width pool bent 45 degrees (per the reference):
      ;; B-C and D-E are the bend sides, C-D the far end
      (setq c (cal:v+ b (list (* bc 0.7071067812) (* bc 0.7071067812)))
            d (cal:v+ c (list (* cd -0.7071067812) (* cd 0.7071067812)))
            e (cal:v+ d (list (* de -0.7071067812) (* de -0.7071067812)))
            f (list 0.0 fa))
      ;; true L (per the reference): B-C is the full right end, the
      ;; wing sits top-right and the notch top-left
      (setq c (list ab bc)
            d (list (- ab cd) bc)
            e (cal:v- d (list 0.0 de))
            f (cal:v- e (list (nth 4 sides) 0.0))))
  (list a b c d e f))

;; In-square lazy L: the DEEP END is what has to be right.  The hopper
;; sits in the main section (A - break - E - F) and is dimensioned off
;; A-B, E-F and F-A, so those three are held EXACTLY and the main body
;; comes out a true rectangle -- A-B and E-F dead horizontal, F-A dead
;; vertical, square corners at A and F.
;;
;; That leaves the wing to absorb whatever the tape did not close.
;; B-C and D-E are held PARALLEL (both on the 45-degree bend), so the
;; only freedom left is how far C and D slide along their own bend
;; lines: one number, m -- the slide of D relative to C, measured
;; along the bend.  It is picked to spread the closure error over the
;; three wing sides in the least-squares sense: B-C and D-E give up
;; half of it each (one grows exactly as much as the other shrinks)
;; and C-D takes what is left.  Every one of those deltas shows in the
;; report, red past pool:*side-tol* (see the SIDES DO NOT CLOSE note).
;;
;; The old build walked the whole chain A->B->C->D->E at exact headings
;; and dropped F onto the left wall, which piled the entire closure
;; error into E-F and F-A -- the two sides the hopper is measured
;; from, and the two that must not move.

;; Summed squared length error of the three wing sides at slide m.
;; m0 is the slide the taped B-C / D-E would have; (vx vy) is B->E,
;; the wing's closing vector, so C-D comes to |(vx+m, vy+m)|.  B-C and
;; D-E split (m - m0) between them, which lands their two squared
;; errors at exactly (m - m0)^2 together.
(defun pool:hexwing (m m0 vx vy cd / g)
  (setq g (sqrt (max 0.0 (+ (* 2.0 m m) (* 2.0 m (+ vx vy))
                            (* vx vx) (* vy vy)))))
  (+ (* (- m m0) (- m m0)) (* (- g cd) (- g cd))))

(defun pool:hexsquare (sides / u ab bc cd de ef fa a b c d e f vx vy m0
                             lo hi n i step m fm bm bf m1 m2 sl s1 s2)
  (setq u 0.7071067812
        ab (nth 0 sides) bc (nth 1 sides) cd (nth 2 sides)
        de (nth 3 sides) ef (nth 4 sides) fa (nth 5 sides)
        a (list 0.0 0.0)
        b (list ab 0.0)
        f (list 0.0 fa)
        e (list ef fa)
        vx (- (car e) (car b))
        vy (- (cadr e) (cadr b))
        m0 (* u (- de bc))
        ;; C stays past B and D past E: the slide can never eat more
        ;; than a bend side's own length (a hair inside, so neither
        ;; collapses to nothing)
        lo (+ (- m0 (* 2.0 u de)) 0.001)
        hi (- (+ m0 (* 2.0 u bc)) 0.001)
        n 240
        step (/ (- hi lo) n)
        bm m0
        bf (pool:hexwing m0 m0 vx vy cd)
        i 0)
  ;; coarse sweep first -- the wing error is a squared distance to a
  ;; circle and can hold two dips, so start the polish in the deeper
  ;; one rather than wherever a local slope points
  (while (<= i n)
    (setq m (+ lo (* i step))
          fm (pool:hexwing m m0 vx vy cd))
    (if (< fm bf) (setq bf fm bm m))
    (setq i (1+ i)))
  ;; ternary polish inside the winning bucket
  (setq lo (max lo (- bm step))
        hi (min hi (+ bm step))
        i 0)
  (while (< i 40)
    (setq m1 (+ lo (/ (- hi lo) 3.0))
          m2 (- hi (/ (- hi lo) 3.0)))
    (if (< (pool:hexwing m1 m0 vx vy cd) (pool:hexwing m2 m0 vx vy cd))
        (setq hi m2)
        (setq lo m1))
    (setq i (1+ i)))
  (setq m (* 0.5 (+ lo hi))
        sl (/ (- m m0) (* 2.0 u))     ; what each bend side gives up
        s1 (- bc sl)
        s2 (+ de sl)
        c (cal:v+ b (list (* s1 u) (* s1 u)))
        d (cal:v+ e (list (* s2 u) (* s2 u))))
  (list a b c d e f))

;; Side constraints (banded by +/-band) for the hexagon.
(defun pool:hexsidecon (sides band w / k out pr)
  (setq k 0 out nil)
  (foreach pr pool:*hexsides*
    (setq out (cons (list (car pr) (cadr pr)
                          (- (nth k sides) band) (+ (nth k sides) band) w)
                    out)
          k (1+ k)))
  (reverse out))

;; Exact-pull constraints for the provided (non-NA) cross dims.
(defun pool:hexdiagcon (diags w / k out pr tgt)
  (setq k 0 out nil)
  (foreach pr pool:*hexdiags*
    (setq tgt (nth k diags))
    (if tgt
        (setq out (cons (list (car pr) (cadr pr) tgt tgt w) out)))
    (setq k (1+ k)))
  (reverse out))

;; (max-side-delta max-cross-delta) of a fitted hexagon; NA cross dims
;; are ignored.
(defun pool:hexerr (pts sides diags / k pr smax xmax d)
  (setq smax 0.0 xmax 0.0 k 0)
  (foreach pr pool:*hexsides*
    (setq d (abs (- (distance (nth (car pr) pts) (nth (cadr pr) pts))
                    (nth k sides)))
          smax (max smax d)
          k (1+ k)))
  (setq k 0)
  (foreach pr pool:*hexdiags*
    (if (nth k diags)
        (setq d (abs (- (distance (nth (car pr) pts) (nth (cadr pr) pts))
                        (nth k diags)))
              xmax (max xmax d)))
    (setq k (1+ k)))
  (list smax xmax))

;; Fit the L hexagon (same policy as the quad):
;;  1. sides held true, provided cross dims pulled as close as they
;;     will come; inside tolerance -> done
;;  2. sides may flex inside +/-stol to pull the cross dims in
;;  3. otherwise sides held true, cross dims as close as possible,
;;     failure flag set
;; Returns (pts failed).
(defun pool:fithex (sides diags lazy stol xtol / guess p1 e1 p2 e2 any dg)
  ;; In-square lazy L (no cross dims measured): build the shape at
  ;; exact headings instead of relaxing, so A-B // E-F and B-C // D-E
  ;; hold perfectly and the closure error goes into the WING lengths,
  ;; leaving the deep-end sides (A-B, E-F, F-A) true -- pool:hexsquare.
  (setq any nil)
  (foreach dg diags (if dg (setq any t)))
  (if (and lazy (not any))
      (list (pool:hexsquare sides) nil)
      (pool:fithexr sides diags lazy stol xtol)))

(defun pool:fithexr (sides diags lazy stol xtol / guess p1 e1 p2 e2)
  (setq guess (pool:hexguess sides lazy)
        p1 (pool:relaxn guess
                        (append (pool:hexdiagcon diags 0.4)
                                (pool:hexsidecon sides 0.0 1.0))
                        3000))
  ;; polish: a sides-only pass so the sides land exactly true
  (setq p1 (pool:relaxn p1 (pool:hexsidecon sides 0.0 1.0) 400)
        e1 (pool:hexerr p1 sides diags))
  (if (<= (cadr e1) xtol)
      (list p1 nil)
      (progn
        (setq p2 (pool:relaxn p1
                              (append (pool:hexdiagcon diags 0.5)
                                      (pool:hexsidecon sides stol 1.0))
                              3000)
              e2 (pool:hexerr p2 sides diags))
        (if (and (<= (car e2) (+ stol 0.05)) (<= (cadr e2) (+ xtol 0.05)))
            (list p2 nil)
            (list p1 t)))))

;; Point-in-polygon (ray casting) -- the L is not convex, so side
;; dimensions find "outward" by testing against the actual shape.
(defun pool:inpoly (p poly / n i j xi yi xj yj in x y)
  (setq x (car p) y (cadr p)
        n (length poly)
        i 0 j (1- n) in nil)
  (while (< i n)
    (setq xi (car (nth i poly)) yi (cadr (nth i poly))
          xj (car (nth j poly)) yj (cadr (nth j poly)))
    (if (and (or (and (> yi y) (<= yj y))
                 (and (> yj y) (<= yi y)))
             (< x (+ xi (* (- xj xi) (/ (- y yi) (- yj yi))))))
        (setq in (not in)))
    (setq j i i (1+ i)))
  in)

;; Midpoint of p->q offset by dist to the side that lies OUTSIDE poly.
(defun pool:outoffp (p q poly dist / m n)
  (setq m (cal:mid p q)
        n (pool:unit (cal:perp (cal:v- q p))))
  (if (pool:inpoly (cal:v+ m (cal:v* n 1.0)) poly)
      (setq n (cal:v* n -1.0)))
  (cal:v+ m (cal:v* n dist)))

;; Corner-label position: away from the centroid, but flipped when
;; that lands inside the shape (the inner corner of an L).
(defun pool:lbloff (p cen poly dist / dir cand)
  (setq dir (pool:unit (cal:v- p cen))
        cand (cal:v+ p (cal:v* dir dist)))
  (if (pool:inpoly cand poly)
      (cal:v+ p (cal:v* dir (- dist)))
      cand))

;; The L / Lazy L guide is built by hx:geo inside pool:hexflow (a
;; live-guide geometry function fed to pool:pvlive): the nominal body
;; reshapes through pool:hexguess as the six sides come in.  hx:geo
;; keeps the flow's hxg on the live ring, which is what the cross
;; diagonals below are drawn against.

;; Add the nine (eight on a lazy L) cross diagonals to the L guide once
;; the side lengths are in, on the live guide ring pts.  Returns the
;; extended highlight assoc.
(defun pool:hexcross (lazy pv pts / keys k ent)
  (setq keys (list 'ac 'bd 'ce 'df 'ae 'bf 'ad 'be 'cf)
        k 0)
  (foreach pr pool:*hexdiags*
    ;; the lazy L omits the B-E joint diagonal (per the reference)
    (if (not (and lazy (equal pr (list 1 4))))
        (setq ent (pool:pvadd (pool:pvlined (nth (car pr) pts)
                                            (nth (cadr pr) pts)))
              pv (cons (cons (nth k keys) (list ent)) pv)))
    (setq k (1+ k)))
  pv)

;; Full guided flow for L / Lazy L pools: preview, prompts, fit, draw,
;; dimension and report.  Caller handles sysvars / undo / zoom-extents.
(defun pool:hexflow (lazy / oldclay pv sides diags res pts failed notes ans hxr
                            cen p pr k w hh xmin xmax ymax ymin doff th
                            odim rows lbls dv mquad sq4 elast hxg
                            octy ocsz icty icsz oc ic hcs hce hcarcs ock
                            rbox mprims mlbls soff)
  (setq oldclay (getvar "CLAYER"))
  ;; The live guide geometry (see "live guide reshaping"): each side
  ;; answered so far is held, every side still open takes its nominal
  ;; length scaled by how the answered ones compare to theirs, and
  ;; pool:hexguess folds the six into the L.  hxg keeps the live ring
  ;; for the cross diagonals to hang on.
  (defun hx:geo ( / nom keys ratio n k s pr sd cen sc spec km p)
    (setq nom (if lazy
                  (list (list 0.0 0.0) (list 296.0 0.0) (list 414.0 119.0)
                        (list 296.0 238.0) (list 226.0 168.0)
                        (list 0.0 168.0))
                  (list (list 0.0 0.0) (list 360.0 0.0) (list 360.0 315.0)
                        (list 225.0 315.0) (list 225.0 180.0)
                        (list 0.0 180.0)))
          keys (list 'ab 'bc 'cd 'de 'ef 'fa)
          ratio 0.0 n 0 k 0 sd nil)
    (foreach pr pool:*hexsides*
      (setq s (pool:pvdim (nth k keys)))
      (if s
          (setq ratio (+ ratio (/ s (distance (nth (car pr) nom)
                                              (nth (cadr pr) nom))))
                n (1+ n)))
      (setq k (1+ k)))
    (setq ratio (if (> n 0) (/ ratio n) 1.0)
          k 0)
    (foreach pr pool:*hexsides*
      (setq s (pool:pvdim (nth k keys))
            sd (cons (if s s (* ratio (distance (nth (car pr) nom)
                                                (nth (cadr pr) nom))))
                     sd)
            k (1+ k)))
    (setq hxg (pool:hexguess (reverse sd) lazy)
          cen (list 0.0 0.0))
    (foreach p hxg (setq cen (cal:v+ cen p)))
    (setq cen (cal:v* cen (/ 1.0 6.0))
          sc (/ (max (- (apply 'max (mapcar 'car hxg))
                        (apply 'min (mapcar 'car hxg)))
                     (- (apply 'max (mapcar 'cadr hxg))
                        (apply 'min (mapcar 'cadr hxg))))
                380.0)
          spec nil km nil k 0)
    (foreach pr pool:*hexsides*
      (setq spec (append spec (list (list "LINE" (nth (car pr) hxg)
                                          (nth (cadr pr) hxg))))
            km (cons (list (nth k keys) k) km)
            k (1+ k)))
    (foreach p hxg
      (setq spec (append spec
                         (list (list "TEXT"
                                     (pool:lbloff p cen hxg (* 20.0 sc))
                                     (* 12.0 sc)
                                     (nth (- k 6) (list "A" "B" "C" "D"
                                                        "E" "F")))))
            km (cons (list (pool:lblkey (nth (- k 6) (list "A" "B" "C" "D"
                                                           "E" "F")))
                           k)
                     km)
            k (1+ k)))
    (list spec km (pool:pvspecbox spec)))
  (setq pv (pool:pvlive 'hx:geo))
  (princ "\nA gray guide pool is shown -- the RED element is the dimension being asked for.")
  (princ "\nCorners: A bottom-left, B bottom-right, C right end top, D inner corner, E wing corner, F top-left.")
  (princ "\n(Back re-asks the previous question, right back to the start)")
  (defun hx:sides ( / ans)
  (setq ans (pool:askseqb
              (mapcar '(lambda (q)
                         (list (car q) 'REQ (cadr q)
                               (append (cdr (assoc (caddr q) pv))
                                       (pool:lbl pv (cadddr q)))))
                      (if lazy
                          (list (list 'ab "Main side A-B (bottom)" 'ab '(lA lB))
                                (list 'bc "Lower bend side B-C (45 deg)" 'bc '(lB lC))
                                (list 'cd "Far end C-D" 'cd '(lC lD))
                                (list 'de "Upper bend side D-E (45 deg)" 'de '(lD lE))
                                (list 'ef "Top side E-F" 'ef '(lE lF))
                                (list 'fa "Left end F-A" 'fa '(lF lA)))
                          (list (list 'ab "Side A-B (bottom, full length)" 'ab '(lA lB))
                                (list 'bc "End B-C (right end, full height)" 'bc '(lB lC))
                                (list 'cd "Side C-D (top of wing)" 'cd '(lC lD))
                                (list 'de "Step D-E (down to the inner corner)" 'de '(lD lE))
                                (list 'ef "Side E-F (top of main section)" 'ef '(lE lF))
                                (list 'fa "End F-A (left end)" 'fa '(lF lA)))))
              nil)
        sides (mapcar '(lambda (k) (pool:sq ans k)) '(ab bc cd de ef fa)))
    nil)
  ;; cross dims only when out-of-square; in-square squares up to sides.
  ;; The diagonals join the guide now that the sides are all in, on the
  ;; live ring the guide has reshaped itself to.
  (defun hx:diags ( / ans)
  (if (not pool:*insq*) (setq pv (pool:hexcross lazy pv hxg)))
  (setq diags
        (if pool:*insq*
            (list nil nil nil nil nil nil nil nil nil)
            (progn
              (setq ans (pool:askseqb
                          (mapcar '(lambda (q)
                                     (list (car q) 'NAX
                                           (strcat "Cross dim " (cadr q))
                                           (append (cdr (assoc (car q) pv))
                                                   (pool:lbl pv (caddr q)))))
                                  (append
                                    (list (list 'ac "A-C" '(lA lC))
                                          (list 'bd "B-D" '(lB lD))
                                          (list 'ce "C-E" '(lC lE))
                                          (list 'df "D-F" '(lD lF))
                                          (list 'ae "A-E" '(lA lE))
                                          (list 'bf "B-F" '(lB lF))
                                          (list 'ad "A-D" '(lA lD)))
                                    ;; the lazy L's bend joint is not taped
                                    (if lazy nil (list (list 'be "B-E" '(lB lE))))
                                    (list (list 'cf "C-F" '(lC lF)))))
                          t))
              (if (eq ans 'CAL-BACK)
                  'CAL-BACK
                  (list (pool:sq ans 'ac) (pool:sq ans 'bd) (pool:sq ans 'ce)
                        (pool:sq ans 'df) (pool:sq ans 'ae) (pool:sq ans 'bf)
                        (pool:sq ans 'ad) (if lazy nil (pool:sq ans 'be))
                        (pool:sq ans 'cf))))))
  (if (eq diags 'CAL-BACK) 'CAL-BACK nil))

  ;; corner treatments, like the rectangle: the five OUTER corners
  ;; take one answer; the INNER corner (E) is typically different, so
  ;; it is asked separately (Enter reuses the outer answer).
  ;;
  ;; The body is FIT first, at the top of this stage rather than after
  ;; the questions, because a treatment's setback depends on the real
  ;; corner angle and on an L those are never all 90 degrees -- a lazy
  ;; L bends 135 at B and E even in-square, and out-of-square every
  ;; corner drifts.  Fitting here (not as its own stage) keeps Back
  ;; working: an extra always-succeeding stage would swallow the Back
  ;; out of the corner question by falling straight forward again.
  ;; Re-entering after a Back re-fits, which is what changing a side
  ;; or a diagonal should do.
  (defun hx:corners ( / v k oang mins de ef icap)
    (princ "\nFitting pool body to the measurements ...")
    (setq res (pool:fithex sides diags lazy pool:*side-tol* pool:*cross-tol*)
          pts (car res)
          failed (cadr res)
          octy "Square" ocsz 0.0 icty "Square" icsz 0.0)
    (setq v (pool:askynf 'crec
                         "Anything to record about the corners (radius / cut / not given)?"
                         "No" t))
    (cond
      ((eq v 'CAL-BACK) 'CAL-BACK)
      ((not v) nil)
      (t
       ;; one answer covers the five OUTER corners (0 1 2 3 5), so it
       ;; has to hold for the SHARPEST of them -- that is the one whose
       ;; cut reaches furthest along its walls.  Budget: half the
       ;; shortest fitted wall, which with the sharpest angle on both
       ;; ends of every wall can never overrun any of them.
       (setq oang (pool:polywedge pts 0) mins nil)
       (foreach k '(1 2 3 5)
         (setq oang (min oang (pool:polywedge pts k))))
       (foreach k pool:*hexsides*
         (setq de (distance (nth (car k) pts) (nth (cadr k) pts))
               mins (if mins (min mins de) de)))
       (setq oc (pool:askcorner "the outer corners" nil nil nil
                                (* 0.5 mins) oang t))
       (if (eq oc 'CAL-BACK)
           'CAL-BACK
           (progn
             (setq octy (car oc) ocsz (cadr oc))
             ;; E is capped by what the outer cuts actually LEFT on its
             ;; two walls, at each of those corners' own angles
             (setq de (- (distance (nth 3 pts) (nth 4 pts))
                         (* ocsz (pool:cornerk octy (pool:polywedge pts 3))))
                   ef (- (distance (nth 4 pts) (nth 5 pts))
                         (* ocsz (pool:cornerk octy (pool:polywedge pts 5))))
                   icap (max 0.0 (min de ef))
                   ic (pool:askcorner "the inner corner E" octy ocsz nil
                                      icap (pool:polywedge pts 4) t))
             (if (eq ic 'CAL-BACK)
                 'CAL-BACK
                 (progn (setq icty (car ic) icsz (cadr ic)) nil)))))))

  (pool:stages (list 'hx:sides 'hx:diags 'hx:corners))
  (pool:pvkill)

  ;; pts / res / failed were fit at the top of hx:corners, so the
  ;; corner questions could be sized against the real corner angles.
  ;;
  ;; soff = every side the fit could not build to the tape.  The
  ;; in-square lazy L pushes closure error into the wing ON PURPOSE
  ;; (pool:hexsquare), so a small delta there is the design working --
  ;; but six measurements that miss each other by more than
  ;; pool:*side-tol* are a bad tape, not a fit, and saying so is the
  ;; whole point of the report.  Those sides are drawn with a red
  ;; dimension, listed red in the table, and called out underneath.
  ;; The trip point carries pool:fithexr's own 0.05 slack, so a side
  ;; the out-of-square fit legitimately flexed to the edge of its
  ;; +/-side-tol band is not reported as a bad measurement.
  (setq soff nil k 0)
  (foreach pr pool:*hexsides*
    (if (> (abs (- (distance (nth (car pr) pts) (nth (cadr pr) pts))
                   (nth k sides)))
           (+ pool:*side-tol* 0.05))
        (setq soff (cons k soff)))
    (setq k (1+ k)))
  (setq soff (reverse soff))
  (if soff
      (pool:valnote
        (strcat "SIDES DO NOT CLOSE - "
                (pool:fixnames soff pool:*hexsidenames*)
                " OFF THE TAPE, RE-MEASURE")))
  (setq notes nil
        xmin (apply 'min (mapcar 'car pts))
        xmax (apply 'max (mapcar 'car pts))
        ymin (apply 'min (mapcar 'cadr pts))
        ymax (apply 'max (mapcar 'cadr pts))
        w (- xmax xmin)
        hh (- ymax ymin)
        doff (max 12.0 (/ (max w hh) 18.0))
        th (max 3.0 (/ (max w hh) 70.0))
        pool:*dashlt* (pool:ltload "DASHED")
        cen (list 0.0 0.0))
  (foreach p pts (setq cen (cal:v+ cen p)))
  (setq cen (cal:v* cen (/ 1.0 6.0)))

  ;; perimeter (layer POOL) -- mark the drawing so the whole pool can
  ;; be mirrored later if the user asks.  Corner treatments cut in
  ;; exactly like the rectangle's: sides run between the treatment
  ;; ends, an arc or chamfer face closes each corner (square corners
  ;; degenerate to the plain corner-to-corner sides).  E (index 4) is
  ;; the inner corner and carries its own treatment; the wedge math in
  ;; pool:cornerends handles the reflex angle as-is.
  (setq elast (entlast))
  (setq hcs (list (list octy ocsz) (list octy ocsz) (list octy ocsz)
                  (list octy ocsz) (list icty icsz) (list octy ocsz))
        hce (mapcar '(lambda (k)
                       (pool:cornerends (nth k pts)
                                        (nth (rem (+ k 5) 6) pts)
                                        (nth (rem (+ k 1) 6) pts)
                                        (car (nth k hcs)) (cadr (nth k hcs))
                                        nil))
                    (list 0 1 2 3 4 5)))
  (foreach pr pool:*hexsides*            ; side i: eNext(i) -> ePrev(i+1)
    (pool:line (cadr (nth (car pr) hce)) (car (nth (cadr pr) hce)) "POOL"))
  (setq hcarcs nil k 0)
  (foreach p hcs
    (cond
      ((= (car p) "Cut")
       (pool:line (car (nth k hce)) (cadr (nth k hce)) "POOL")
       (setq hcarcs (cons nil hcarcs)))
      ((= (car p) "Radius")
       (pool:arc3p (car (nth k hce)) (caddr (nth k hce)) (cadr (nth k hce))
                   "POOL")
       (setq hcarcs (cons (entlast) hcarcs)))
      (t (setq hcarcs (cons nil hcarcs))))
    (setq k (1+ k)))
  (setq hcarcs (reverse hcarcs))

  ;; dimensions (layer DIMENSION) -- side dims read to the TRUE
  ;; corners, same convention as the rectangle.  Per the reference
  ;; sheet, the wing/step detail sides read in SIDE STANDARD while the
  ;; principal walls (main run, far end, deep end) stay standard:
  ;; true L -> C-D, D-E, E-F secondary; lazy L -> the bends B-C, D-E
  ;; and the top E-F.
  (setvar "CLAYER" "DIMENSION")
  (setq k 0)
  (foreach pr pool:*hexsides*
    (if (member k (if lazy '(1 3 4) '(2 3 4)))
        (pool:dimalgs (nth (car pr) pts) (nth (cadr pr) pts)
                      (pool:outoffp (nth (car pr) pts) (nth (cadr pr) pts)
                                    pts doff))
        (pool:dimalg (nth (car pr) pts) (nth (cadr pr) pts)
                     (pool:outoffp (nth (car pr) pts) (nth (cadr pr) pts)
                                   pts doff)))
    ;; a side the tape could not close reads its BUILT length, so the
    ;; dimension goes red like any other measurement the validator had
    ;; to move
    (if (member k soff) (pool:dimred))
    (setq k (1+ k)))
  ;; corner annotations: one Typ. callout on an outer corner (B), the
  ;; inner corner E dimensioned on its own.  B carries its own fitted
  ;; angle, so a true L's square corners are marked 90 and a lazy L's
  ;; 135-degree bend is not.  E passes nil: it is the REFLEX corner,
  ;; and pool:wedge is unsigned -- 270 degrees measures back as 90, so
  ;; the mark has to be forbidden outright rather than angle-tested.
  ;; one answer covers five outer corners, so the single Typ. mark has
  ;; to sit on one that can actually carry it: B is the convention, but
  ;; a lazy L bends B 135 degrees, and marking it 90 would be a lie --
  ;; so fall through to whichever outer corner is genuinely square
  (setq ock 1)
  (if (> (abs (- (pool:polywedge pts 1) (/ pi 2.0))) pool:*sq90-tol*)
      (foreach k '(0 2 3 5)
        (if (and (= ock 1)
                 (<= (abs (- (pool:polywedge pts k) (/ pi 2.0)))
                     pool:*sq90-tol*))
            (setq ock k))))
  (pool:dimtreat1 (nth ock hce) octy (nth ock hcarcs) (nth ock pts)
                  (pool:unit (cal:v- (nth ock pts) cen)) doff " Typ."
                  (pool:polywedge pts ock))
  (pool:dimtreat1 (nth 4 hce) icty (nth 4 hcarcs) (nth 4 pts)
                  (pool:unit
                    (cal:v+ (pool:unit (cal:v- (nth 3 pts) (nth 4 pts)))
                             (pool:unit (cal:v- (nth 5 pts) (nth 4 pts)))))
                  doff "" nil)
  ;; provided cross dims, in the CROSS DIMENSIONS style when available
  (setq odim (pool:dimxbegin) k 0)
  (foreach pr pool:*hexdiags*
    (if (nth k diags)
        (pool:dimalg (nth (car pr) pts) (nth (cadr pr) pts)
                     (cal:v+ (cal:mid (nth (car pr) pts) (nth (cadr pr) pts))
                              (cal:v* (pool:unit
                                         (cal:perp
                                           (cal:v- (nth (cadr pr) pts)
                                                    (nth (car pr) pts))))
                                       (* (if (= 0 (rem k 2)) 0.15 -0.15)
                                          doff)))))
    (setq k (1+ k)))
  (pool:dimxend odim)
  (setvar "CLAYER" oldclay)

  ;; corner letters live on the mini-model beside the report, not in
  ;; the corners of the drawing itself -- see the pool:minimap call
  (setq lbls (list "A" "B" "C" "D" "E" "F"))

  ;; report table
  (setq rows nil k 0)
  (foreach pr pool:*hexsides*
    (setq rows (cons (pool:vrow (strcat "SIDE " (nth k pool:*hexsidenames*))
                                (nth k sides)
                                (distance (nth (car pr) pts)
                                          (nth (cadr pr) pts))
                                k soff)
                     rows)
          k (1+ k)))
  (if (not pool:*insq*)
      (progn
        (setq k 0)
        (foreach pr pool:*hexdiags*
          (setq rows (cons (list (strcat "CROSS " (nth k pool:*hexdiagnames*))
                                 (nth k diags)
                                 (distance (nth (car pr) pts) (nth (cadr pr) pts)))
                           rows)
                k (1+ k)))))
  (setq rows (reverse rows))
  (setq rows (append rows
                     (pool:cornerrows (list "OUTER CORNER" "INNER CORNER")
                                      (list (list octy ocsz) (list icty icsz)))))

  ;; -------- standard hopper in the main section (no sport for L).
  ;; dv = the virtual main-section corner where the break line (down
  ;; from inner corner E) meets the main-run line A-B; the hopper
  ;; anchors off the main rectangle A-dv-E-F and its left corners tie
  ;; to A and F.  A and F are REAL pool corners, so when the outer
  ;; corner treatment cuts them, the ties must land on the ends of
  ;; that cut -- exactly like the rectangle's hopper -- not on the
  ;; sharp corner behind it.  dv and E are not real treated walls in
  ;; this virtual frame (dv has no corner at all; E's real treatment
  ;; is sized for the true reflex angle against D, not against dv), so
  ;; they stay plain "Square" the way they always have.
  (if (pool:askbottom)
      (progn
        ;; per the reference: the break line drops from the inner
        ;; corner E to the bottom side, and the hopper lives in the
        ;; main section A - breakBottom - E - F
        (setq dv (pool:linex (nth 4 pts) (cal:v- (nth 5 pts) (nth 0 pts))
                             (nth 0 pts) (cal:v- (nth 1 pts) (nth 0 pts)))
              mquad (list (nth 0 pts) dv (nth 4 pts) (nth 5 pts))
              sq4 (list (list octy ocsz) (list "Square" 0.0)
                        (list "Square" 0.0) (list octy ocsz)))
        (command "_.ZOOM" "_Window"
                 (pool:wp (list (- (apply 'min (mapcar 'car mquad)) doff)
                                (- (apply 'min (mapcar 'cadr mquad)) doff)))
                 (pool:wp (list (+ (apply 'max (mapcar 'car mquad)) doff)
                                (+ (apply 'max (mapcar 'cadr mquad)) doff))))
        ;; L pools take the standard hopper only
        (setq rows (append rows
                           (pool:hopnormal mquad sq4 doff th t "Normal"
                                           (apply 'min (mapcar 'car pts))
                                           (- (apply 'min (mapcar 'cadr pts))
                                              (* 2.2 doff))
                                           t)))))

  ;; -------- all dimensions are in: offer to mirror the pool.
  ;; Top-to-bottom, so the wing swaps sides but the deep end (and its
  ;; hopper) stays on the left -- see pool:mirrory.
  (if (pool:askynf 'mirror
                   "Mirror the pool (flips the wing; deep end stays left)"
                   "No" nil)
      (progn
        (pool:mirrory elast (cadr (pool:wp (list 0.0 (* 0.5 (+ ymin ymax))))))
        ;; the mini-model must show the pool as BUILT, so its points
        ;; flip with the plan
        (setq pts (mapcar '(lambda (p) (list (car p)
                                             (- (+ ymin ymax) (cadr p))))
                          pts))
        (princ "\nPool mirrored -- the wing swapped sides, deep end still on the left.")))

  (if failed (setq notes (cons "CROSS DIMS FAILED" notes)))
  (setq notes (append notes pool:*valnotes*))
  (setq rbox (pool:report rows notes (+ xmax (* 2.0 doff)) ymax th "POOL-NOTES"))
  ;; perimeter mini-model with the corner letters, right of the report
  (setq mprims nil k 0)
  (foreach pr pool:*hexsides*
    (setq mprims (cons (list 'l (nth (car pr) pts) (nth (cadr pr) pts)) mprims)))
  (setq mlbls nil)
  (foreach p pts
    (setq mlbls (append mlbls (list (cons p (nth (length mlbls) lbls))))))
  (pool:minimap mprims pts mlbls (+ (car rbox) (* 3.0 th)) (cadr rbox)
                (* 24.0 th) th)
  (cond
    (failed
     (princ "\n*** CROSS DIMS FAILED -- sides held true, see report table ***"))
    (soff
     (princ (strcat "\n*** SIDES DO NOT CLOSE -- deep end held true, the wing"
                    " carries the error, see report table ***")))
    (t (princ "\nPool layout complete -- see the report table.")))
  (princ))

;;; -------------------- report table -----------------------------------

;; Report cell: red when the row is flagged.
(defun pool:rtext (pt h str lay red)
  (if red (pool:textc pt h str lay 1) (pool:text pt h str lay)))

;; rows  = list of (label target actual [red])
;; notes = list of failure strings (written big and red)
;; TARGET / ACTUAL lengths in the crew's own units: feet-inches when
;; the drawing was in architectural or engineering units before POOL
;; switched to architectural for its prompts, plain inches otherwise.
;; (getdist keeps only the value, never the text typed, so the
;; drawing's own units are the crew's declared preference.)
(defun pool:fmtlen (v)
  (if pool:*ftin* (rtos v 4 4) (rtos v 2 2)))

;; DELTA is always plain signed inches -- a delta is a small number
;; and reads best that way whichever units the lengths are in.
(defun pool:fmtdelta (dl)
  (strcat (if (< dl 0.0) "" "+") (rtos dl 2 2)))

;; Returns the table's box as (xr ytop y0) so the caller can hang the
;; perimeter mini-model off its right edge (pool:minimap).
(defun pool:report (rows notes x y h lay / lh ytop y0 xr r tgt act c2 c3 n)
  ;; feet-inch strings run longer than decimal inches, so the TARGET/
  ;; ACTUAL/DELTA columns spread out when the report is in feet-inches
  (setq lh (* 2.2 h)
        ytop (+ y lh)
        c2 (if pool:*ftin* 33.0 29.0)
        c3 (if pool:*ftin* 46.0 38.0)
        xr (+ x (* (if pool:*ftin* 54.0 46.0) h))
        y ytop)
  (setq y (- y lh))
  (pool:text (list x y) (* 1.25 h) "POOL LAYOUT REPORT" lay)
  (setq y (- y lh))
  (pool:text (list x y) h "MEASUREMENT" lay)
  (pool:text (list (+ x (* 20.0 h)) y) h "TARGET" lay)
  (pool:text (list (+ x (* c2 h)) y) h "ACTUAL" lay)
  (pool:text (list (+ x (* c3 h)) y) h "DELTA" lay)
  ;; a 4th row element flags the row RED: the validator adjusted it
  (foreach r rows
    (setq y (- y lh)
          tgt (cadr r)
          act (caddr r))
    (pool:rtext (list x y) h (car r) lay (nth 3 r))
    (if (and tgt act)
        (progn
          (pool:rtext (list (+ x (* 20.0 h)) y) h (pool:fmtlen tgt) lay (nth 3 r))
          (pool:rtext (list (+ x (* c3 h)) y) h (pool:fmtdelta (- act tgt))
                      lay (nth 3 r)))
        ;; NA target: measurement was not taken in the field.  A row
        ;; may also carry no ACTUAL -- a NotGiven corner records that
        ;; the sheet never said, so there is nothing to compare and
        ;; nothing was built to a size
        (progn
          (pool:rtext (list (+ x (* 20.0 h)) y) h
                      (if tgt (pool:fmtlen tgt) "N/A") lay (nth 3 r))
          (pool:rtext (list (+ x (* c3 h)) y) h "-" lay (nth 3 r))))
    (pool:rtext (list (+ x (* c2 h)) y) h
                (if act (pool:fmtlen act) "N/A") lay (nth 3 r)))
  (foreach n notes
    (setq y (- y (* 1.5 lh)))
    (pool:textc (list x y) (* 1.4 h) n lay 1))
  (setq y0 (- y lh)
        ytop (+ ytop (* 0.6 lh)))
  (pool:line (list (- x h) y0) (list xr y0) lay)
  (pool:line (list xr y0) (list xr ytop) lay)
  (pool:line (list xr ytop) (list (- x h) ytop) lay)
  (pool:line (list (- x h) ytop) (list (- x h) y0) lay)
  (list xr ytop y0))

;; Map a pool-space point into the mini-model's box.  Called only from
;; pool:minimap -- sc / ox / oy / xmin / ymax are ITS locals, seen here
;; through dynamic scope (top-left anchored, y measured downward).
(defun pool:mms (p)
  (list (+ ox (* sc (- (car p) xmin)))
        (- oy (* sc (- ymax (cadr p))))))

;; The perimeter mini-model drawn beside the report: the pool outline
;; at a small fixed size with the corner LETTERS on it.  The letters
;; used to sit in the corners of the full-size drawing; they live here
;; now, so the drawing itself stays clean.
;;   prims  ('l p1 p2) line | ('a p1 pmid p2) arc as three points
;;          (uniform scaling keeps an arc an arc) | ('rb cen b a) a
;;          round/elliptical body
;;   poly   the corner ring, for keeping letters outside the outline
;;          (nil -> plain outward-from-centre offsets)
;;   lbls   ((pt . "A") ...)
;;   x y    top-left anchor (pool-report space); size = fit box
(defun pool:minimap (prims poly lbls x y size th / pts p l xmin xmax ymin ymax
                                                   sc ox oy w hh spoly cen tx
                                                   lth)
  (setq pts nil)
  (foreach p prims
    (if (eq (car p) 'rb)
        (setq pts (cons (cal:v- (cadr p) (list (* 0.5 (caddr p))
                                                (* 0.5 (cadddr p))))
                        (cons (cal:v+ (cadr p) (list (* 0.5 (caddr p))
                                                      (* 0.5 (cadddr p))))
                              pts)))
        (setq pts (append (cdr p) pts))))
  (foreach l lbls (setq pts (cons (car l) pts)))
  (if pts
      (progn
        (setq xmin (apply 'min (mapcar 'car pts))
              xmax (apply 'max (mapcar 'car pts))
              ymin (apply 'min (mapcar 'cadr pts))
              ymax (apply 'max (mapcar 'cadr pts))
              w (max 1.0e-6 (- xmax xmin))
              hh (max 1.0e-6 (- ymax ymin))
              sc (min (/ size w) (/ size hh))
              ox x oy y
              lth (* 1.4 th))
        (foreach p prims
          (cond
            ((eq (car p) 'l)
             (pool:line (pool:mms (cadr p)) (pool:mms (caddr p)) "POOL-NOTES"))
            ((eq (car p) 'a)
             (pool:arc3p (pool:mms (cadr p)) (pool:mms (caddr p))
                         (pool:mms (cadddr p)) "POOL-NOTES"))
            ((eq (car p) 'rb)
             (pool:roundbody (pool:mms (cadr p)) (* sc (caddr p))
                             (* sc (cadddr p)) "POOL-NOTES"))))
        (setq spoly (if poly (mapcar 'pool:mms poly))
              cen (list 0.0 0.0))
        (foreach l lbls (setq cen (cal:v+ cen (pool:mms (car l)))))
        (if lbls (setq cen (cal:v* cen (/ 1.0 (length lbls)))))
        (foreach l lbls
          (setq tx (pool:mms (car l)))
          (pool:text (if spoly
                         (pool:lbloff tx cen spoly (* 1.6 lth))
                         (cal:v+ tx (cal:v* (pool:unit (cal:v- tx cen))
                                              (* 1.6 lth))))
                     lth (cdr l) "POOL-NOTES"))))
  (princ))


;;; -------------------- rectangle corner treatments --------------------
;;;
;;;  A rectangle corner may be Square, Radius, Cut (a chamfer) or
;;;  NotGiven.  Side lengths are always measured to the TRUE (sharp)
;;;  corner; the treatment cuts inward from there.  The size typed is:
;;;    Radius -> the corner RADIUS
;;;    Cut    -> the CUT FACE length (the chamfer itself)
;;;  Square and NotGiven have no size: nothing was cut, and in the
;;;  NotGiven case nothing was measured either.
;;;  In-square pools assume all four corners identical; out-of-square
;;;  pools ask per corner (Enter reuses the previous corner's answer).

;; The two points where a corner's treatment meets the straight sides
;; (toward the previous / next corner) plus, for Radius, the arc mid.
;; Returns (ePrev eNext arcMid|nil).  Square -> (P P nil).
;; ctype "Ends" is the escape hatch for corners that are not a plain
;; treatment of this quad's corner (a Grecian's angled cut, say): size
;; and xtra ARE the two treatment ends, prev-side first.
;; The wedge angle the two walls at p actually make (0..pi), measured
;; from p toward its previous and next corners.  A reflex corner is
;; measured by the wedge its walls make, not the 360-minus angle --
;; which is what the treatment geometry wants either way.
(defun pool:wedge (p pp pn / u v dp)
  (setq u (pool:unit (cal:v- pp p))
        v (pool:unit (cal:v- pn p))
        dp (cal:dot u v))
  (atan (sqrt (max 0.0 (- 1.0 (* dp dp)))) dp))

;; Same, for corner i of a closed polygon.
(defun pool:polywedge (pts i / n)
  (setq n (length pts))
  (pool:wedge (nth i pts)
              (nth (rem (+ i (1- n)) n) pts)
              (nth (rem (+ i 1) n) pts)))

;; The setback budget for a treatment at corner i of a closed polygon:
;; half the shorter of its two walls, so the treatments at the two
;; ends of any wall can never overrun each other and fold it.
(defun pool:polycap (pts i / n)
  (setq n (length pts))
  (* 0.5 (min (distance (nth i pts) (nth (rem (+ i (1- n)) n) pts))
              (distance (nth i pts) (nth (rem (+ i 1) n) pts)))))

;; The tightest budget over a GROUP of corners answered together, and
;; the sharpest angle in it -- the corner whose cut reaches furthest
;; along its walls is the one the single answer has to fit.
;; Returns (cap angle).
(defun pool:groupcap (pts ks / cap ang k)
  (foreach k ks
    (setq cap (if cap (min cap (pool:polycap pts k)) (pool:polycap pts k))
          ang (if ang (min ang (pool:polywedge pts k)) (pool:polywedge pts k))))
  (list cap ang))

;; How far a corner treatment eats along EACH adjacent wall, per unit
;; of entered size, at wedge angle ang:
;;   Radius  radius r -> r / tan(ang/2)
;;   Cut     face   f -> f / (2 sin(ang/2))
;; At 90 degrees these come to 1.0 and 0.70711, which is what the old
;; fixed arithmetic assumed -- but they diverge fast away from square
;; (a 60-degree Radius corner sets back 1.73 x its radius, a
;; 135-degree one only 0.41 x), so anything sizing a treatment against
;; the wall it has to fit on must ask for the real angle.  L and Lazy
;; L pools are the ones that care: their bends are 135 degrees even
;; in-square, and out-of-square every corner drifts off 90.
(defun pool:cornerk (ctype ang / h s)
  (setq h (* 0.5 ang) s (sin h))
  (if (< s 1.0e-9)
      1.0e9                             ; degenerate: treat as unusable
      (cond ((= ctype "Radius") (/ (cos h) s))
            ((= ctype "Cut") (/ 1.0 (* 2.0 s)))
            (t 0.0))))

(defun pool:cornerends (p pp pn ctype size xtra / uprev unext ang sb bis cen)
  (setq uprev (pool:unit (cal:v- pp p))
        unext (pool:unit (cal:v- pn p))
        ang (pool:wedge p pp pn))                          ; interior angle
  (cond
    ((= ctype "Ends") (list size xtra nil))
    ((= ctype "Cut")
     (setq sb (/ size (* 2.0 (sin (/ ang 2.0)))))           ; face -> edge setback
     (list (cal:v+ p (cal:v* uprev sb))
           (cal:v+ p (cal:v* unext sb)) nil))
    ((= ctype "Radius")
     (setq sb (/ (* size (cos (/ ang 2.0))) (sin (/ ang 2.0)))  ; r/tan(ang/2)
           bis (pool:unit (cal:v+ uprev unext))
           cen (cal:v+ p (cal:v* bis (/ size (sin (/ ang 2.0))))))
     (list (cal:v+ p (cal:v* uprev sb))
           (cal:v+ p (cal:v* unext sb))
           (cal:v- cen (cal:v* bis size))))              ; arc point nearest corner
    (t (list p p nil))))

;; A reference point at corner i of quad q for a cross-dim measurement:
;;   spec = 'true (sharp corner) | 'prev | 'next (treatment ends) |
;;          'mid (chamfer/arc middle).
(defun pool:cornerpoint (q corners i spec / ce)
  (setq ce (pool:cornerends (nth i q)
                            (nth (rem (+ i 3) 4) q)
                            (nth (rem (+ i 1) 4) q)
                            (car (nth i corners)) (cadr (nth i corners))
                            (caddr (nth i corners))))
  (cond ((eq spec 'prev) (car ce))
        ((eq spec 'next) (cadr ce))
        ((eq spec 'mid) (if (caddr ce) (caddr ce) (cal:mid (car ce) (cadr ce))))
        (t (nth i q))))

;; Draw the rectangle perimeter with corner treatments on layer POOL.
;; Returns the list of fillet-arc entity names per corner (nil where
;; the corner is square or chamfered) for the corner dimensions.
(defun pool:drawrect (q corners / ce i tyi arcs)
  (setq ce (mapcar '(lambda (i)
                      (pool:cornerends (nth i q)
                                       (nth (rem (+ i 3) 4) q)
                                       (nth (rem (+ i 1) 4) q)
                                       (car (nth i corners)) (cadr (nth i corners))
                                       (caddr (nth i corners))))
                   (list 0 1 2 3)))
  (foreach i (list 0 1 2 3)             ; straight sides (eNext(i) -> ePrev(i+1))
    (pool:line (cadr (nth i ce)) (car (nth (rem (+ i 1) 4) ce)) "POOL"))
  (setq arcs nil)
  (foreach i (list 0 1 2 3)             ; corner treatments
    (setq tyi (car (nth i corners)))
    (cond
      ((= tyi "Cut")
       (pool:line (car (nth i ce)) (cadr (nth i ce)) "POOL")
       (setq arcs (cons nil arcs)))
      ((= tyi "Radius")
       (pool:arc3p (car (nth i ce)) (caddr (nth i ce)) (cadr (nth i ce)) "POOL")
       (setq arcs (cons (entlast) arcs)))
      (t (setq arcs (cons nil arcs)))))
  (reverse arcs))

;; One corner-treatment annotation: a radius dim on a fillet arc or an
;; aligned dim on a cut face, dropped outward along outd, with an
;; optional " Typ." suffix.  Square corners are not this helper's job.
;; The square-corner mark of STANDARDS.md section 2: a small circle on
;; the corner point with a leader out along the corner's outward
;; diagonal.  Ported from spa:dim90 (lisp/spa/SPA.LSP), the reference
;; implementation, so the two tools' sheets match.  txt is what the
;; leader says -- "90%%d" on a square corner, "?" on a NotGiven one,
;; either with a " Typ." suffix when one mark speaks for several.
(defun pool:dim90 (p outd doff txt / r)
  (setq r (* 0.18 doff))
  (entmake (list '(0 . "CIRCLE")
                 (cons 8 "DIMENSION")
                 (cons 10 (pool:wp p))
                 (cons 40 r)))
  (command "_.LEADER" (pool:wp (cal:v+ p (cal:v* outd r)))
           (pool:wp (cal:v+ p (cal:v* outd (* 1.2 doff))))
           "" txt ""))

;; A NotGiven corner: the same circled mark, but the leader asks a
;; question instead of asserting an angle, and a note under it spells
;; the reason out.  The sheet has to SAY the treatment was never
;; recorded -- drawing a bare 90 would claim a measurement nobody took.
(defun pool:dimng (p outd doff sfx / h tp)
  (pool:dim90 p outd doff (strcat "?" sfx))
  ;; the note sits just past the leader tip, and is pulled back by its
  ;; own width when the corner points LEFT -- text runs left-to-right
  ;; from its insertion point, so an unadjusted note on a left-hand
  ;; corner would read back across its own leader and into the pool
  (setq h (* 0.25 doff)
        tp (cal:v+ p (cal:v* outd (* 1.45 doff))))
  (if (< (car outd) 0.0)
      (setq tp (list (- (car tp) (* 9.0 0.6 h)) (cadr tp))))
  (pool:text tp h "Not Given" "DIMENSION"))

;; One corner's annotation, whichever of the four treatments it
;; carries.  ang is the corner's real wedge angle, and it decides
;; whether a plain Square corner may be marked at all:
;;
;;   the "90%%d" mark ASSERTS a right angle, so it is only drawn where
;;   the corner really is one.  A grecian's corners sit at ~135 and an
;;   L's bend at 135, and stamping 90 on those would be a lie -- they
;;   stay unmarked, exactly as before.  Pass ang = nil to forbid the
;;   mark outright, which is what the L's INNER corner needs: it is
;;   reflex, and pool:wedge is unsigned, so a 270-degree corner
;;   measures back as 90 and would otherwise be marked.
;;
;;   "?" asserts nothing about the angle, so a NotGiven corner is
;;   flagged on every shape at every angle, no exceptions.
(defun pool:dimtreat1 (ce ty arc p outd doff sfx ang)
  (cond
    ((pool:cutp ty) (pool:dimcorner1 ce ty arc outd doff sfx))
    ((= ty "NotGiven") (pool:dimng p outd doff sfx))
    ((and ang (< (abs (- ang (/ pi 2.0))) pool:*sq90-tol*))
     (pool:dim90 p outd doff (strcat "90%%d" sfx)))))

(defun pool:dimcorner1 (ce ty arc outd doff sfx / am fm od)
  (cond
    ((= ty "Radius")
     (setq am (caddr ce)
           od (pool:dimsbegin (if (and arc (entget arc))
                                  (cdr (assoc 40 (entget arc)))
                                  (distance (car ce) (cadr ce)))))
     (if (= sfx "")
         (command "_.DIMRADIUS" (list arc (pool:wp am))
                  (pool:wp (cal:v+ am (cal:v* outd (* 0.9 doff)))))
         (command "_.DIMRADIUS" (list arc (pool:wp am))
                  "_T" (strcat "<>" sfx)
                  (pool:wp (cal:v+ am (cal:v* outd (* 0.9 doff))))))
     (pool:dimsend od))
    ((= ty "Cut")
     (setq fm (cal:mid (car ce) (cadr ce))
           od (pool:dimsbegin (distance (car ce) (cadr ce))))
     (if (= sfx "")
         (command "_.DIMALIGNED" (pool:wp (car ce)) (pool:wp (cadr ce))
                  (pool:wp (cal:v+ fm (cal:v* outd (* 0.5 doff)))))
         (command "_.DIMALIGNED" (pool:wp (car ce)) (pool:wp (cadr ce))
                  "_T" (strcat "<>" sfx)
                  (pool:wp (cal:v+ fm (cal:v* outd (* 0.5 doff))))))
     (pool:dimsend od))))

;; Corner annotations for the rectangle.  In-square pools get a single
;; "Typ." note at the bottom-right corner (B): the radius or cut-face
;; measurement with a Typ. suffix, or the circled 90 mark for square
;; corners.  Out-of-square pools dim every corner individually --
;; radius dim, cut-face dim, or its own circled mark.  Assumes CLAYER
;; is already DIMENSION.
(defun pool:dimcorners (quad corners arcs cen doff / ilist sfx i cc ce p pp pn
                                                    ty outd same)
  ;; out-of-square, the corners are asked one at a time -- but when
  ;; every answer came back the SAME treatment at the SAME size (Enter
  ;; reusing the previous corner, typically), one "Typ." callout reads
  ;; cleaner than four identical dims, exactly like in-square
  (setq same t)
  (foreach cc (cdr corners)
    (if (not (and (equal (car cc) (car (car corners)))
                  (equal (cadr cc) (cadr (car corners)) 1.0e-6)))
        (setq same nil)))
  (if (or pool:*insq* same)
      (setq ilist (list 1) sfx " Typ.")
      (setq ilist (list 0 1 2 3) sfx ""))
  (foreach i ilist
    (setq p (nth i quad)
          pp (nth (rem (+ i 3) 4) quad)
          pn (nth (rem (+ i 1) 4) quad)
          cc (nth i corners)
          ty (car cc)
          ce (pool:cornerends p pp pn ty (cadr cc) (caddr cc))
          outd (pool:unit (cal:v- p cen)))
    ;; a rectangle's corners are square by definition -- out of square
    ;; they drift a fraction of a degree -- so the 90 mark is earned
    ;; here and pool:dimtreat1 draws it
    (pool:dimtreat1 ce ty (nth i arcs) p outd doff sfx
                    (pool:wedge p pp pn))))

;; Corner-treatment annotations for a ring with more corners than the
;; rectangle's four.  groups = the index groups that were answered
;; TOGETHER, each ordered reference-corner first (a grecian's body
;; family and tip family in square; eight singletons out of square).
;; Whether a plain Square corner earns the circled 90 mark is decided
;; per corner from its own fitted angle inside pool:dimtreat1, so a
;; roman's true 90s are marked while a grecian's 135s are not; a
;; NotGiven corner is flagged on any shape at any angle.
;;   every corner in the ring identical -> one Typ. on the first
;;                                         group's reference corner
;;   else, per group all-same           -> one Typ. on its reference
;;   else (members differ)              -> each corner its own mark
(defun pool:dimringcorners (pts corners ces arcs cen doff groups
                            / allsame ord g i cc same ref)
  (setq ord (apply 'append groups)
        allsame t)
  (foreach i (cdr ord)
    (if (not (and (equal (car (nth i corners)) (car (nth (car ord) corners)))
                  (equal (cadr (nth i corners)) (cadr (nth (car ord) corners))
                         1.0e-6)))
        (setq allsame nil)))
  (foreach g (if allsame (list ord) groups)
    (setq same t ref (car g))
    (foreach i (cdr g)
      (if (not (and (equal (car (nth i corners)) (car (nth ref corners)))
                    (equal (cadr (nth i corners)) (cadr (nth ref corners))
                           1.0e-6)))
          (setq same nil)))
    (foreach i (if same (list ref) g)
      (setq cc (nth i corners))
      (pool:dimtreat1 (nth i ces) (car cc) (nth i arcs) (nth i pts)
                      (pool:unit (cal:v- (nth i pts) cen)) doff
                      (if (and same (> (length g) 1)) " Typ." "")
                      (pool:polywedge pts i)))))

;; Re-draw the guide rectangle's corners with the chosen treatments so
;; the visual matches what will be built.  gq = the guide quad,
;; corners = per-corner (type size), sizes already clamped for display.
;; The four full-length guide sides are replaced by shortened sides
;; plus gray chamfer lines / fillet arcs; the pv assoc side keys are
;; re-pointed at the new side entities.  Returns the updated pv.
(defun pool:pvcorners (pv gq corners / ce i k cc ent)
  (foreach k (list 'ab 'bc 'dc 'da)
    (pool:pvdel (cdr (assoc k pv))))
  (setq ce (mapcar '(lambda (i)
                      (pool:cornerends (nth i gq)
                                       (nth (rem (+ i 3) 4) gq)
                                       (nth (rem (+ i 1) 4) gq)
                                       (car (nth i corners)) (cadr (nth i corners))
                                       (caddr (nth i corners))))
                   (list 0 1 2 3)))
  ;; shortened straight sides (side i runs corner i -> corner i+1)
  (setq i 0)
  (foreach k (list 'ab 'bc 'dc 'da)
    (setq ent (pool:pvadd (pool:pvline (cadr (nth i ce))
                                       (car (nth (rem (+ i 1) 4) ce))))
          pv (subst (cons k (list ent)) (assoc k pv) pv)
          i (1+ i)))
  ;; the corner treatments themselves
  (setq i 0)
  (foreach cc corners
    (cond
      ((= (car cc) "Cut")
       (pool:pvadd (pool:pvline (car (nth i ce)) (cadr (nth i ce)))))
      ((= (car cc) "Radius")
       (pool:arc3p (car (nth i ce)) (caddr (nth i ce)) (cadr (nth i ce))
                   "POOL-NOTES")
       (pool:pvadd (pool:setcol (entlast) pool:*pv-col*))))
    (setq i (1+ i)))
  pv)

;; Prompt one corner's treatment (Enter reuses prevty/prevsz).
;; maxsb caps the treatment's setback along the walls at half the
;; shorter adjacent wall, so two treatments can never overlap and fold
;; the perimeter; too-large answers are re-asked.
;; ang = the wedge angle to size this answer against (the SHARPEST of
;; them when one answer covers several corners, since that is the one
;; that eats furthest into its walls).  nil means "assume square",
;; which is right for the rectangle: it asks its corners before the
;; cross dims, so its true angles are not known yet -- and a pool
;; still called a rectangle is within a degree of 90 anyway.
(defun pool:askcorner (subject prevty prevsz ents maxsb ang back
                       / ty sz cols sb wed dflt szmsg nofit fk fty fsz)
  ;; A form can answer this corner: <stem>-ty carries the treatment,
  ;; <stem>-sz the radius or cut face.  Both are consumed NOW, valid or
  ;; not -- consume-once is what keeps Back from deadlocking, and what
  ;; lets a rejected size be retyped at the keyboard instead of re-fed.
  ;; An answer the question would not accept falls through to the
  ;; prompt exactly as if the box had been left empty.
  (if (setq fk (pool:fckey subject))
      (progn
        (if (pool:fhas (read (strcat fk "-ty")))
            (progn
              (setq fty (pool:ftake (read (strcat fk "-ty"))))
              (if (not (member fty '("Square" "Radius" "Cut" "NotGiven")))
                  (setq fty nil))))
        (if (pool:fhas (read (strcat fk "-sz")))
            (progn
              (setq fsz (pool:ftake (read (strcat fk "-sz"))))
              (if (not (and (numberp fsz) (> fsz 0.0)))
                  (setq fsz nil))))))
  ;; A corner whose walls leave no room for a cut cannot be given one:
  ;; every size would be rejected and re-asked forever.  That is a fact
  ;; about the GEOMETRY, though, and it must not answer the question
  ;; the sheet asks -- "nobody wrote this corner down" is still a
  ;; truthful answer here.  So the two sized options are withheld and
  ;; the question is still put.
  (if (and maxsb (< maxsb 0.125))
      (progn
        (princ (strcat "\nNo room for a cut on " subject
                       " -- Radius and Cut are not offered."))
        (setq maxsb nil nofit t)
        ;; the geometry outranks the form: a sized treatment cannot fit
        ;; here whoever supplied it, so the question is put after all
        (if (pool:cutp fty) (setq fty nil))))
  (progn
  (setq cols (mapcar 'pool:getcol ents))
  (foreach e ents (pool:setcol e pool:*hi-col*))
  (cal:osup)
  (setq ty (cond
             (fty fty)
             (nofit
              ;; a remembered Radius/Cut is not among the offered
              ;; words, and pool:askkw hands a default straight back
              ;; on Enter without checking it -- so drop it
              (pool:asktreatng subject
                               (if (member prevty '("Square" "NotGiven"))
                                   prevty nil)
                               back))
             (t (cal:asktreat subject prevty back))))
  (cal:osdown)
  (if (eq ty 'CAL-BACK)
      (progn (mapcar '(lambda (e c) (pool:setcol e c)) ents cols)
             (setq ty nil)))
  (if (null ty)
      (progn (mapcar '(lambda (e c) (pool:setcol e c)) ents cols)
             (setq sz nil)))
  (if (null ty)
      nil
  ;; Square has no size, and NotGiven has none either -- nothing was
  ;; measured, so there is no number to ask for
  (if (not (pool:cutp ty))
      (setq sz 0.0)
      (progn
        ;; the remembered size is only offered back when the answer
        ;; MATCHES the one it was measured for: a radius is not a cut
        ;; face, so carrying 24" across from one to the other would be
        ;; a wrong default, not a convenient one
        (setq dflt (if (and prevsz (> prevsz 0.0) (= ty prevty)) prevsz nil)
              szmsg (strcat "\n" (if (= ty "Radius") "Radius for "
                                     "Cut face length for ")
                            subject))
        (cal:osup)
        (if fsz
            ;; the form's size skips the prompt but NOT the cap check
            ;; below: one that will not fit is rejected there and
            ;; retyped at the keyboard, the store already being empty
            (setq sz fsz)
            (progn
              (initget (if dflt 6 7))
              (setq sz (getdist (strcat szmsg
                                        (if dflt (strcat " <" (rtos dflt) ">")
                                            "")
                                        ": ")))
              (if (null sz) (setq sz dflt))))
        ;; how far this treatment eats along each wall, at the real
        ;; corner angle -- so the cap holds on a 135-degree bend or a
        ;; skewed out-of-square corner, not just on a square one
        (setq wed (if ang ang (/ pi 2.0)))
        (while (and maxsb
                    (> (setq sb (* sz (pool:cornerk ty wed))) maxsb))
          (princ (strcat "\nToo large for this corner's walls -- max "
                         (rtos (/ maxsb (pool:cornerk ty wed)))
                         ".  Re-enter."))
          (initget 7)
          (setq sz (getdist (strcat szmsg ": "))))
        (cal:osdown))))
  (mapcar '(lambda (e c) (pool:setcol e c)) ents cols)
  (if ty (list ty sz) 'CAL-BACK)))

;; Ask one treatment per corner, in order, Enter reusing the previous
;; corner's answer -- the out-of-square pattern.  labels / caps / angs
;; / entl run parallel: the prompt text, the setback budget, the real
;; wedge angle to size the budget against, and the guide entities to
;; light up while that corner is being asked.
;; Back inside the loop steps to the PREVIOUS corner and re-asks it;
;; Back on the first corner returns CAL-BACK for the stage to hand on.
;; Returns a list of (type size), or CAL-BACK.
(defun pool:askcorners (labels caps angs entl / i n out prevty prevsz cc back)
  (setq i 0 n (length labels) out nil back nil)
  (while (and (< i n) (not back))
    (setq cc (pool:askcorner (nth i labels) prevty prevsz (nth i entl)
                             (nth i caps) (nth i angs) t))
    (if (eq cc 'CAL-BACK)
        (if (= i 0)
            (setq back t)               ; back out of the whole stage
            (setq i (1- i)
                  out (cdr out)
                  ;; the reuse default is the corner BEFORE the one
                  ;; being re-asked
                  prevty (if out (car (car out)) nil)
                  prevsz (if out (cadr (car out)) nil)))
        (setq prevty (car cc) prevsz (cadr cc)
              out (cons cc out)
              i (1+ i))))
  (if back 'CAL-BACK (reverse out)))

;; Treatment ends for every corner of a closed ring of points, in ring
;; order -- pool:cornerends applied all the way round.
(defun pool:ringends (pts corners / n i out)
  (setq n (length pts) i 0)
  (while (< i n)
    (setq out (cons (pool:cornerends (nth i pts)
                                     (nth (rem (+ i (1- n)) n) pts)
                                     (nth (rem (+ i 1) n) pts)
                                     (car (nth i corners)) (cadr (nth i corners))
                                     (caddr (nth i corners)))
                    out)
          i (1+ i)))
  (reverse out))

;; Draw the corner treatments themselves -- chamfer faces and fillet
;; arcs -- for a ring whose straight walls the caller has already
;; drawn between the treatment ends.  Returns the fillet-arc entity
;; per corner (nil where the corner is square or chamfered), which is
;; what the radius dims measure.
(defun pool:ringarcs (ce corners lay / out k cc)
  (setq k 0 out nil)
  (foreach cc corners
    (cond
      ((= (car cc) "Cut")
       (pool:line (car (nth k ce)) (cadr (nth k ce)) lay)
       (setq out (cons nil out)))
      ((= (car cc) "Radius")
       (pool:arc3p (car (nth k ce)) (caddr (nth k ce)) (cadr (nth k ce)) lay)
       (setq out (cons (entlast) out)))
      (t (setq out (cons nil out))))
    (setq k (1+ k)))
  (reverse out))

;; Report rows for a set of corner treatments: one row per corner that
;; is not Square, labelled "<label> RAD" or "<label> FACE".  labels
;; and corners run parallel.
(defun pool:cornerrows (labels corners / out k cc)
  (setq k 0 out nil)
  (foreach cc corners
    (cond
      ((pool:cutp (car cc))
       (setq out (cons (list (strcat (nth k labels)
                                     (if (= (car cc) "Radius") " RAD" " FACE"))
                             (cadr cc) (cadr cc))
                       out)))
      ;; nothing was measured, so both columns read N/A -- the row
      ;; exists to record that the sheet never said
      ((= (car cc) "NotGiven")
       (setq out (cons (list (strcat (nth k labels) " NotGiven") nil nil)
                       out))))
    (setq k (1+ k)))
  (reverse out))

;; Cross-dim measurement templates for the chosen reference mode.
;; Each entry: (diagkey prompt rowlabel iA specA iC specC).  Ends uses
;; both endpoints on each side of the diagonal.
(defun pool:crosstemplate (cmode)
  (cond
    ((= cmode "Middle")
     (list (list 'ac "Cross dim A-C (to corner middles)" "AC MID" 0 'mid 2 'mid)
           (list 'bd "Cross dim B-D (to corner middles)" "BD MID" 1 'mid 3 'mid)))
    ;; The two ties of a diagonal CROSS each other, the way the tape
    ;; actually runs: each starts at one end of a corner treatment and
    ;; finishes at the OPPOSITE end of the far treatment.  Pairing the
    ;; same side at both corners would give two near-parallel ties,
    ;; which pin the out-of-squareness down far less.
    ((= cmode "Ends")
     (list (list 'ac "Cross A-C (A>B end to C>D end)" "AC B-D" 0 'next 2 'next)
           (list 'ac "Cross A-C (A>D end to C>B end)" "AC D-B" 0 'prev 2 'prev)
           (list 'bd "Cross B-D (B>A end to D>C end)" "BD A-C" 1 'prev 3 'prev)
           (list 'bd "Cross B-D (B>C end to D>A end)" "BD C-A" 1 'next 3 'next)))
    (t
     (list (list 'ac "Cross dim bottom-left to top-right (A-C)" "CROSS A-C" 0 'true 2 'true)
           (list 'bd "Cross dim bottom-right to top-left (B-D)" "CROSS B-D" 1 'true 3 'true)))))

;; Average of a diagonal's raw measurements (bootstrap), or the
;; corner-corrected effective true-corner target using estimate q.
(defun pool:rawavg (xmeas diagkey / sum n)
  (setq sum 0.0 n 0)
  (foreach m xmeas
    (if (and (eq (car m) diagkey) (nth 7 m))
        (setq sum (+ sum (nth 7 m)) n (1+ n))))
  (if (> n 0) (/ sum n) nil))

(defun pool:effcross (q corners xmeas diagkey / sum n ra rc)
  (setq sum 0.0 n 0)
  (foreach m xmeas
    (if (and (eq (car m) diagkey) (nth 7 m))
        (progn
          (setq ra (pool:cornerpoint q corners (nth 3 m) (nth 4 m))
                rc (pool:cornerpoint q corners (nth 5 m) (nth 6 m))
                sum (+ sum (+ (nth 7 m)
                              (- (distance (nth (nth 3 m) q) (nth (nth 5 m) q))
                                 (distance ra rc))))
                n (1+ n)))))
  (if (> n 0) (/ sum n) nil))

;;; -------------------- pool bottom / hopper (rectangle) ---------------
;;;
;;;  Field-sheet letters (plan view):
;;;
;;;      D ------------------------------------ C
;;;      |\        M                           /|
;;;      | htl --------- htr                 /  |
;;;      |  |   hopper    |  \            brkt  |
;;;      |H |G    (G x L) |     \           |   |
;;;      | hbl --------- hbr       \        | E |
;;;      |/        K          \       \   brkb  |
;;;      A ------------------------------------ B
;;;
;;;  H = left end -> hopper, G = hopper length, F = hopper -> slope
;;;  break (CHECK), E = slope break -> right end, M = top -> hopper,
;;;  L = hopper width (CHECK), K = hopper -> bottom.  The primary dims
;;;  are perimeter OFFSETS (H, E, M, K) plus the hopper size G; F and
;;;  L are redundant and reported as checks with their deltas.
;;;  The hopper's left corners tie to the pool's left corners -- to the
;;;  end-wall end of the corner treatment when that corner is cut or
;;;  rounded -- and its right corners tie to the slope-break ends.

;; Intersection of two infinite lines (p1 along d1, p2 along d2).
(defun pool:linex (p1 d1 p2 d2 / den s)
  (setq den (- (* (car d1) (cadr d2)) (* (cadr d1) (car d2))))
  (if (> (abs den) 1.0e-9)
      (progn
        (setq s (/ (- (* (- (car p2) (car p1)) (cadr d2))
                      (* (- (cadr p2) (cadr p1)) (car d2)))
                   den))
        (cal:v+ p1 (cal:v* d1 s)))
      ;; parallel lines never truly happen on sane input; a degenerate
      ;; fit must not crash a caller with nil, so fall back to the
      ;; midpoint of the two anchor points
      (cal:mid p1 p2)))

;; The side p->q offset inward (toward cen) by dist, as (point dir).
(defun pool:offline (p q cen dist / n)
  (setq n (pool:unit (cal:perp (cal:v- q p))))
  (if (> (cal:dot (cal:v- (cal:mid p q) cen) n) 0.0)
      (setq n (cal:v* n -1.0)))
  (list (cal:v+ p (cal:v* n dist)) (cal:v- q p)))

;; All hopper geometry for quad + corner treatments + the primary
;; offsets.  Returns an assoc list of named points: hopper corners
;; (hbl htl hbr htr), slope-break ends (brkb brkt), left tie anchors
;; (lab lat), and the measuring-chain points -- horizontal pl phl phr
;; pbrk pr, vertical pb phb pht pt (through the hopper centre).
(defun pool:hopcalc (quad corners h g e m k / a b c d cen hl hr ht hb brk
                                              hbl htl hbr htr brkb brkt
                                              lab1 lab2 lat1 lat2
                                              rab1 rab2 rat1 rat2
                                              hc hdir vdir hc2)
  (setq a (car quad) b (cadr quad) c (caddr quad) d (cadddr quad)
        cen (cal:v* (cal:v+ (cal:v+ a b) (cal:v+ c d)) 0.25)
        hl (pool:offline a d cen h)
        hr (pool:offline a d cen (+ h g))
        ht (pool:offline d c cen m)
        hb (pool:offline a b cen k)
        brk (pool:offline b c cen e)
        hbl (pool:linex (car hl) (cadr hl) (car hb) (cadr hb))
        htl (pool:linex (car hl) (cadr hl) (car ht) (cadr ht))
        hbr (pool:linex (car hr) (cadr hr) (car hb) (cadr hb))
        htr (pool:linex (car hr) (cadr hr) (car ht) (cadr ht))
        brkb (pool:linex (car brk) (cadr brk) a (cal:v- b a))
        brkt (pool:linex (car brk) (cadr brk) d (cal:v- c d))
        ;; both ends of each left corner treatment (Square -> both ends
        ;; coincide with the true corner)
        lab1 (pool:cornerpoint quad corners 0 'prev)
        lab2 (pool:cornerpoint quad corners 0 'next)
        lat1 (pool:cornerpoint quad corners 3 'next)
        lat2 (pool:cornerpoint quad corners 3 'prev)
        ;; and the same for the right corners, used when E = 0 puts the
        ;; slope break on the end wall: the floor breaks to the ends of
        ;; the corner treatment, not to the sharp corner behind it
        rab1 (pool:cornerpoint quad corners 1 'prev)
        rab2 (pool:cornerpoint quad corners 1 'next)
        rat1 (pool:cornerpoint quad corners 2 'next)
        rat2 (pool:cornerpoint quad corners 2 'prev)
        hc (cal:v* (cal:v+ (cal:v+ hbl htl) (cal:v+ hbr htr)) 0.25)
        hdir (cal:v- b a)
        vdir (cal:v- d a)
        ;; H/G/F/E chain sits below the hopper centre by 12" or L/6
        ;; (2/3 down from the top of L), whichever is closer; the
        ;; M/L/K chain sits 12" right of the hopper's right edge
        hc2 (cal:v- hc (cal:v* (pool:unit vdir)
                                 (min 12.0 (/ (distance hbr htr) 6.0)))))
  (list (list 'hbl hbl) (list 'htl htl) (list 'hbr hbr) (list 'htr htr)
        (list 'brkb brkb) (list 'brkt brkt)
        (list 'lab1 lab1) (list 'lab2 lab2)
        (list 'lat1 lat1) (list 'lat2 lat2)
        (list 'rab1 rab1) (list 'rab2 rab2)
        (list 'rat1 rat1) (list 'rat2 rat2)
        (list 'pl (pool:linex hc2 hdir a (cal:v- d a)))
        (list 'phl (pool:linex hc2 hdir (car hl) (cadr hl)))
        (list 'phr (pool:linex hc2 hdir (car hr) (cadr hr)))
        (list 'pbrk (pool:linex hc2 hdir (car brk) (cadr brk)))
        (list 'pr (pool:linex hc2 hdir b (cal:v- c b)))
        ;; M/L/K attach to the hopper's right edge itself; the dim
        ;; line floats 12" further right via 'voff
        (list 'pb (pool:linex (car hr) (cadr hr) a (cal:v- b a)))
        (list 'phb hbr)
        (list 'pht htr)
        (list 'pt (pool:linex (car hr) (cadr hr) d (cal:v- c d)))
        (list 'voff (cal:v* (pool:unit hdir) pool:*mlkoff*))
        ;; G = 0 collapses the pad to a single deep line; E = 0 puts the
        ;; slope break on the end wall, which is already drawn
        (list 'zg (< g 1.0e-6))
        (list 'ze (< e 1.0e-6))))

;; Draw the hopper, slope break and corner ties on layer lay.  Each
;; hopper left corner ties to BOTH ends of its pool corner treatment
;; (one line when the corner is square and the ends coincide).
;; tie = draw the left corner ties (off for shapes whose "left end" is
;; an arc rather than a pair of corners).
(defun pool:hopdraw (gg lay tie / hbl htl hbr htr brkb brkt lab1 lab2 lat1 lat2
                                  rab1 rab2 rat1 rat2)
  (setq hbl (cadr (assoc 'hbl gg)) htl (cadr (assoc 'htl gg))
        hbr (cadr (assoc 'hbr gg)) htr (cadr (assoc 'htr gg))
        brkb (cadr (assoc 'brkb gg)) brkt (cadr (assoc 'brkt gg))
        lab1 (cadr (assoc 'lab1 gg)) lab2 (cadr (assoc 'lab2 gg))
        lat1 (cadr (assoc 'lat1 gg)) lat2 (cadr (assoc 'lat2 gg))
        rab1 (cadr (assoc 'rab1 gg)) rab2 (cadr (assoc 'rab2 gg))
        rat1 (cadr (assoc 'rat1 gg)) rat2 (cadr (assoc 'rat2 gg)))
  (pool:line hbl htl lay)               ; deep-end line (the whole pad when G=0)
  (if (not (cadr (assoc 'zg gg)))
      (progn
        (pool:line htl htr lay)
        (pool:line htr hbr lay)
        (pool:line hbr hbl lay)))
  (if tie
      (progn
        (pool:line lab1 hbl lay)
        (if (> (distance lab1 lab2) 1.0e-6) (pool:line lab2 hbl lay))
        (pool:line lat1 htl lay)
        (if (> (distance lat1 lat2) 1.0e-6) (pool:line lat2 htl lay))))
  (if (and (cadr (assoc 'ze gg)) tie)
      ;; E = 0: the break IS the end wall, so the floor breaks to BOTH
      ;; ends of each right corner treatment -- the same rule the left
      ;; corners follow -- rather than to the sharp corner behind it
      (progn
        (pool:line rab1 hbr lay)
        (if (> (distance rab1 rab2) 1.0e-6) (pool:line rab2 hbr lay))
        (pool:line rat1 htr lay)
        (if (> (distance rat1 rat2) 1.0e-6) (pool:line rat2 htr lay)))
      (progn
        (if (not (cadr (assoc 'ze gg))) (pool:line brkb brkt lay))
        (pool:line htr brkt lay)
        (pool:line hbr brkb lay))))

;;; -------------------- bottom styles ----------------------------------
;;;
;;;  Every one of these is the standard hopper's plan language -- the
;;;  same H/G/F/E/M/L/K chain, deep-end line, slope break and corner
;;;  ties -- with G and/or E pinned to zero, plus the side profile the
;;;  style implies (per the reference drawing):
;;;
;;;    Normal     full hopper, plan only.  A G of 0 turns it into a
;;;               Slope bottom and the profile appears automatically.
;;;    Wedge      G=0, E=0: a deep line at H, floor rising all the way
;;;               to the far wall.
;;;    SLope      G=0: a deep line at H, floor rising to a full-width
;;;               break, then flat to the far wall.
;;;    MOdflat    E=0: one flat pad inset H / G / F, sloping up to the
;;;               walls all round, no shallow flat.
;;;    SHallow    full hopper whose shallow floor is not flat -- it
;;;               slopes from C2 at the break up to C at the wall.

;; Per style: (ask-G ask-E has-profile ask-C2 slack-index).  The slack
;; member absorbs any mismatch when the whole chain was given: G where
;; there is a pad, F where the deep end is a line.
(defun pool:btmspec (style)
  (cond
    ((= style "Wedge")   (list nil nil t   nil 2))
    ((= style "SLope")   (list nil t   t   nil 2))
    ((= style "MOdflat") (list t   nil t   nil 1))
    ((= style "SHallow") (list t   t   t   t   1))
    (t                   (list t   t   nil nil 1))))

;; Nominal guide proportions (h g e) for the style's preview.
(defun pool:btmnom (style len)
  (cond
    ((= style "Wedge")   (list (* 0.12 len) 0.0 0.0))
    ((= style "SLope")   (list (* 0.12 len) 0.0 (* 0.30 len)))
    ((= style "MOdflat") (list (* 0.10 len) (* 0.70 len) 0.0))
    (t                   (list (* 0.12 len) (* 0.20 len) (* 0.40 len)))))

;; Bottom vertices ((run . depth) ...) between the two wall bottoms,
;; left (deep end) to right.  wh = wall height, dp = deep depth,
;; c2 = depth where the shallow floor meets the slope break.
(defun pool:btmbrks (style h g f wh dp c2)
  (cond
    ((= style "Wedge")   (list (cons h dp)))
    ((= style "MOdflat") (list (cons h dp) (cons (+ h g) dp)))
    ((= style "SHallow") (list (cons h dp) (cons (+ h g) dp)
                               (cons (+ h g f) c2)))
    ;; SLope, and a Normal hopper whose G came out at 0
    (t                   (list (cons h dp) (cons (+ h g f) wh)))))

;; Letters the style prompts for, in order, with their chain points.
(defun pool:btmties (style / sp)
  (setq sp (pool:btmspec style))
  (append (list (list "H" 'pl 'phl))
          (if (car sp) (list (list "G" 'phl 'phr)) nil)
          (list (list "F" 'phr 'pbrk))
          (if (cadr sp) (list (list "E" 'pbrk 'pr)) nil)
          (list (list "M" 'pht 'pt) (list "L" 'phb 'pht)
                (list "K" 'pb 'phb))))

;; The field-sheet guide inside the fitted pool is LIVE: hn:geo inside
;; pool:hopnormal builds it through the collector (see "live guide
;; reshaping"), so the hopper, its ties and the nominal section all
;; reshape as the letters and depths come in.

;; Resolve a bottom measurement chain against the pool total:
;;   * NA (nil) entries take the remainder -- split evenly when there
;;     is more than one
;;   * when every value is provided but the sum misses the total, the
;;     slack member at index islack (G on the horizontal chain, L on
;;     the vertical) absorbs the difference; islack -1 = nobody (the
;;     caller handles the residual itself)
;; Returns the resolved list.
(defun pool:chainfix (vals total islack / sum n share out k v)
  (setq sum 0.0 n 0)
  (foreach v vals (if v (setq sum (+ sum v)) (setq n (1+ n))))
  (setq out nil k 0)
  (if (> n 0)
      (progn
        (setq share (/ (- total sum) n))
        (foreach v vals (setq out (cons (if v v share) out))))
      (foreach v vals
        (setq out (cons (if (and (= k islack)
                                 (> (abs (- sum total)) 1.0e-6))
                            (+ v (- total sum))
                            v)
                        out)
              k (1+ k))))
  (reverse out))

;; Post-check a resolved chain: no member may be negative.  A member
;; that resolved below zero is lifted to a positive floor (12", or a
;; share of the total on a small pool) and the deficit comes out of
;; the LARGEST other member -- e.g. a G that went negative is drawn
;; 1' long and F gives up the difference.  Returns (vals fixed):
;; fixed holds the index of every member changed (the lifted one AND
;; its donor) so the caller can flag their dims and report rows red.
(defun pool:chainval (vals total / out fixed n i j v flo need big bigi w)
  (setq n (length vals)
        flo (min 12.0 (/ (abs total) (* 4.0 n)))
        out vals fixed nil i 0)
  (while (< i n)
    (setq v (nth i out))
    (if (< v -1.0e-6)
        (progn
          (setq need (- flo v) big -1.0e30 bigi nil j 0)
          (foreach w out
            (if (and (/= j i) (> w big)) (setq big w bigi j))
            (setq j (1+ j)))
          (setq out (pool:setnth (pool:setnth out i flo) bigi (- big need))
                fixed (append fixed (list i bigi)))))
    (setq i (1+ i)))
  (list out fixed))

;; Record a validation problem: an immediate command-line warning now,
;; and a red note under the report table later.
(defun pool:valnote (msg)
  (setq pool:*valnotes* (append pool:*valnotes* (list msg)))
  (princ (strcat "\n*** " msg " ***"))
  (princ))

;; The adjusted letters as "G/F" for a note.
(defun pool:fixnames (fixed labels / out i)
  (setq out "")
  (foreach i fixed
    (setq out (strcat out (if (= out "") "" "/") (nth i labels))))
  out)

;; Color the just-drawn dimension red (a measurement the validator had
;; to adjust).
(defun pool:dimred ( / e ed)
  (setq e (entlast))
  (if (and e (setq ed (entget e)))
      (entmod (if (assoc 62 ed)
                  (subst (cons 62 1) (assoc 62 ed) ed)
                  (append ed (list (cons 62 1)))))))

;; Report row, red-flagged when index i is among the adjusted ones.
(defun pool:vrow (label tgt act i fixed)
  (append (list label tgt act) (if (member i fixed) (list t) nil)))

;; Deep depth must beat the wall height; C2 must land between them.
(defun pool:askdeep (msg ents wh / dp)
  (setq dp (pool:askh msg ents))
  (while (<= dp wh)
    (princ (strcat "\nD must be deeper than the wall height C ("
                   (rtos wh) ") -- re-enter."))
    (setq dp (pool:askh msg ents)))
  dp)

(defun pool:askc2 (msg ents wh dp / c2)
  (setq c2 (pool:askh msg ents))
  (while (or (< c2 wh) (> c2 dp))
    (princ (strcat "\nC2 must be between C (" (rtos wh) ") and D ("
                   (rtos dp) ") -- re-enter."))
    (setq c2 (pool:askh msg ents)))
  c2)

;; Hopper-language bottom: lettered guide, the H/G/F/E/M/L/K chain,
;; plan hopper + chain dims, and -- for every style but Normal -- the
;; side profile below with its depth dims.
;; style = Normal / Wedge / SLope / MOdflat / SHallow (see above);
;; x0/y0 place the side profile below the pool; tie draws the left
;; corner ties.
(defun pool:hopnormal (quad corners doff th lmode style x0 y0 tie
                       / pv h g f e m l k gg tl odl sp
                         hraw graw fraw eraw mraw lraw kraw wh dp c2
                         a b c d cen toth totv hres vres skipe rows
                         cv hfx vfx ans lmode2 toth2 totv2)
  (setq sp (pool:btmspec style))
  ;; wall-to-wall totals through the pool centre: B1 along the run,
  ;; V1 across it
  (setq a (car quad) b (cadr quad) c (caddr quad) d (cadddr quad)
        cen (cal:v* (cal:v+ (cal:v+ a b) (cal:v+ c d)) 0.25)
        toth (distance (pool:linex cen (cal:v- b a) a (cal:v- d a))
                       (pool:linex cen (cal:v- b a) b (cal:v- c b)))
        totv (distance (pool:linex cen (cal:v- d a) a (cal:v- b a))
                       (pool:linex cen (cal:v- d a) d (cal:v- c d))))
  ;; The live guide geometry (see "live guide reshaping"): the chain
  ;; letters answered so far are held and the open ones share what the
  ;; two totals have left (pool:pvchain), so the hopper on screen
  ;; closes against the pool at every answer -- and, on the profile
  ;; styles, the section under the plan reshapes the same way as the
  ;; depths come in.
  (defun hn:geo ( / len nom res hv gv fv ev mv kv gg pr tl wh2 dp2 c22 fb)
    (setq len (distance (car quad) (cadr quad))
          nom (pool:btmnom style len)
          res (pool:pvchain
                (list (pool:pvdim 'h)
                      (if (car sp) (pool:pvdim 'g) 0.0)
                      (pool:pvdim 'f)
                      (if (cadr sp) (pool:pvdim 'e) 0.0))
                (list (car nom) (cadr nom)
                      (max 1.0 (- len (car nom) (cadr nom) (caddr nom)))
                      (caddr nom))
                toth)
          hv (car res) gv (cadr res) fv (caddr res) ev (cadddr res)
          res (pool:pvchain
                (list (pool:pvdim 'm) (pool:pvdim 'l) (pool:pvdim 'k))
                (list (* 0.25 totv) (* 0.5 totv) (* 0.25 totv))
                totv)
          mv (car res) kv (caddr res)
          gg (pool:hopcalc quad corners hv gv ev mv kv))
    (pool:pvcopen)
    ;; the outline, with the structure the STYLE fixes -- a pad or a
    ;; break that shrinks to nothing simply collapses in place
    (foreach pr (append (list (list 'hbl 'htl))
                        (if (car sp)
                            (list (list 'htl 'htr) (list 'htr 'hbr)
                                  (list 'hbr 'hbl))
                            nil)
                        (if (cadr sp) (list (list 'brkb 'brkt)) nil)
                        (if tie
                            (list (list 'lab1 'hbl) (list 'lab2 'hbl)
                                  (list 'lat1 'htl) (list 'lat2 'htl))
                            nil)
                        ;; a style with E pinned to 0 breaks to the
                        ;; right corner treatments instead
                        (if (and (not (cadr sp)) tie)
                            (list (list 'rab1 'hbr) (list 'rab2 'hbr)
                                  (list 'rat1 'htr) (list 'rat2 'htr))
                            (list (list 'htr 'brkt) (list 'hbr 'brkb))))
      (pool:pvcput (list "LINE" (cadr (assoc (car pr) gg))
                         (cadr (assoc (cadr pr) gg)))))
    (foreach tl (pool:btmties style)
      (pool:pvctie (cadr (assoc (cadr tl) gg))
                   (cadr (assoc (caddr tl) gg))
                   (car tl) th))
    ;; the profile styles get a section under the plan, so the depth
    ;; prompts highlight a tie the same way the plan letters do
    (if (caddr sp)
        (progn
          (setq wh2 (cond ((pool:pvdim 'wh)) ((* 0.25 totv)))
                dp2 (cond ((pool:pvdim 'dp)) ((* 0.55 totv)))
                ;; a deep C with D still open must not float the floor
                ;; above the wall bottoms while D is being asked
                dp2 (max dp2 (* 1.15 wh2))
                c22 (cond ((pool:pvdim 'c2)) ((* 0.5 (+ wh2 dp2))))
                fb (max 0.0 (- toth hv gv ev)))
          (pool:profdraw x0 y0 toth wh2
                         (pool:btmbrks style hv gv fb wh2 dp2 c22)
                         "POOL-NOTES" t)
          (pool:pvctie (list (+ x0 toth (* 0.6 doff)) y0)
                       (list (+ x0 toth (* 0.6 doff)) (- y0 wh2)) "C" th)
          (pool:pvctie (list (+ x0 hv) y0)
                       (list (+ x0 hv) (- y0 dp2)) "D" th)
          (if (cadddr sp)
              (pool:pvctie (list (+ x0 hv gv fb) y0)
                           (list (+ x0 hv gv fb) (- y0 c22)) "C2" th))))
    (pool:pvcout quad))
  (setq pv (pool:pvlive 'hn:geo))
  (princ "\nPool bottom -- offsets from the perimeter; the RED tie is the one being asked for.")
  (princ "\n(after the first answer, Back re-asks the previous one)")
  ;; L pools: when H+G+F are all given and already span the main
  ;; section (B1), the break lands on the inner corner and E is moot.
  ;;
  ;; Suggestions, all taken with Enter and all still typeable over:
  ;;   * H, M and K are usually the same offset, so M suggests H;
  ;;   * the LAST member of either chain is arithmetic once the rest
  ;;     are in -- E is what B1 has left of H+G+F, K what A has left
  ;;     of M+L -- so it is offered rather than asked for cold;
  ;;   * M answered the same as H says the deep end sits square in the
  ;;     pool, which fixes L at A - 2M (pool:sugsym).
  ;; Between them a squarely-set hopper is four Enters.
  (setq lmode2 lmode toth2 toth totv2 totv
        ans (pool:askseq
              (append
                (list (list 'h 'NAX "H - left end to deep end" (cdr (assoc "H" pv))))
                (if (car sp)
                    (list (list 'g 'ZER (if (= style "MOdflat")
                                            "G - flat pad length"
                                            "G - hopper length, 0 = slope bottom")
                                (cdr (assoc "G" pv))))
                    (list (list 'g 'NAX "G" nil nil ''t)))
                (list (list 'f 'NAX (if (= style "MOdflat")
                                        "F - pad to right end"
                                        "F - deep end to slope break")
                            (cdr (assoc "F" pv)))
                      (list 'e 'NAX "E - slope break to right end"
                            (cdr (assoc "E" pv)) nil
                            '(or (not (cadr sp))
                                 (and lmode2 (pool:sq ans 'h) (pool:sq ans 'g)
                                      (pool:sq ans 'f)
                                      (<= (abs (- (+ (pool:sq ans 'h) (pool:sq ans 'g)
                                                     (pool:sq ans 'f))
                                                  toth2))
                                          0.5)))
                            "\nH + G + F span the main section -- E not needed."
                            '(pool:chainrest ans '(h g f) toth2))
                      (list 'm 'SUG "M - top side to deep end" (cdr (assoc "M" pv)) '(h))
                      (list 'l 'NAX "L - deep end width" (cdr (assoc "L" pv))
                            nil nil nil '(pool:sugsym ans totv2))
                      (list 'k 'SUG "K - deep end to bottom side"
                            (cdr (assoc "K" pv)) '(m h) nil nil
                            '(pool:chainrest ans '(m l) totv2)))))
        hraw (pool:sq ans 'h) graw (pool:sq ans 'g) fraw (pool:sq ans 'f)
        eraw (pool:sq ans 'e) mraw (pool:sq ans 'm) lraw (pool:sq ans 'l)
        kraw (pool:sq ans 'k)
        skipe (and (cadr sp) (equal eraw 0.0)))
  (if (not (car sp)) (setq graw 0.0))
  (if (not (cadr sp)) (setq eraw 0.0))
  ;; depths, while the live section is still on screen -- each answer
  ;; reshapes it, so C sets the walls and D digs the deep end in front
  ;; of the user
  (if (caddr sp)
      (progn
        (setq wh (pool:askh "C - wall height (shallow depth)" (cdr (assoc "C" pv))))
        (pool:pvnote 'wh wh)
        (setq dp (pool:askdeep "D - deep end depth" (cdr (assoc "D" pv)) wh))
        (pool:pvnote 'dp dp)
        (setq c2 (if (cadddr sp)
                     (pool:askc2 "C2 - depth where the shallow floor meets the break"
                                 (cdr (assoc "C2" pv)) wh dp)
                     wh))
        (if (cadddr sp) (pool:pvnote 'c2 c2))))
  (pool:pvkill)
  ;; resolve the chains: NA takes the remainder (split when several);
  ;; the style's slack member (G with a pad, F without) absorbs any
  ;; leftover, and L does across the pool
  (setq hres (pool:chainfix (list hraw graw fraw eraw) toth (nth 4 sp))
        vres (pool:chainfix (list mraw lraw kraw) totv 1)
        cv (pool:chainval hres toth) hres (car cv) hfx (cadr cv)
        cv (pool:chainval vres totv) vres (car cv) vfx (cadr cv)
        h (car hres) g (cadr hres) f (caddr hres) e (cadddr hres)
        m (car vres) l (cadr vres) k (caddr vres))
  ;; a chain member that resolved negative was floored and its donor
  ;; trimmed: both get RED dims and RED report rows below
  (if hfx (pool:valnote (strcat "BOTTOM LENGTHS FAILED - "
                                (pool:fixnames hfx '("H" "G" "F" "E"))
                                " ADJUSTED, VERIFY")))
  (if vfx (pool:valnote (strcat "BOTTOM WIDTHS FAILED - "
                                (pool:fixnames vfx '("M" "L" "K"))
                                " ADJUSTED, VERIFY")))
  ;; a G that came out at zero is a slope bottom whatever was asked
  ;; for, so the section comes along automatically
  (if (< g 1.0e-6) (setq g 0.0))
  (if (and (= g 0.0) (not (caddr sp)))
      (progn
        (princ "\nG = 0 -- that is a slope bottom, so a side view is drawn too.")
        (setq wh (pool:askh "C - wall height (shallow depth)" nil)
              dp (pool:askdeep "D - deep end depth" nil wh)
              c2 wh)))
  (setq gg (pool:hopcalc quad corners h g e m k))
  (pool:hopdraw gg "POOL" tie)
  ;; side profile below the plan, per the style
  (if wh
      (pool:profdraw x0 y0 toth wh
                     (pool:btmbrks (if (caddr sp) style "SLope")
                                   h g f wh dp c2)
                     "POOL" nil))
  ;; chain dimensions along the two centerlines, like the sheet
  (setq odl (getvar "CLAYER"))
  (setvar "CLAYER" "DIMENSION")
  ;; M/L/K def points sit on the hopper edge; their dim line floats
  ;; 30" right via the 'voff vector
  (foreach tl (list (list 'pl 'phl nil (member 0 hfx))
                    (list 'phl 'phr nil (member 1 hfx))
                    (list 'phr 'pbrk nil (member 2 hfx))
                    (list 'pbrk 'pr nil (member 3 hfx))
                    (list 'pht 'pt t (member 0 vfx))
                    (list 'phb 'pht t (member 1 vfx))
                    (list 'pb 'phb t (member 2 vfx)))
    ;; a pinned-out letter (G with no pad, E on the wall) has nothing
    ;; to dimension
    (if (> (distance (cadr (assoc (car tl) gg)) (cadr (assoc (cadr tl) gg)))
           1.0e-6)
        (progn
          (pool:dimalg (cadr (assoc (car tl) gg)) (cadr (assoc (cadr tl) gg))
                       (cal:v+ (cal:mid (cadr (assoc (car tl) gg))
                                          (cadr (assoc (cadr tl) gg)))
                                (if (caddr tl) (cadr (assoc 'voff gg))
                                    (list 0.0 0.0))))
          (if (cadddr tl) (pool:dimred)))))
  ;; profile depths: C at the shallow wall, D at the deep end.  These
  ;; belong to the section, so they join pool:*profents* and stay put
  ;; when an L pool's plan is mirrored.
  (if wh
      (progn
        (pool:dimalg (list (+ x0 toth) y0) (list (+ x0 toth) (- y0 wh))
                     (list (+ x0 toth (* 0.8 doff)) (- y0 (* 0.5 wh))))
        (setq pool:*profents* (cons (entlast) pool:*profents*))
        (pool:dimalg (list (+ x0 h) y0) (list (+ x0 h) (- y0 dp))
                     (list (+ x0 h (* -0.5 doff)) (- y0 (* 0.5 dp))))
        (setq pool:*profents* (cons (entlast) pool:*profents*))
        (if (cadddr sp)
            (progn
              (pool:dimalg (list (+ x0 h g f) y0) (list (+ x0 h g f) (- y0 c2))
                           (list (+ x0 h g f (* 0.3 doff)) (- y0 (* 0.5 c2))))
              (setq pool:*profents* (cons (entlast) pool:*profents*))))))
  (setvar "CLAYER" odl)
  (setq rows (list
    (pool:vrow "HOP H" hraw (distance (cadr (assoc 'pl gg)) (cadr (assoc 'phl gg))) 0 hfx)
    (pool:vrow "HOP G" (if (car sp) graw nil)
               (distance (cadr (assoc 'phl gg)) (cadr (assoc 'phr gg))) 1 hfx)
    (pool:vrow "HOP F" fraw (distance (cadr (assoc 'phr gg)) (cadr (assoc 'pbrk gg))) 2 hfx)
    (pool:vrow "HOP E" (if (or skipe (not (cadr sp))) nil eraw)
               (distance (cadr (assoc 'pbrk gg)) (cadr (assoc 'pr gg))) 3 hfx)
    (pool:vrow "HOP M" mraw (distance (cadr (assoc 'pht gg)) (cadr (assoc 'pt gg))) 0 vfx)
    (pool:vrow "HOP L" lraw (distance (cadr (assoc 'phb gg)) (cadr (assoc 'pht gg))) 1 vfx)
    (pool:vrow "HOP K" kraw (distance (cadr (assoc 'pb gg)) (cadr (assoc 'phb gg))) 2 vfx)))
  (if wh
      (setq rows (append rows
                         (list (list "WALL HT C" wh wh)
                               (list "DEPTH D" dp dp))
                         (if (cadddr sp)
                             (list (list "BRK DEPTH C2" c2 c2))
                             nil))))
  rows)


;; Offset an infinite line (pt dir) toward cen by dist -> (pt dir).
(defun pool:offln (ln cen dist / n)
  (setq n (pool:unit (cal:perp (cadr ln))))
  (if (> (cal:dot (cal:v- (car ln) cen) n) 0.0)
      (setq n (cal:v* n -1.0)))
  (list (cal:v+ (car ln) (cal:v* n dist)) (cadr ln)))

;; Sport bottom PLAN geometry (per the reference drawing): full-width
;; break lines at the outer breaks, the deep flat drawn as a rectangle
;; inset M/K from the side walls, and corner diagonals tying the outer
;; breaks to the deep-flat corners -- the standard hopper language.
;; Chain points follow the standard-hopper placement rules.
(defun pool:hopsportc (lline rline bline tline cen e2 f2 g f1 e1 m k
                       / obl dfl dfr obr dfb dft oblb oblt obrb obrt
                         dbl dtl dbr dtr hc hc2 up)
  (setq obl (pool:offln lline cen e2)
        dfl (pool:offln lline cen (+ e2 f2))
        dfr (pool:offln lline cen (+ e2 f2 g))
        obr (pool:offln lline cen (+ e2 f2 g f1))
        dfb (pool:offln bline cen k)
        dft (pool:offln tline cen m)
        oblb (pool:linex (car obl) (cadr obl) (car bline) (cadr bline))
        oblt (pool:linex (car obl) (cadr obl) (car tline) (cadr tline))
        obrb (pool:linex (car obr) (cadr obr) (car bline) (cadr bline))
        obrt (pool:linex (car obr) (cadr obr) (car tline) (cadr tline))
        dbl (pool:linex (car dfl) (cadr dfl) (car dfb) (cadr dfb))
        dtl (pool:linex (car dfl) (cadr dfl) (car dft) (cadr dft))
        dbr (pool:linex (car dfr) (cadr dfr) (car dfb) (cadr dfb))
        dtr (pool:linex (car dfr) (cadr dfr) (car dft) (cadr dft))
        hc (cal:v* (cal:v+ (cal:v+ dbl dtl) (cal:v+ dbr dtr)) 0.25)
        up (pool:unit (cadr lline))
        hc2 (cal:v- hc (cal:v* up (min 12.0 (/ (distance dbr dtr) 6.0)))))
  (list (list 'oblb oblb) (list 'oblt oblt)
        (list 'obrb obrb) (list 'obrt obrt)
        (list 'dbl dbl) (list 'dtl dtl) (list 'dbr dbr) (list 'dtr dtr)
        (list 'pl (pool:linex hc2 (cadr bline) (car lline) (cadr lline)))
        (list 'pobl (pool:linex hc2 (cadr bline) (car obl) (cadr obl)))
        (list 'pdfl (pool:linex hc2 (cadr bline) (car dfl) (cadr dfl)))
        (list 'pdfr (pool:linex hc2 (cadr bline) (car dfr) (cadr dfr)))
        (list 'pobr (pool:linex hc2 (cadr bline) (car obr) (cadr obr)))
        (list 'pr (pool:linex hc2 (cadr bline) (car rline) (cadr rline)))
        ;; M/L/K attach to the deep flat's right edge; dim line +12"
        (list 'pb (pool:linex (car dfr) (cadr dfr) (car bline) (cadr bline)))
        (list 'pdb dbr)
        (list 'pdt dtr)
        (list 'pt (pool:linex (car dfr) (cadr dfr) (car tline) (cadr tline)))
        (list 'voff (cal:v* (pool:unit (cadr bline)) pool:*mlkoff*))))

(defun pool:hopsportdraw (gg nopad lay pvflag / oblb oblt obrb obrt
                                                dbl dtl dbr dtr)
  (setq oblb (cadr (assoc 'oblb gg)) oblt (cadr (assoc 'oblt gg))
        obrb (cadr (assoc 'obrb gg)) obrt (cadr (assoc 'obrt gg))
        dbl (cadr (assoc 'dbl gg)) dtl (cadr (assoc 'dtl gg))
        dbr (cadr (assoc 'dbr gg)) dtr (cadr (assoc 'dtr gg)))
  (pool:hgl oblb oblt lay pvflag)
  (pool:hgl obrb obrt lay pvflag)
  (if nopad
      (pool:hgl dbl dtl lay pvflag)     ; G = 0: the V line
      (progn
        (pool:hgl dbl dtl lay pvflag)
        (pool:hgl dtl dtr lay pvflag)
        (pool:hgl dtr dbr lay pvflag)
        (pool:hgl dbr dbl lay pvflag)))
  (pool:hgl oblb dbl lay pvflag)
  (pool:hgl oblt dtl lay pvflag)
  (pool:hgl obrb dbr lay pvflag)
  (pool:hgl obrt dtr lay pvflag))

;; Guided sport bottom: plan hopper (standard-hopper dim logic) plus
;; the side profile below with C and D only.  Returns report rows.
;; G = 0 means no hopper pad (V bottom): the deep flat collapses to
;; the single V line, its residual splits across F2/F1, and the G
;; dim/report row are skipped -- the old NOhopper variant, now just a
;; zero answer at the G prompt.
(defun pool:hopsport (lline rline bline tline cen total x0 y0 ymax doff th
                      / wid whn hdn pv e2r f2r gr f1r e1r mraw lraw kraw
                        wh hd res resid e2 f2 g f1 e1 m l k vres gg rows odl
                        brks tl xd nopad cv hfx vfx ans total2 wid2)
  (setq wid (distance (pool:linex cen (cadr lline) (car bline) (cadr bline))
                      (pool:linex cen (cadr lline) (car tline) (cadr tline)))
        whn (* 0.25 wid)
        hdn (* 0.55 wid)
        ;; the two chain totals under names of their own, for the
        ;; suggestion expressions below to read
        total2 total wid2 wid)
  ;; The live guide geometry (see "live guide reshaping"): plan and
  ;; profile together, the chain closing against the pool at every
  ;; answer and the section digging itself as C and D come in.  The
  ;; padded structure is kept whatever G does -- a zero pad simply
  ;; collapses onto the V line.
  (defun hs:geo ( / res e2v f2v gv f1v e1v mv kv wh2 dp2 gg)
    (setq res (pool:pvchain
                (list (pool:pvdim 'e2) (pool:pvdim 'f2) (pool:pvdim 'g)
                      (pool:pvdim 'f1) (pool:pvdim 'e1))
                (list (* 0.12 total) (* 0.20 total) (* 0.30 total)
                      (* 0.26 total) (* 0.12 total))
                total)
          e2v (car res) f2v (cadr res) gv (caddr res)
          f1v (cadddr res) e1v (nth 4 res)
          res (pool:pvchain
                (list (pool:pvdim 'm) (pool:pvdim 'l) (pool:pvdim 'k))
                (list (* 0.2 wid) (* 0.6 wid) (* 0.2 wid))
                wid)
          mv (car res) kv (caddr res)
          wh2 (cond ((pool:pvdim 'wh)) (whn))
          dp2 (cond ((pool:pvdim 'dp)) (hdn))
          ;; a deep C with D still open must not float the floor above
          ;; the wall bottoms while D is being asked
          dp2 (max dp2 (* 1.15 wh2))
          gg (pool:hopsportc lline rline bline tline cen
                             e2v f2v gv f1v e1v mv kv))
    (pool:pvcopen)
    (pool:hopsportdraw gg nil "POOL-NOTES" t)
    (pool:profdraw x0 y0 total wh2
                   (list (cons e2v wh2) (cons (+ e2v f2v) dp2)
                         (cons (+ e2v f2v gv) dp2)
                         (cons (- total e1v) wh2))
                   "POOL-NOTES" t)
    (pool:pvctie (cadr (assoc 'pl gg)) (cadr (assoc 'pobl gg)) "E2" th)
    (pool:pvctie (cadr (assoc 'pobl gg)) (cadr (assoc 'pdfl gg)) "F2" th)
    (pool:pvctie (cadr (assoc 'pdfl gg)) (cadr (assoc 'pdfr gg)) "G" th)
    (pool:pvctie (cadr (assoc 'pdfr gg)) (cadr (assoc 'pobr gg)) "F1" th)
    (pool:pvctie (cadr (assoc 'pobr gg)) (cadr (assoc 'pr gg)) "E1" th)
    (pool:pvctie (cadr (assoc 'pdt gg)) (cadr (assoc 'pt gg)) "M" th)
    (pool:pvctie (cadr (assoc 'pdb gg)) (cadr (assoc 'pdt gg)) "L" th)
    (pool:pvctie (cadr (assoc 'pb gg)) (cadr (assoc 'pdb gg)) "K" th)
    (pool:pvctie (list (+ x0 total (* 0.6 doff)) y0)
                 (list (+ x0 total (* 0.6 doff)) (- y0 wh2)) "C" th)
    (pool:pvctie (list (+ x0 e2v f2v (* 0.5 gv)) y0)
                 (list (+ x0 e2v f2v (* 0.5 gv)) (- y0 dp2)) "D" th)
    (pool:pvcout (append (pool:bodyquad lline rline bline tline)
                         (list (list x0 ymax)))))
  (setq pv (pool:pvlive 'hs:geo))
  (princ "\nSport bottom -- plan hopper letters; the RED tie is being asked for.")
  (princ "\n(after the first answer, Back re-asks the previous one)")
  (setq ans (pool:askseq
              (list (list 'e2 'NAX "E2 - left end shallow flat" (cdr (assoc "E2" pv)))
                    (list 'f2 'NAX "F2 - left slope" (cdr (assoc "F2" pv)))
                    (list 'g 'ZER "G - deep flat length, 0 = no hopper pad"
                          (cdr (assoc "G" pv)))
                    (list 'f1 'NAX "F1 - right slope" (cdr (assoc "F1" pv)))
                    (list 'e1 'NAX "E1 - right end shallow flat" (cdr (assoc "E1" pv))
                          nil nil nil '(pool:chainrest ans '(e2 f2 g f1) total2))
                    (list 'm 'NAX "M - top side to deep flat" (cdr (assoc "M" pv)))
                    (list 'l 'NAX "L - deep flat width" (cdr (assoc "L" pv)))
                    (list 'k 'SUG "K - deep flat to bottom side"
                          (cdr (assoc "K" pv)) '(m) nil nil
                          '(pool:chainrest ans '(m l) wid2))))
        e2r (pool:sq ans 'e2) f2r (pool:sq ans 'f2) gr (pool:sq ans 'g)
        f1r (pool:sq ans 'f1) e1r (pool:sq ans 'e1)
        mraw (pool:sq ans 'm) lraw (pool:sq ans 'l) kraw (pool:sq ans 'k)
        nopad (and gr (< gr 1.0e-6))
        wh (pool:askh "C - wall height (shallow depth)" (cdr (assoc "C" pv))))
  (pool:pvnote 'wh wh)
  (setq hd (pool:askdeep "D - deep depth" (cdr (assoc "D" pv)) wh))
  (pool:pvnote 'dp hd)
  (pool:pvkill)
  ;; resolve: horizontal chain vs the pool length (G absorbs; the
  ;; no-pad sport fixes G = 0 and splits its residual across F2/F1),
  ;; vertical chain vs the width (L absorbs)
  (if nopad
      (progn
        (setq res (pool:chainfix (list e2r f2r f1r e1r) total -1)
              e2 (car res) f2 (cadr res) f1 (caddr res) e1 (cadddr res)
              g 0.0
              resid (- total e2 f2 f1 e1))
        (if (> (abs resid) 1.0e-6)
            (setq f2 (+ f2 (* 0.5 resid))
                  f1 (+ f1 (* 0.5 resid)))))
      (setq res (pool:chainfix (list e2r f2r gr f1r e1r) total 2)
            e2 (car res) f2 (cadr res) g (caddr res)
            f1 (cadddr res) e1 (nth 4 res)))
  ;; no member of the resolved chain may be negative: floor it and
  ;; trim the largest other member, marking both red below
  (setq cv (pool:chainval (list e2 f2 g f1 e1) total)
        hfx (cadr cv)
        e2 (nth 0 (car cv)) f2 (nth 1 (car cv)) g (nth 2 (car cv))
        f1 (nth 3 (car cv)) e1 (nth 4 (car cv)))
  (if hfx (pool:valnote (strcat "SPORT LENGTHS FAILED - "
                                (pool:fixnames hfx '("E2" "F2" "G" "F1" "E1"))
                                " ADJUSTED, VERIFY")))
  ;; a G that resolves away (NA with the rest filling the length, or
  ;; absorbed to nothing) also collapses to the no-pad V bottom
  (if (< g 1.0e-6) (setq nopad t g 0.0))
  (setq vres (pool:chainfix (list mraw lraw kraw) wid 1)
        cv (pool:chainval vres wid) vres (car cv) vfx (cadr cv)
        m (car vres) l (cadr vres) k (caddr vres)
        gg (pool:hopsportc lline rline bline tline cen e2 f2 g f1 e1 m k))
  (if vfx (pool:valnote (strcat "SPORT WIDTHS FAILED - "
                                (pool:fixnames vfx '("M" "L" "K"))
                                " ADJUSTED, VERIFY")))
  (pool:hopsportdraw gg nopad "POOL" nil)
  ;; profile below, with C and D dims only
  (setq brks (if nopad
                 (list (cons e2 wh) (cons (+ e2 f2) hd) (cons (- total e1) wh))
                 (list (cons e2 wh) (cons (+ e2 f2) hd)
                       (cons (- total e1 f1) hd) (cons (- total e1) wh))))
  (pool:profdraw x0 y0 total wh brks "POOL" nil)
  (setq odl (getvar "CLAYER"))
  (setvar "CLAYER" "DIMENSION")
  ;; plan chains, standard-hopper style
  (foreach tl (append (list (list 'pl 'pobl nil (member 0 hfx))
                            (list 'pobl 'pdfl nil (member 1 hfx)))
                      (if nopad nil (list (list 'pdfl 'pdfr nil (member 2 hfx))))
                      (list (list 'pdfr 'pobr nil (member 3 hfx))
                            (list 'pobr 'pr nil (member 4 hfx))
                            (list 'pdt 'pt t (member 0 vfx))
                            (list 'pdb 'pdt t (member 1 vfx))
                            (list 'pb 'pdb t (member 2 vfx))))
    (pool:dimalg (cadr (assoc (car tl) gg)) (cadr (assoc (cadr tl) gg))
                 (cal:v+ (cal:mid (cadr (assoc (car tl) gg))
                                    (cadr (assoc (cadr tl) gg)))
                          (if (caddr tl) (cadr (assoc 'voff gg))
                              (list 0.0 0.0))))
    (if (cadddr tl) (pool:dimred)))
  (pool:dimalg (list (+ x0 total) y0) (list (+ x0 total) (- y0 wh))
               (list (+ x0 total (* 0.8 doff)) (- y0 (* 0.5 wh))))
  (setq xd (if nopad (+ x0 e2 f2) (+ x0 e2 f2 (* 0.5 g))))
  (pool:dimalg (list xd y0) (list xd (- y0 hd))
               (list (+ xd (* 0.3 doff)) (- y0 (* 0.5 hd))))
  (setvar "CLAYER" odl)
  (setq rows (append
    (list (pool:vrow "SPT E2" e2r (distance (cadr (assoc 'pl gg)) (cadr (assoc 'pobl gg))) 0 hfx)
          (pool:vrow "SPT F2" f2r (distance (cadr (assoc 'pobl gg)) (cadr (assoc 'pdfl gg))) 1 hfx))
    (if nopad nil
        (list (pool:vrow "SPT G" gr (distance (cadr (assoc 'pdfl gg)) (cadr (assoc 'pdfr gg))) 2 hfx)))
    (list (pool:vrow "SPT F1" f1r (distance (cadr (assoc 'pdfr gg)) (cadr (assoc 'pobr gg))) 3 hfx)
          (pool:vrow "SPT E1" e1r (distance (cadr (assoc 'pobr gg)) (cadr (assoc 'pr gg))) 4 hfx)
          (pool:vrow "SPT M" mraw (distance (cadr (assoc 'pdt gg)) (cadr (assoc 'pt gg))) 0 vfx)
          (pool:vrow "SPT L" lraw (distance (cadr (assoc 'pdb gg)) (cadr (assoc 'pdt gg))) 1 vfx)
          (pool:vrow "SPT K" kraw (distance (cadr (assoc 'pb gg)) (cadr (assoc 'pdb gg))) 2 vfx)
          (list "WALL HT C" wh wh)
          (list "DEPTH D" hd hd))))
  rows)

;; Pool-bottom dispatcher for the rectangle.
;; Returns the report rows (nil if skipped).
(defun pool:hopper (quad corners doff th / btype xmin xmax ymin ymax
                                           a b c d cen sres ln xi)
  (if (not (pool:askbottom))
      nil
      (progn
        (setq xmin (apply 'min (mapcar 'car quad))
              xmax (apply 'max (mapcar 'car quad))
              ymin (apply 'min (mapcar 'cadr quad))
              ymax (apply 'max (mapcar 'cadr quad)))
        (command "_.ZOOM" "_Window"
                 (pool:wp (list (- xmin doff) (- ymin doff)))
                 (pool:wp (list (+ xmax doff) (+ ymax doff))))
        (setq btype (pool:askkwf 'btype "Bottom type"
                                 pool:*btypes* pool:*btshown*
                                 "Normal" nil))
        (if (/= btype "Sport")
            (pool:hopnormal quad corners doff th nil btype
                            xmin (- ymin (* 2.2 doff)) t)
            (progn
              (setq a (car quad) b (cadr quad) c (caddr quad) d (cadddr quad)
                    cen (cal:v* (cal:v+ (cal:v+ a b) (cal:v+ c d)) 0.25))
              (pool:hopsport (list a (cal:v- d a)) (list b (cal:v- c b))
                             (list a (cal:v- b a)) (list d (cal:v- c d))
                             cen (distance a b)
                             xmin (- ymin (* 2.2 doff)) ymax
                             doff th))))))

;;; -------------------- side profile -----------------------------------
;;;
;;;  Section view under the plan: waterline across the top, walls of
;;;  height C at both ends, and the bottom running through the given
;;;  break vertices.  Used by the normal hoppers and by the Sport
;;;  bottoms (whose field sheets ARE this profile).

;; Draw the profile outline.  x0/y0 = top-left, total = pool length,
;; wh = wall height, brks = bottom vertices ((dist . depth) ...) from
;; the left wall, left to right.
(defun pool:profdraw (x0 y0 total wh brks lay pvflag / pts prev p)
  (setq pts (append (list (list x0 y0)
                          (list (+ x0 total) y0)
                          (list (+ x0 total) (- y0 wh)))
                    (mapcar '(lambda (p) (list (+ x0 (car p)) (- y0 (cdr p))))
                            (reverse brks))
                    (list (list x0 (- y0 wh))
                          (list x0 y0)))
        prev (car pts))
  (foreach p (cdr pts)
    ;; a break sitting exactly on a wall bottom repeats that point --
    ;; but a COLLECTED profile keeps every segment, even zero-length,
    ;; so the live guide's primitive count never changes as the
    ;; answers move the breaks around
    (if (or (and pvflag pool:*pvcoll*) (> (distance prev p) 1.0e-6))
        (progn
          (pool:hgl prev p lay pvflag)
          ;; remember the real (non-preview) section lines so an L
          ;; pool's plan mirror can leave them alone
          (if (not pvflag)
              (setq pool:*profents* (cons (entlast) pool:*profents*)))))
    (setq prev p)))

;; Line/arc makers used by the shape-specific hopper draws.  Three
;; ways out: the real drawing on layer lay; the old gray-guide preview
;; (pvflag); and, when the live-guide collector is armed, the pvflag
;; path emits a spec primitive instead of an entity -- which is how
;; the bottom guides reshape with every answer.
(defun pool:hgl (p q lay pvflag)
  (cond
    ((and pvflag pool:*pvcoll*) (pool:pvcput (list "LINE" p q)))
    (pvflag (pool:pvadd (pool:pvline p q)))
    (t (pool:line p q lay))))

(defun pool:hga (p mm q lay pvflag)
  (cond
    ((and pvflag pool:*pvcoll*) (pool:pvcput (list "ARC" p mm q)))
    (pvflag
     (pool:arc3p p mm q "POOL-NOTES")
     (pool:pvadd (pool:setcol (entlast) pool:*pv-col*)))
    (t (pool:arc3p p mm q lay))))

;;; ---------------- oval pool bottom (True Oval sheet) -----------------
;;;
;;;  The hopper is a box with a radius (R3) left end, set out along
;;;  the pool axis (arc tip to arc tip):
;;;    H = pool left tip -> hopper tip      E = break -> pool right tip
;;;    G = hopper tip -> hopper right edge  M/K = top/bottom offsets
;;;    R3 = hopper end radius               L = hopper width (CHECK)
;;;    W = hopper flat top, tangent -> right edge (CHECK, = G - R3)
;;;    F = hopper -> slope break (CHECK)    T = straight side (CHECK)
;;;  No left ties (the radius IS the end); the right corners tie to
;;;  the slope-break ends as usual.

(defun pool:hopovalc (quad tipl tipr h g e m k r3 / a b c d cen u v ht hb
                                                    lt re tan brk tt tb tip vc
                                                    tip2)
  (setq a (car quad) b (cadr quad) c (caddr quad) d (cadddr quad)
        cen (cal:v* (cal:v+ (cal:v+ a b) (cal:v+ c d)) 0.25)
        u (pool:unit (cal:v- tipr tipl))
        v (cal:perp u)
        ht (pool:offline d c cen m)
        hb (pool:offline a b cen k)
        lt (list (cal:v+ tipl (cal:v* u h)) v)
        re (list (cal:v+ tipl (cal:v* u (+ h g))) v)
        tan (list (cal:v+ tipl (cal:v* u (+ h r3))) v)
        brk (list (cal:v- tipr (cal:v* u e)) v)
        tt (pool:linex (car tan) (cadr tan) (car ht) (cadr ht))
        tb (pool:linex (car tan) (cadr tan) (car hb) (cadr hb))
        tip (cal:mid (pool:linex (car lt) (cadr lt) (car ht) (cadr ht))
                      (pool:linex (car lt) (cadr lt) (car hb) (cadr hb)))
        ;; M/L/K attach to the hopper's right edge; dim line +12"
        vc (cal:v+ tipl (cal:v* u (+ h g)))
        ;; H/G/F/E chain below the hopper centre by 12" or L/6,
        ;; whichever is closer
        tip2 (cal:v- tip
                      (cal:v* (pool:unit v)
                               (min 12.0
                                    (/ (distance
                                         (pool:linex vc v (car hb) (cadr hb))
                                         (pool:linex vc v (car ht) (cadr ht)))
                                       6.0)))))
  (list (list 'tip tip) (list 'ttop tt) (list 'tbot tb)
        (list 'htr (pool:linex (car re) (cadr re) (car ht) (cadr ht)))
        (list 'hbr (pool:linex (car re) (cadr re) (car hb) (cadr hb)))
        (list 'brkb (pool:linex (car brk) (cadr brk) a (cal:v- b a)))
        (list 'brkt (pool:linex (car brk) (cadr brk) d (cal:v- c d)))
        (list 'ptan (pool:linex tip2 u (car tan) v))
        (list 'pl (pool:linex tip2 u tipl v))
        (list 'phl (pool:linex tip2 u (car lt) (cadr lt)))
        (list 'phr (pool:linex tip2 u (car re) v))
        (list 'pbrk (pool:linex tip2 u (car brk) v))
        (list 'pr (pool:linex tip2 u tipr v))
        (list 'pb (pool:linex vc v a (cal:v- b a)))
        (list 'phb (pool:linex vc v (car hb) (cadr hb)))
        (list 'pht (pool:linex vc v (car ht) (cadr ht)))
        (list 'pt (pool:linex vc v d (cal:v- c d)))
        (list 'voff (cal:v* u pool:*mlkoff*))))

(defun pool:hopovaldraw (gg lay pvflag / tt tb tip htr hbr brkb brkt)
  (setq tt (cadr (assoc 'ttop gg)) tb (cadr (assoc 'tbot gg))
        tip (cadr (assoc 'tip gg))
        htr (cadr (assoc 'htr gg)) hbr (cadr (assoc 'hbr gg))
        brkb (cadr (assoc 'brkb gg)) brkt (cadr (assoc 'brkt gg)))
  (pool:hgl tt htr lay pvflag)
  (pool:hgl tb hbr lay pvflag)
  (pool:hgl htr hbr lay pvflag)
  (pool:hga tt tip tb lay pvflag)
  (pool:hgl brkb brkt lay pvflag)
  (pool:hgl htr brkt lay pvflag)
  (pool:hgl hbr brkb lay pvflag))

;; Guided oval bottom phase.  Returns report rows (nil if skipped).
(defun pool:hopoval (quad tipl tipr doff th / pv gg rows tl odl
                                              h g f e m l k r3 r3raw w tt o
                                              hraw graw fraw eraw mraw lraw kraw
                                              totv hres vres cv hfx vfx r3wbad
                                              ans len2 totv2)
  (if nil                               ; Yes/No now lives in the dispatcher
      nil
      (progn
        ;; The live guide geometry (see "live guide reshaping"): the
        ;; axis chain closes against the tip-to-tip length at every
        ;; answer, the M/L/K chain against the width, and the radius
        ;; end follows R3 / W -- or stays the tangent semicircle of
        ;; whatever hopper width the offsets currently give.
        (defun ho:geo ( / len wid res hv gv ev mv lv kv r3v gg)
          (setq len (distance tipl tipr)
                wid (distance (car quad) (cadddr quad))
                res (pool:pvchain
                      (list (pool:pvdim 'h) (pool:pvdim 'g)
                            (pool:pvdim 'f) (pool:pvdim 'e))
                      (list (* 0.10 len) (* 0.24 len)
                            (* 0.28 len) (* 0.38 len))
                      len)
                hv (car res) gv (cadr res) ev (cadddr res)
                res (pool:pvchain
                      (list (pool:pvdim 'm) (pool:pvdim 'l) (pool:pvdim 'k))
                      (list (* 0.25 wid) (* 0.5 wid) (* 0.25 wid))
                      wid)
                mv (car res) lv (cadr res) kv (caddr res)
                ;; the same precedence the resolver applies below: a
                ;; given R3 wins, else the tangent semicircle of the
                ;; hopper width, and only a collapsed width lets W
                ;; spend the hopper length -- so the end the user
                ;; watches is the end the final draw keeps
                r3v (cond ((pool:pvdim 'r3))
                          ((> lv 1.0e-6) (* 0.5 lv))
                          ((and (pool:pvdim 'w)
                                (> (- gv (pool:pvdim 'w)) 1.0))
                           (- gv (pool:pvdim 'w)))
                          (t (* 0.20 wid)))
                r3v (max (min r3v (* 0.9 gv)) (* 0.02 len))
                gg (pool:hopovalc quad tipl tipr hv gv ev mv kv r3v))
          (pool:pvcopen)
          (pool:hopovaldraw gg "POOL-NOTES" t)
          (pool:pvctie (cadr (assoc 'pl gg)) (cadr (assoc 'phl gg)) "H" th)
          (pool:pvctie (cadr (assoc 'phl gg)) (cadr (assoc 'phr gg)) "G" th)
          (pool:pvctie (cadr (assoc 'phl gg)) (cadr (assoc 'ptan gg)) "R3" th)
          (pool:pvctie (cadr (assoc 'ttop gg)) (cadr (assoc 'htr gg)) "W" th)
          (pool:pvctie (cadr (assoc 'phr gg)) (cadr (assoc 'pbrk gg)) "F" th)
          (pool:pvctie (cadr (assoc 'pbrk gg)) (cadr (assoc 'pr gg)) "E" th)
          (pool:pvctie (cadr (assoc 'pht gg)) (cadr (assoc 'pt gg)) "M" th)
          (pool:pvctie (cadr (assoc 'phb gg)) (cadr (assoc 'pht gg)) "L" th)
          (pool:pvctie (cadr (assoc 'pb gg)) (cadr (assoc 'phb gg)) "K" th)
          (pool:pvctie (cadddr quad) (caddr quad) "T" th)
          (pool:pvcout (append quad (list tipl tipr))))
        (setq pv (pool:pvlive 'ho:geo))
        (princ "\nPool bottom -- offsets along the pool axis; the RED tie is being asked for.")
        (princ "\n(after the first answer, Back re-asks the previous one)")
        ;; the two chain totals -- tip to tip along the pool, wall to
        ;; wall across it -- are worked out BEFORE the questions now,
        ;; so the last letter of each chain can be suggested as it is
        ;; reached rather than only resolved afterwards
        (setq len2 (distance tipl tipr)
              totv (distance
                     (pool:linex (cal:mid (car quad) (caddr quad))
                                 (cal:v- (cadddr quad) (car quad))
                                 (car quad) (cal:v- (cadr quad) (car quad)))
                     (pool:linex (cal:mid (car quad) (caddr quad))
                                 (cal:v- (cadddr quad) (car quad))
                                 (cadddr quad) (cal:v- (caddr quad) (cadddr quad))))
              totv2 totv)
        (setq ans (pool:askseq
                    (list (list 'h 'NAX "H - pool left tip to hopper tip" (cdr (assoc "H" pv)))
                          (list 'g 'NAX "G - hopper length (tip to right edge)" (cdr (assoc "G" pv)))
                          (list 'r3 'NAX "R3 - hopper end radius" (cdr (assoc "R3" pv)))
                          (list 'w 'NAX "W - hopper flat top" (cdr (assoc "W" pv)))
                          (list 'f 'NAX "F - hopper to slope break" (cdr (assoc "F" pv)))
                          (list 'e 'NAX "E - slope break to pool right tip" (cdr (assoc "E" pv))
                                nil nil nil '(pool:chainrest ans '(h g f) len2))
                          (list 'm 'SUG "M - top side to hopper" (cdr (assoc "M" pv)) '(h))
                          (list 'l 'NAX "L - hopper width" (cdr (assoc "L" pv))
                                nil nil nil '(pool:sugsym ans totv2))
                          (list 'k 'SUG "K - hopper to bottom side" (cdr (assoc "K" pv)) '(m h)
                                nil nil '(pool:chainrest ans '(m l) totv2))
                          (list 'tt 'NAX "T - straight side length (check)" (cdr (assoc "T" pv)))))
              hraw (pool:sq ans 'h) graw (pool:sq ans 'g) r3raw (pool:sq ans 'r3)
              w (pool:sq ans 'w) fraw (pool:sq ans 'f) eraw (pool:sq ans 'e)
              mraw (pool:sq ans 'm) lraw (pool:sq ans 'l) kraw (pool:sq ans 'k)
              tt (pool:sq ans 'tt))
        (pool:pvkill)
        ;; resolve against tip-to-tip length and side-to-side width
        ;; (both measured out above, before the questions)
        (setq hres (pool:chainfix (list hraw graw fraw eraw) (distance tipl tipr) 1)
              vres (pool:chainfix (list mraw lraw kraw) totv 1)
              cv (pool:chainval hres (distance tipl tipr))
              hres (car cv) hfx (cadr cv)
              cv (pool:chainval vres totv) vres (car cv) vfx (cadr cv)
              h (car hres) g (cadr hres) f (caddr hres) e (cadddr hres)
              m (car vres) l (cadr vres) k (caddr vres))
        (if hfx (pool:valnote (strcat "BOTTOM LENGTHS FAILED - "
                                      (pool:fixnames hfx '("H" "G" "F" "E"))
                                      " ADJUSTED, VERIFY")))
        (if vfx (pool:valnote (strcat "BOTTOM WIDTHS FAILED - "
                                      (pool:fixnames vfx '("M" "L" "K"))
                                      " ADJUSTED, VERIFY")))
        ;; The hopper's radius end and its flat top close against the
        ;; hopper length:  R3 + W = G.
        ;;   * R3 NA -> half the hopper width the offsets give (L/2),
        ;;     the semicircle end that meets the straight sides
        ;;     tangentially; failing that, whatever W leaves of G
        ;;   * W NA  -> G - R3, i.e. the flat runs from the arc's
        ;;     tangent point to the hopper's right edge
        (setq r3 (cond (r3raw r3raw)
                       ((> l 1.0e-6) (* 0.5 l))
                       (w (- g w))
                       (t (* 0.5 l))))
        (if (< r3 1.0e-6) (setq r3 (* 0.5 l)))
        ;; when BOTH were measured they must close against the hopper
        ;; length: R3 + W = G
        (if (and r3raw w (> (abs (- (+ r3raw w) g)) 0.5))
            (progn
              (setq r3wbad t)
              (pool:valnote "OVAL HOPPER R3 + W DOES NOT CLOSE AGAINST G - VERIFY")))
        (setq gg (pool:hopovalc quad tipl tipr h g e m k r3))
        (pool:hopovaldraw gg "POOL" nil)
        (setq odl (getvar "CLAYER"))
        (setvar "CLAYER" "DIMENSION")
        (foreach tl (list (list 'pl 'phl nil (member 0 hfx))
                          (list 'phl 'phr nil (member 1 hfx))
                          (list 'phr 'pbrk nil (member 2 hfx))
                          (list 'pbrk 'pr nil (member 3 hfx))
                          (list 'phl 'ptan nil r3wbad)
                          (list 'ttop 'htr nil r3wbad)
                          (list 'pht 'pt t (member 0 vfx))
                          (list 'phb 'pht t (member 1 vfx))
                          (list 'pb 'phb t (member 2 vfx)))
          (pool:dimalg (cadr (assoc (car tl) gg)) (cadr (assoc (cadr tl) gg))
                       (cal:v+ (cal:mid (cadr (assoc (car tl) gg))
                                          (cadr (assoc (cadr tl) gg)))
                                (if (caddr tl) (cadr (assoc 'voff gg))
                                    (list 0.0 0.0))))
          (if (cadddr tl) (pool:dimred)))
        (setvar "CLAYER" odl)
        (setq o (pool:circum (cadr (assoc 'ttop gg)) (cadr (assoc 'tip gg))
                             (cadr (assoc 'tbot gg)))
              rows (list
          (pool:vrow "HOP H" hraw (distance (cadr (assoc 'pl gg)) (cadr (assoc 'phl gg))) 0 hfx)
          (pool:vrow "HOP G" graw (distance (cadr (assoc 'phl gg)) (cadr (assoc 'phr gg))) 1 hfx)
          (append (list "HOP R3" r3raw (if o (distance o (cadr (assoc 'tip gg))) r3))
                  (if r3wbad (list t) nil))
          (append (list "HOP W" w (distance (cadr (assoc 'ttop gg)) (cadr (assoc 'htr gg))))
                  (if r3wbad (list t) nil))
          (pool:vrow "HOP F" fraw (distance (cadr (assoc 'phr gg)) (cadr (assoc 'pbrk gg))) 2 hfx)
          (pool:vrow "HOP E" eraw (distance (cadr (assoc 'pbrk gg)) (cadr (assoc 'pr gg))) 3 hfx)
          (pool:vrow "HOP M" mraw (distance (cadr (assoc 'pht gg)) (cadr (assoc 'pt gg))) 0 vfx)
          (pool:vrow "HOP L" lraw (distance (cadr (assoc 'phb gg)) (cadr (assoc 'pht gg))) 1 vfx)
          (pool:vrow "HOP K" kraw (distance (cadr (assoc 'pb gg)) (cadr (assoc 'phb gg))) 2 vfx)
          (list "HOP T" tt (distance (cadddr quad) (caddr quad)))))
        rows)))

;;; ---------------- grecian pool bottom (Square / 6-sided) -------------
;;;
;;;  Square hopper = the rectangle letters (H G F E M L K), anchored
;;;  off the end walls; each hopper left corner ties to BOTH ends of
;;;  its pool corner cut.  The 6-sided hopper cuts the deep pad's left
;;;  corners, and can be measured TWO ways (hex argument):
;;;
;;;    ("Offsets" co) -- offsets from the walls only: every pad edge
;;;      is its pool wall offset inward (left wall by H, top/bottom by
;;;      M/K) and the cut faces are the pool CORNER CUTS offset in by
;;;      co, so every hopper line is PARALLEL to its wall.  Corners
;;;      land wherever adjacent offset lines intersect.
;;;
;;;    ("Letters" w l1 lw) -- the field-sheet letters:
;;;      W  = the top/bottom flat, cut corner to the pad's right edge
;;;      L1 = the left edge length, centred on the pad
;;;      (lw = the resolved hopper width L, so the cut drop per corner
;;;      is (L - L1)/2; X = sqrt((G-W)^2 + ((L-L1)/2)^2) is a CHECK.)
;;;      The flats and the left edge ride their wall-offset lines
;;;      (parallel); the cut faces just CONNECT the corners and need
;;;      not be parallel to anything.
;;;
;;;  Either way the pool cut ends tie to the matching hopper corners.

(defun pool:hopgrecc (pts h g e m k hex / aa bb rb rt cc dd ltp lbp cen p
                                          hl hr ht hb brk hbl htl hbr htr
                                          hlw htl1 hbl1 hc u v hc2 out
                                          tcut bcut dy ct1 ct2 cb1 cb2)
  (setq aa (nth 0 pts) bb (nth 1 pts) rb (nth 2 pts) rt (nth 3 pts)
        cc (nth 4 pts) dd (nth 5 pts) ltp (nth 6 pts) lbp (nth 7 pts)
        cen (list 0.0 0.0))
  (foreach p pts (setq cen (cal:v+ cen p)))
  (setq cen (cal:v* cen 0.125)
        hl (pool:offline lbp ltp cen h)
        hr (pool:offline lbp ltp cen (+ h g))
        ht (pool:offline dd cc cen m)
        hb (pool:offline aa bb cen k)
        brk (pool:offline rb rt cen e)
        hbl (pool:linex (car hl) (cadr hl) (car hb) (cadr hb))
        htl (pool:linex (car hl) (cadr hl) (car ht) (cadr ht))
        hbr (pool:linex (car hr) (cadr hr) (car hb) (cadr hb))
        htr (pool:linex (car hr) (cadr hr) (car ht) (cadr ht))
        hc (cal:v* (cal:v+ (cal:v+ hbl htl) (cal:v+ hbr htr)) 0.25)
        u (cal:v- bb aa)
        v (cal:v- dd aa)
        ;; chain placement: H/G/F/E below the hopper centre by 12" or
        ;; L/6 (whichever is closer); M/L/K 12" right of the hopper
        hc2 (cal:v- hc (cal:v* (pool:unit v)
                                 (min 12.0 (/ (distance hbr htr) 6.0))))
        out (list
          (list 'hbl hbl) (list 'htl htl) (list 'hbr hbr) (list 'htr htr)
          (list 'brkb (pool:linex (car brk) (cadr brk) aa (cal:v- bb aa)))
          (list 'brkt (pool:linex (car brk) (cadr brk) dd (cal:v- cc dd)))
          (list 'aa aa) (list 'dd dd) (list 'ltp ltp) (list 'lbp lbp)
          (list 'pl (pool:linex hc2 u lbp (cal:v- ltp lbp)))
          (list 'phl (pool:linex hc2 u (car hl) (cadr hl)))
          (list 'phr (pool:linex hc2 u (car hr) (cadr hr)))
          (list 'pbrk (pool:linex hc2 u (car brk) (cadr brk)))
          (list 'pr (pool:linex hc2 u rb (cal:v- rt rb)))
          (list 'pb (pool:linex (car hr) (cadr hr) aa (cal:v- bb aa)))
          (list 'phb hbr)
          (list 'pht htr)
          (list 'pt (pool:linex (car hr) (cadr hr) dd (cal:v- cc dd)))
          (list 'voff (cal:v* (pool:unit u) pool:*mlkoff*))))
  (if hex
      (progn
        (if (= (car hex) "Offsets")
            ;; cut faces = the pool corner cuts offset inward by co;
            ;; corners at the intersections with the adjacent offsets
            (setq tcut (pool:offline ltp dd cen (cadr hex))
                  bcut (pool:offline lbp aa cen (cadr hex))
                  ct1 (pool:linex (car tcut) (cadr tcut) (car ht) (cadr ht))
                  ct2 (pool:linex (car tcut) (cadr tcut) (car hl) (cadr hl))
                  cb1 (pool:linex (car bcut) (cadr bcut) (car hb) (cadr hb))
                  cb2 (pool:linex (car bcut) (cadr bcut) (car hl) (cadr hl)))
            ;; sheet letters: cut corners W back from the pad's right
            ;; edge along the flats, the left edge L1 long centred on
            ;; the pad; the faces connect them (no parallelism forced)
            (setq hlw (pool:offline lbp ltp cen (+ h (- g (cadr hex))))
                  dy (* 0.5 (- (cadddr hex) (caddr hex)))
                  htl1 (pool:offline dd cc cen (+ m dy))
                  hbl1 (pool:offline aa bb cen (+ k dy))
                  ct1 (pool:linex (car hlw) (cadr hlw) (car ht) (cadr ht))
                  ct2 (pool:linex (car hl) (cadr hl) (car htl1) (cadr htl1))
                  cb1 (pool:linex (car hlw) (cadr hlw) (car hb) (cadr hb))
                  cb2 (pool:linex (car hl) (cadr hl) (car hbl1) (cadr hbl1))))
        (setq out (append out (list (list 'ct1 ct1) (list 'ct2 ct2)
                                    (list 'cb1 cb1) (list 'cb2 cb2))))))
  out)

(defun pool:hopgrecdraw (gg lay six pvflag / hbl htl hbr htr brkb brkt
                                             aa dd ltp lbp ct1 ct2 cb1 cb2)
  (setq hbl (cadr (assoc 'hbl gg)) htl (cadr (assoc 'htl gg))
        hbr (cadr (assoc 'hbr gg)) htr (cadr (assoc 'htr gg))
        brkb (cadr (assoc 'brkb gg)) brkt (cadr (assoc 'brkt gg))
        aa (cadr (assoc 'aa gg)) dd (cadr (assoc 'dd gg))
        ltp (cadr (assoc 'ltp gg)) lbp (cadr (assoc 'lbp gg)))
  (pool:hgl htr hbr lay pvflag)
  (pool:hgl brkb brkt lay pvflag)
  (pool:hgl htr brkt lay pvflag)
  (pool:hgl hbr brkb lay pvflag)
  (if six
      (progn
        (setq ct1 (cadr (assoc 'ct1 gg)) ct2 (cadr (assoc 'ct2 gg))
              cb1 (cadr (assoc 'cb1 gg)) cb2 (cadr (assoc 'cb2 gg)))
        (pool:hgl ct1 htr lay pvflag)
        (pool:hgl cb1 hbr lay pvflag)
        (pool:hgl ct2 cb2 lay pvflag)
        (pool:hgl ct2 ct1 lay pvflag)
        (pool:hgl cb2 cb1 lay pvflag)
        (pool:hgl dd ct1 lay pvflag)
        (pool:hgl ltp ct2 lay pvflag)
        (pool:hgl aa cb1 lay pvflag)
        (pool:hgl lbp cb2 lay pvflag))
      (progn
        (pool:hgl htl htr lay pvflag)
        (pool:hgl hbl hbr lay pvflag)
        (pool:hgl htl hbl lay pvflag)
        (pool:hgl dd htl lay pvflag)
        (pool:hgl ltp htl lay pvflag)
        (pool:hgl aa hbl lay pvflag)
        (pool:hgl lbp hbl lay pvflag))))

;; Guided grecian bottom phase.  Returns report rows (nil if skipped).
(defun pool:hopgrec (pts doff th / htype six mode pv gg rows tl odl
                                   h g f e m l k w l1 x co coraw xcal sixbad
                                   hraw graw fraw eraw mraw lraw kraw
                                   cen p u vv toth totv hres vres cv hfx vfx ans
                                   mm ud proj toth2 totv2)
  (if nil                               ; Yes/No now lives in the dispatcher
      nil
      (progn
        ;; the bracket is exactly the keyword list (STANDARDS section
        ;; 1 rule 1): a click on "SIX-sided" sent text initget could
        ;; not accept, so the explanation moved into the question
        (setq htype (pool:askkwf 'htype "Hopper type (SIX = six-sided)"
                                 "Square SIX" "Square/SIX"
                                 "Square" nil)
              six (= htype "SIX"))
        ;; a six-sided deep end can be taped two ways: offsets shot
        ;; from every wall (cut faces parallel to the pool cuts), or
        ;; the sheet letters W / X / L / L1 / G / M / K
        (if six
            (setq mode (pool:askkwf 'hmode "SIX-sided corners measured by"
                                    "Offsets Letters" "Offsets/Letters"
                                    "Offsets" nil)))
        ;; The live guide geometry (see "live guide reshaping"): the
        ;; chain closes against the end-wall-to-end-wall total at every
        ;; answer, and the six-sided corner letters move their own cut
        ;; faces as they come in.
        (defun hg:geo ( / len wid gcen gu p2 gth gtv res
                          hv gv ev mv lv kv hx gg)
          (setq len (distance (nth 0 pts) (nth 1 pts))
                wid (distance (nth 0 pts) (nth 5 pts))
                gcen (list 0.0 0.0))
          (foreach p2 pts (setq gcen (cal:v+ gcen p2)))
          (setq gcen (cal:v* gcen 0.125)
                gu (cal:v- (nth 1 pts) (nth 0 pts))
                gth (distance
                      (pool:linex gcen gu (nth 7 pts)
                                  (cal:v- (nth 6 pts) (nth 7 pts)))
                      (pool:linex gcen gu (nth 2 pts)
                                  (cal:v- (nth 3 pts) (nth 2 pts))))
                gtv (distance
                      (pool:linex gcen (cal:v- (nth 5 pts) (nth 0 pts))
                                  (nth 0 pts)
                                  (cal:v- (nth 1 pts) (nth 0 pts)))
                      (pool:linex gcen (cal:v- (nth 5 pts) (nth 0 pts))
                                  (nth 5 pts)
                                  (cal:v- (nth 4 pts) (nth 5 pts))))
                res (pool:pvchain
                      (list (pool:pvdim 'h) (pool:pvdim 'g)
                            (pool:pvdim 'f) (pool:pvdim 'e))
                      (list (* 0.10 len) (* 0.20 len)
                            (* 0.32 len) (* 0.38 len))
                      gth)
                hv (car res) gv (cadr res) ev (cadddr res)
                res (pool:pvchain
                      (list (pool:pvdim 'm) (pool:pvdim 'l) (pool:pvdim 'k))
                      (list (* 0.27 wid) (* 0.46 wid) (* 0.27 wid))
                      gtv)
                mv (car res) lv (cadr res) kv (caddr res)
                hx (cond
                     ((not six) nil)
                     ((= mode "Offsets")
                      (list "Offsets" (cond ((pool:pvdim 'co)) (hv))))
                     (t (list "Letters"
                              ;; clamped the way the resolver will
                              ;; clamp them, so a W or L1 typo cannot
                              ;; draw a preview that crosses itself
                              (min (cond ((pool:pvdim 'w)) ((* 0.12 len)))
                                   gv)
                              (min (cond ((pool:pvdim 'l1)) ((* 0.26 wid)))
                                   lv)
                              lv)))
                gg (pool:hopgrecc pts hv gv ev mv kv hx))
          (pool:pvcopen)
          (pool:hopgrecdraw gg "POOL-NOTES" six t)
          (pool:pvctie (cadr (assoc 'pl gg)) (cadr (assoc 'phl gg)) "H" th)
          (pool:pvctie (cadr (assoc 'phl gg)) (cadr (assoc 'phr gg)) "G" th)
          (pool:pvctie (cadr (assoc 'phr gg)) (cadr (assoc 'pbrk gg)) "F" th)
          (pool:pvctie (cadr (assoc 'pbrk gg)) (cadr (assoc 'pr gg)) "E" th)
          (pool:pvctie (cadr (assoc 'pht gg)) (cadr (assoc 'pt gg)) "M" th)
          (pool:pvctie (cadr (assoc 'phb gg)) (cadr (assoc 'pht gg)) "L" th)
          (pool:pvctie (cadr (assoc 'pb gg)) (cadr (assoc 'phb gg)) "K" th)
          (if six
              (if (= mode "Offsets")
                  (pool:pvctie
                    (cal:mid (cadr (assoc 'dd gg)) (cadr (assoc 'ltp gg)))
                    (cal:mid (cadr (assoc 'ct2 gg)) (cadr (assoc 'ct1 gg)))
                    "CUT" th)
                  (progn
                    (pool:pvctie (cadr (assoc 'ct1 gg))
                                 (cadr (assoc 'htr gg)) "W" th)
                    (pool:pvctie (cadr (assoc 'ct2 gg))
                                 (cadr (assoc 'cb2 gg)) "L1" th)
                    (pool:pvctie (cadr (assoc 'ct2 gg))
                                 (cadr (assoc 'ct1 gg)) "X" th))))
          (pool:pvcout pts))
        (setq pv (pool:pvlive 'hg:geo))
        (princ "\nPool bottom -- offsets from the end walls; the RED tie is being asked for.")
        (princ "\n(after the first answer, Back re-asks the previous one)")
        ;; wall-to-wall totals through the pool centre, worked out
        ;; BEFORE the questions so the last letter of each chain can be
        ;; suggested as it is reached rather than only resolved after
        (setq cen (list 0.0 0.0))
        (foreach p pts (setq cen (cal:v+ cen p)))
        (setq cen (cal:v* cen 0.125)
              u (cal:v- (nth 1 pts) (nth 0 pts))
              vv (cal:v- (nth 5 pts) (nth 0 pts))
              toth (distance
                     (pool:linex cen u (nth 7 pts) (cal:v- (nth 6 pts) (nth 7 pts)))
                     (pool:linex cen u (nth 2 pts) (cal:v- (nth 3 pts) (nth 2 pts))))
              totv (distance
                     (pool:linex cen vv (nth 0 pts) (cal:v- (nth 1 pts) (nth 0 pts)))
                     (pool:linex cen vv (nth 5 pts) (cal:v- (nth 4 pts) (nth 5 pts))))
              toth2 toth totv2 totv)
        (setq ans (pool:askseq
                    (append
                      (list (list 'h 'NAX "H - left end to hopper" (cdr (assoc "H" pv)))
                            (list 'g 'NAX "G - hopper length" (cdr (assoc "G" pv))))
                      (cond
                        ((not six) nil)
                        ((= mode "Offsets")
                         (list (list 'co 'NAX
                                     "Cut faces - offset in from the pool corner cuts (NA = H)"
                                     (cdr (assoc "CUT" pv)))))
                        (t
                         (list (list 'w 'REQ "W - top/bottom flat, cut corner to hopper end"
                                     (cdr (assoc "W" pv)))
                               (list 'l1 'REQ "L1 - hopper left edge length"
                                     (cdr (assoc "L1" pv)))
                               (list 'x 'NAX "X - hopper cut face length (check)"
                                     (cdr (assoc "X" pv))))))
                      (list (list 'f 'NAX "F - hopper to slope break" (cdr (assoc "F" pv)))
                            (list 'e 'NAX "E - slope break to right end" (cdr (assoc "E" pv))
                                  nil nil nil '(pool:chainrest ans '(h g f) toth2))
                            (list 'm 'SUG "M - top side to hopper" (cdr (assoc "M" pv)) '(h))
                            (list 'l 'NAX "L - hopper width" (cdr (assoc "L" pv))
                                  nil nil nil '(pool:sugsym ans totv2))
                            (list 'k 'SUG "K - hopper to bottom side"
                                  (cdr (assoc "K" pv)) '(m h) nil nil
                                  '(pool:chainrest ans '(m l) totv2)))))
              hraw (pool:sq ans 'h) graw (pool:sq ans 'g)
              coraw (pool:sq ans 'co)
              w (pool:sq ans 'w) l1 (pool:sq ans 'l1) x (pool:sq ans 'x)
              fraw (pool:sq ans 'f) eraw (pool:sq ans 'e)
              mraw (pool:sq ans 'm) lraw (pool:sq ans 'l) kraw (pool:sq ans 'k))
        (pool:pvkill)
        ;; resolve against the wall-to-wall totals measured out above
        (setq hres (pool:chainfix (list hraw graw fraw eraw) toth 1)
              vres (pool:chainfix (list mraw lraw kraw) totv 1)
              cv (pool:chainval hres toth) hres (car cv) hfx (cadr cv)
              cv (pool:chainval vres totv) vres (car cv) vfx (cadr cv)
              h (car hres) g (cadr hres) f (caddr hres) e (cadddr hres)
              m (car vres) l (cadr vres) k (caddr vres))
        (if hfx (pool:valnote (strcat "BOTTOM LENGTHS FAILED - "
                                      (pool:fixnames hfx '("H" "G" "F" "E"))
                                      " ADJUSTED, VERIFY")))
        (if vfx (pool:valnote (strcat "BOTTOM WIDTHS FAILED - "
                                      (pool:fixnames vfx '("M" "L" "K"))
                                      " ADJUSTED, VERIFY")))
        ;; six-sided closure checks, per input method
        (if (and six (= mode "Offsets"))
            (setq co (if coraw coraw h)))
        (if (and six (= mode "Letters"))
            (progn
              (if (> w g)
                  (progn (setq w g sixbad t)
                         (pool:valnote "HOPPER W LONGER THAN G - ADJUSTED")))
              (if (> l1 l)
                  (progn (setq l1 l sixbad t)
                         (pool:valnote "HOPPER L1 LONGER THAN L - ADJUSTED")))
              (setq xcal (sqrt (+ (* (- g w) (- g w))
                                  (* (* 0.5 (- l l1)) (* 0.5 (- l l1))))))
              (if (and x (> (abs (- x xcal)) 0.5))
                  (progn (setq sixbad t)
                         (pool:valnote "HOPPER CUT X DOES NOT CLOSE AGAINST W/L1 - VERIFY")))))
        (setq gg (pool:hopgrecc pts h g e m k
                                (cond
                                  ((not six) nil)
                                  ((= mode "Offsets") (list "Offsets" co))
                                  (t (list "Letters" w l1 l)))))
        (pool:hopgrecdraw gg "POOL" six nil)
        (setq odl (getvar "CLAYER"))
        (setvar "CLAYER" "DIMENSION")
        (foreach tl (list (list 'pl 'phl nil (member 0 hfx))
                          (list 'phl 'phr nil (member 1 hfx))
                          (list 'phr 'pbrk nil (member 2 hfx))
                          (list 'pbrk 'pr nil (member 3 hfx))
                          (list 'pht 'pt t (member 0 vfx))
                          (list 'phb 'pht t (member 1 vfx))
                          (list 'pb 'phb t (member 2 vfx)))
          (pool:dimalg (cadr (assoc (car tl) gg)) (cadr (assoc (cadr tl) gg))
                       (cal:v+ (cal:mid (cadr (assoc (car tl) gg))
                                          (cadr (assoc (cadr tl) gg)))
                                (if (caddr tl) (cadr (assoc 'voff gg))
                                    (list 0.0 0.0))))
          (if (cadddr tl) (pool:dimred)))
        (if six
            (if (= mode "Offsets")
                ;; one offset dim per cut face, square off the pool
                ;; cut -- hopper cut letters read in SIDE STANDARD,
                ;; per the reference sheet
                (foreach tl (list (list 'ct1 'ct2 'dd 'ltp)
                                  (list 'cb1 'cb2 'aa 'lbp))
                  (setq mm (cal:mid (cadr (assoc (car tl) gg))
                                     (cadr (assoc (cadr tl) gg)))
                        ud (pool:unit (cal:v- (cadr (assoc (cadddr tl) gg))
                                               (cadr (assoc (caddr tl) gg))))
                        proj (cal:v+ (cadr (assoc (caddr tl) gg))
                                      (cal:v* ud (cal:dot
                                        (cal:v- mm (cadr (assoc (caddr tl) gg)))
                                        ud))))
                  (pool:dimalgs proj mm (cal:mid proj mm))
                  (if sixbad (pool:dimred)))
                ;; the sheet letters: W flat, L1 left edge, X on a
                ;; face -- all SIDE STANDARD, per the reference sheet
                (progn
                  (pool:dimalgs (cadr (assoc 'ct1 gg)) (cadr (assoc 'htr gg))
                                (cal:mid (cadr (assoc 'ct1 gg)) (cadr (assoc 'htr gg))))
                  (if sixbad (pool:dimred))
                  (pool:dimalgs (cadr (assoc 'ct2 gg)) (cadr (assoc 'cb2 gg))
                                (cal:mid (cadr (assoc 'ct2 gg)) (cadr (assoc 'cb2 gg))))
                  (if sixbad (pool:dimred))
                  (pool:dimalgs (cadr (assoc 'cb2 gg)) (cadr (assoc 'cb1 gg))
                                (cal:mid (cadr (assoc 'cb2 gg)) (cadr (assoc 'cb1 gg))))
                  (if sixbad (pool:dimred)))))
        (setvar "CLAYER" odl)
        (setq rows (list
          (pool:vrow "HOP H" hraw (distance (cadr (assoc 'pl gg)) (cadr (assoc 'phl gg))) 0 hfx)
          (pool:vrow "HOP G" graw (distance (cadr (assoc 'phl gg)) (cadr (assoc 'phr gg))) 1 hfx)
          (pool:vrow "HOP F" fraw (distance (cadr (assoc 'phr gg)) (cadr (assoc 'pbrk gg))) 2 hfx)
          (pool:vrow "HOP E" eraw (distance (cadr (assoc 'pbrk gg)) (cadr (assoc 'pr gg))) 3 hfx)
          (pool:vrow "HOP M" mraw (distance (cadr (assoc 'pht gg)) (cadr (assoc 'pt gg))) 0 vfx)
          (pool:vrow "HOP L" lraw (distance (cadr (assoc 'phb gg)) (cadr (assoc 'pht gg))) 1 vfx)
          (pool:vrow "HOP K" kraw (distance (cadr (assoc 'pb gg)) (cadr (assoc 'phb gg))) 2 vfx)))
        (if six
            (setq rows (append rows
              (if (= mode "Offsets")
                  ;; actual = the drawn face's true perpendicular
                  ;; offset from the pool's corner cut
                  (progn
                    (setq mm (cal:mid (cadr (assoc 'ct2 gg)) (cadr (assoc 'ct1 gg)))
                          ud (pool:unit (cal:v- (cadr (assoc 'ltp gg))
                                                 (cadr (assoc 'dd gg))))
                          proj (cal:v+ (cadr (assoc 'dd gg))
                                        (cal:v* ud (cal:dot
                                          (cal:v- mm (cadr (assoc 'dd gg))) ud))))
                    (list (list "HOP CUT OFF" coraw (distance proj mm))))
                  (list
                    (append (list "HOP W" w (distance (cadr (assoc 'ct1 gg))
                                                      (cadr (assoc 'htr gg))))
                            (if sixbad (list t) nil))
                    (append (list "HOP L1" l1 (distance (cadr (assoc 'ct2 gg))
                                                        (cadr (assoc 'cb2 gg))))
                            (if sixbad (list t) nil))
                    (append (list "HOP X" x (distance (cadr (assoc 'ct2 gg))
                                                      (cadr (assoc 'ct1 gg))))
                            (if sixbad (list t) nil)))))))
        rows)))

;; Body quad spanning two end lines and the two side lines: the frame
;; the special bottoms measure their chain off for the shapes whose
;; ends are not plain corners.
(defun pool:bodyquad (lline rline bline tline)
  (list (pool:linex (car lline) (cadr lline) (car bline) (cadr bline))
        (pool:linex (car rline) (cadr rline) (car bline) (cadr bline))
        (pool:linex (car rline) (cadr rline) (car tline) (cadr tline))
        (pool:linex (car lline) (cadr lline) (car tline) (cadr tline))))

;; Bottom-type dispatchers for oval and grecian pools.  Normal keeps
;; each shape's own field sheet (radius end / corner cuts); the four
;; special bottoms are the standard chain measured off the body, so
;; they work here too.

(defun pool:hopovaldsp (quad tipl tipr doff th / btype u v sres p xi
                                                 lline rline bline tline)
  (if (not (pool:askbottom))
      nil
      (progn
        (setq btype (pool:askkwf 'btype "Bottom type"
                                 pool:*btypes* pool:*btshown*
                                 "Normal" nil))
        (setq u (pool:unit (cal:v- tipr tipl))
              v (cal:perp u)
              lline (list tipl v)
              rline (list tipr v)
              bline (list (car quad) (cal:v- (cadr quad) (car quad)))
              tline (list (cadddr quad)
                          (cal:v- (caddr quad) (cadddr quad))))
        (cond
          ((= btype "Normal") (pool:hopoval quad tipl tipr doff th))
          ;; the oval's ends are arcs, so there are no left corners to
          ;; tie the deep end back to
          ((/= btype "Sport")
           (pool:hopnormal (pool:bodyquad lline rline bline tline)
                           pool:*sq4* doff th nil btype
                           (min (car tipl) (car tipr))
                           (- (apply 'min (mapcar 'cadr quad)) (* 2.2 doff))
                           nil))
          (t
            (pool:hopsport (list tipl v) (list tipr v)
                             (list (car quad) (cal:v- (cadr quad) (car quad)))
                             (list (cadddr quad)
                                   (cal:v- (caddr quad) (cadddr quad)))
                             (cal:v* (cal:v+ (cal:v+ (car quad) (cadr quad))
                                               (cal:v+ (caddr quad) (cadddr quad)))
                                      0.25)
                             (distance tipl tipr)
                             (min (car tipl) (car tipr))
                             (- (apply 'min (mapcar 'cadr quad)) (* 2.2 doff))
                             (apply 'max (mapcar 'cadr quad))
                             doff th))))))

(defun pool:hopgrecdsp (pts doff th / btype cen p u pl pr sres xi ln
                                      lline rline bline tline)
  (if (not (pool:askbottom))
      nil
      (progn
        (setq btype (pool:askkwf 'btype "Bottom type"
                                 pool:*btypes* pool:*btshown*
                                 "Normal" nil))
        (setq cen (list 0.0 0.0))
        (foreach p pts (setq cen (cal:v+ cen p)))
        (setq cen (cal:v* cen 0.125)
              u (cal:v- (nth 1 pts) (nth 0 pts))
              lline (list (nth 7 pts) (cal:v- (nth 6 pts) (nth 7 pts)))
              rline (list (nth 2 pts) (cal:v- (nth 3 pts) (nth 2 pts)))
              bline (list (nth 0 pts) (cal:v- (nth 1 pts) (nth 0 pts)))
              tline (list (nth 5 pts) (cal:v- (nth 4 pts) (nth 5 pts)))
              pl (pool:linex cen u (car lline) (cadr lline))
              pr (pool:linex cen u (car rline) (cadr rline)))
        (cond
          ((= btype "Normal") (pool:hopgrec pts doff th))
          ((/= btype "Sport")
           ;; the deep end ties to BOTH ends of each left corner cut,
           ;; exactly as the Grecian's own hopper does
           (pool:hopnormal (pool:bodyquad lline rline bline tline)
                           (list (list "Ends" (nth 7 pts) (nth 0 pts))
                                 (list "Square" 0.0)
                                 (list "Square" 0.0)
                                 (list "Ends" (nth 5 pts) (nth 6 pts)))
                           doff th nil btype
                           (apply 'min (mapcar 'car pts))
                           (- (apply 'min (mapcar 'cadr pts)) (* 2.2 doff))
                           t))
          (t
            (pool:hopsport lline rline bline tline
                             cen (distance pl pr)
                             (apply 'min (mapcar 'car pts))
                             (- (apply 'min (mapcar 'cadr pts)) (* 2.2 doff))
                             (apply 'max (mapcar 'cadr pts))
                             doff th))))))

;;; -------------------- oval ends --------------------------------------
;;;
;;;  R1/R2 are TRUE arc radii: each end arc springs from the two end
;;;  corners (chord c = the end length) and bulges past them by the
;;;  sagitta  s = R - sqrt(R^2 - (c/2)^2).  Dimensioning the drawn arc
;;;  therefore reads back the radius that was typed in.

;; Bulge of an arc of radius r spanning a chord c.  An r smaller than
;; the chord's half cannot reach across it, so it is clamped to the
;; semicircle (the tightest arc that end can have).
(defun pool:sag (r c / half)
  (setq half (* 0.5 c))
  (if (<= r half) half (- r (sqrt (- (* r r) (* half half))))))

;; The inverse: radius of the arc that bulges s past a chord c.
(defun pool:sagr (s c / half)
  (setq half (* 0.5 c))
  (if (<= s 1.0e-9) nil (/ (+ (* s s) (* half half)) (* 2.0 s))))

;; The straight body the overall leaves -- the same chain read the
;; other way, for the sheet that gives the overall and the width but
;; never taped the sides.  Each end spends its own bulge out of the
;; overall and what is left over is the side.  A radius that WAS given
;; sets its own bulge; one that was not is taken TANGENT to the box the
;; pool sits in -- an arc that meets the sides square, i.e. the
;; semicircle s = c/2, which is exactly what a true oval is.  Returns
;; nil when the overall does not reach past the two ends at all.
(defun pool:ovalaxis (totl lraw rraw lc rc / v)
  (if totl
      (progn
        (setq v (- totl
                   (+ (if lraw (pool:sag lraw lc) (* 0.5 lc))
                      (if rraw (pool:sag rraw rc) (* 0.5 rc)))))
        (if (> v 1.0e-6) v nil))))

;; Resolve the two end arcs against the overall length.  The overall
;; closes the chain  s_left + axis + s_right = TOTAL, so any one of
;; TOTAL / R1 / R2 may be NA:
;;   * both radii NA -> the remainder splits evenly between the ends,
;;     i.e. both arcs the same -- exactly what an in-square oval is;
;;   * one radius NA -> it takes the remainder;
;;   * TOTAL NA      -> it is computed from the two radii.
;; lc/rc are the end lengths (chords).  Returns (lrad rrad sl sr total notes).
(defun pool:ovalends (totl lraw rraw axis lc rc / sl sr left notes lr rr)
  (if (and lraw rraw)
      (setq sl (pool:sag lraw lc)
            sr (pool:sag rraw rc))
      (progn
        (setq left (- totl axis))       ; length left over for the ends
        (cond
          ((and (null lraw) (null rraw))
           (setq sl (* 0.5 left) sr (* 0.5 left)))
          ((null lraw)
           (setq sr (pool:sag rraw rc) sl (- left sr)))
          (t
           (setq sl (pool:sag lraw lc) sr (- left sl))))))
  ;; a bulge that came out at or below zero means the overall and the
  ;; body disagree; fall back to the semicircle and say so
  (if (<= sl 1.0e-6)
      (setq sl (* 0.5 lc)
            notes (cons "LEFT END DOES NOT FIT THE TOTAL LENGTH - SEMICIRCLE USED" notes)))
  (if (<= sr 1.0e-6)
      (setq sr (* 0.5 rc)
            notes (cons "RIGHT END DOES NOT FIT THE TOTAL LENGTH - SEMICIRCLE USED" notes)))
  ;; a radius tighter than the end is half its width was clamped above
  (if (and lraw (< lraw (- (* 0.5 lc) 1.0e-6)))
      (setq notes (cons "LEFT RADIUS SMALLER THAN HALF THE END - SEMICIRCLE USED" notes)))
  (if (and rraw (< rraw (- (* 0.5 rc) 1.0e-6)))
      (setq notes (cons "RIGHT RADIUS SMALLER THAN HALF THE END - SEMICIRCLE USED" notes)))
  (setq lr (pool:sagr sl lc)
        rr (pool:sagr sr rc))
  (list lr rr sl sr (+ sl axis sr) notes))

;;; -------------------- rectangle / oval flow --------------------------

;; Full guided flow for the quad-based pools: preview, prompts, fit,
;; draw, dimension and report.  Caller handles sysvars/undo/zoom.
(defun pool:quadflow (ptype / oldclay pv arcs
                             tp bo le ri dac dbd totl lrad rrad tpna bona
                             corners cmode anycut cc prevty prevsz lbl
                             gq gcorners xmeas xg tm hl val m rpa rpb pass
                             ans xitems cc2
                             fitres quad failed a b c d cen meas notes tri
                             doff th endoff pr odim k
                             midl midr ml mr tipl tipr
                             ores lrfit rrfit larc rarc
                             allpts xmax ymax ymin rows rbox mprims)
  (setq oldclay (getvar "CLAYER"))

  ;; The live guide geometry (see "live guide reshaping"): each side
  ;; borrows its unanswered partner, then the 360 x 180 nominal, and
  ;; the quad is fit the way the final fit will hold it -- so once the
  ;; cross dims start coming in, the guide leans out of square in
  ;; front of the user.  gq keeps the quad the guide sits on: the
  ;; corner-treatment guides and the cross-dim reference points ride
  ;; the same shape the user is looking at.
  (defun qf:geo ( / bov tpv lev riv xac xbd q qa qb qc qd cen2 sc hgt
                    spec km k tm s cl cr axis ml2 mr2 midl2 midr2
                    extl extr left tot lr rr tipl2 tipr2 o1 o2)
    (setq bov (cond ((pool:pvdim 'bo)) ((pool:pvdim 'tp)) (360.0))
          tpv (cond ((pool:pvdim 'tp)) ((pool:pvdim 'bo)) (360.0))
          lev (cond ((pool:pvdim 'le)) ((pool:pvdim 'ri))
                    ((* 0.25 (+ bov tpv))))
          riv (cond ((pool:pvdim 'ri)) ((pool:pvdim 'le)) (lev)))
    ;; cross dims answered so far, averaged per diagonal like the
    ;; bootstrap pool:rawavg
    (if cmode
        (progn
          (setq k 0)
          (foreach tm (pool:crosstemplate cmode)
            (setq s (pool:pvdim (read (strcat "x" (itoa k)))))
            (if s
                (if (eq (car tm) 'ac)
                    (setq xac (if xac (* 0.5 (+ xac s)) s))
                    (setq xbd (if xbd (* 0.5 (+ xbd s)) s))))
            (setq k (1+ k)))))
    (setq q (pool:fitsides bov tpv lev riv xac xbd))
    (if (null q)
        (setq q (list (list 0.0 0.0) (list bov 0.0)
                      (list bov (* 0.5 (+ lev riv))) (list 0.0 lev))))
    (setq gq q
          qa (car q) qb (cadr q) qc (caddr q) qd (cadddr q)
          cen2 (cal:v* (cal:v+ (cal:v+ qa qb) (cal:v+ qc qd)) 0.25)
          sc (/ (max bov tpv lev riv) 360.0)
          hgt (* 12.0 sc)
          spec (list (list "LINE" qa qb) (list "LINE" qb qc)
                     (list "LINE" qd qc) (list "LINE" qd qa))
          km (list (list 'ab 0) (list 'bc 1) (list 'dc 2) (list 'da 3)
                   (list 'lA 4) (list 'lB 5) (list 'lC 6) (list 'lD 7)))
    (foreach tm (list (list qa "A") (list qb "B") (list qc "C")
                      (list qd "D"))
      (setq spec (append spec
                   (list (list "TEXT"
                               (cal:v+ (car tm)
                                        (cal:v* (pool:unit
                                                   (cal:v- (car tm) cen2))
                                                 (* 20.0 sc)))
                               hgt (cadr tm))))))
    (if (= ptype "Oval")
        (progn
          ;; ends resolved the way the final pool:ovalends will: a
          ;; radius sets its own bulge (semicircle when NA), and a
          ;; given overall re-spends what the body leaves over
          (setq tot (pool:pvdim 'tot) lr (pool:pvdim 'lr)
                rr (pool:pvdim 'rr)
                midl2 (cal:mid qa qd) midr2 (cal:mid qb qc)
                cl (distance qa qd) cr (distance qb qc)
                axis (distance midl2 midr2)
                ml2 (pool:unit (cal:perp (cal:v- qd qa)))
                mr2 (pool:unit (cal:perp (cal:v- qc qb))))
          (if (< (cal:dot (cal:v- midl2 cen2) ml2) 0.0)
              (setq ml2 (cal:v* ml2 -1.0)))
          (if (< (cal:dot (cal:v- midr2 cen2) mr2) 0.0)
              (setq mr2 (cal:v* mr2 -1.0)))
          (setq extl (if lr (pool:sag lr cl) (* 0.5 cl))
                extr (if rr (pool:sag rr cr) (* 0.5 cr)))
          (if tot
              (progn
                (setq left (- tot axis))
                (cond
                  ((and lr rr) nil)     ; both pinned; the total is a check
                  ((and (null lr) (null rr))
                   (if (> left 1.0e-6) (setq extl (* 0.5 left) extr extl)))
                  ((null lr)
                   (if (> (- left extr) 1.0e-6) (setq extl (- left extr))))
                  (t
                   (if (> (- left extl) 1.0e-6)
                       (setq extr (- left extl)))))))
          ;; the radius lines run from each arc's centre to its tip, so
          ;; they read as the true radius that is being asked for
          (setq tipl2 (cal:v+ midl2 (cal:v* ml2 extl))
                tipr2 (cal:v+ midr2 (cal:v* mr2 extr))
                o1 (pool:circum qa tipl2 qd)
                o2 (pool:circum qb tipr2 qc)
                spec (append spec
                       (list (list "LINED" (if o1 o1 midl2) tipl2)
                             (list "LINED" (if o2 o2 midr2) tipr2)
                             (list "ARC" qa tipl2 qd)
                             (list "ARC" qb tipr2 qc)
                             (list "LINED" tipl2 tipr2)))
                km (append km (list (list 'lrad 8 10) (list 'rrad 9 11)
                                    (list 'tot 12))))))
    (list spec km (pool:pvspecbox spec)))

  ;; what the generic reshape cannot move: the corner-treatment guides
  ;; are recreated on the live quad, and the cross-dim guide lines are
  ;; walked onto their reference points on it
  (defun qf:more ( / k tm)
    (if (and anycut gcorners) (setq pv (pool:pvcorners pv gq gcorners)))
    (if (and xg cmode)
        (progn
          (setq k 0)
          (foreach tm (pool:crosstemplate cmode)
            (if (nth k xg)
                (pool:pvmod (nth k xg)
                            (list "LINED"
                                  (pool:cornerpoint gq gcorners (nth 3 tm)
                                                    (nth 4 tm))
                                  (pool:cornerpoint gq gcorners (nth 5 tm)
                                                    (nth 6 tm)))))
            (setq k (1+ k))))))

  ;; -------------------------------------- guide preview + input
  (setq pv (pool:pvlive 'qf:geo)
        pool:*pvmore* 'qf:more)
  (princ "\nA gray guide pool is shown -- the RED element is the dimension being asked for.")
  (princ "\nCorners: A bottom-left, B bottom-right, C top-right, D top-left.")

  ;; in-square: opposing sides are equal, ask each pair once
  (princ "\n(Back re-asks the previous question, right back to the start)")
  ;; An OVAL's sides are the one pair that may be NA: the overall and
  ;; the two ends read them back (qf:ovalsides).  The ends themselves
  ;; are always required -- they are the chords the arcs spring from.
  (defun qf:sides ( / ans sk)
  (setq sk (if (= ptype "Oval") 'NAX 'REQ))
  (if pool:*insq*
      (setq ans (pool:askseqb
                  (list (list 'tp sk "Side length (top & bottom)"
                              (append (cdr (assoc 'dc pv)) (cdr (assoc 'ab pv))
                                      (pool:lbl pv '(lA lB lC lD))))
                        (list 'le 'REQ "End length (left & right)"
                              (append (cdr (assoc 'da pv)) (cdr (assoc 'bc pv))
                                      (pool:lbl pv '(lA lB lC lD)))))
                  nil)
            tp (pool:sq ans 'tp) bo tp
            le (pool:sq ans 'le) ri le)
      (setq ans (pool:askseqb
                  (list (list 'tp sk "Side length TOP (D-C)"
                              (append (cdr (assoc 'dc pv)) (pool:lbl pv '(lD lC))))
                        (list 'bo sk "Side length BOTTOM (A-B)"
                              (append (cdr (assoc 'ab pv)) (pool:lbl pv '(lA lB))))
                        (list 'le 'REQ "End length LEFT (A-D)"
                              (append (cdr (assoc 'da pv)) (pool:lbl pv '(lA lD))))
                        (list 'ri 'REQ "End length RIGHT (B-C)"
                              (append (cdr (assoc 'bc pv)) (pool:lbl pv '(lB lC)))))
                  nil)
            tp (pool:sq ans 'tp) bo (pool:sq ans 'bo)
            le (pool:sq ans 'le) ri (pool:sq ans 'ri)))
    ;; re-flagged on every run, so backing in and out re-derives cleanly
    (setq tpna (null tp) bona (null bo))
    ans)

  ;; -------- oval ends.  Any ONE of total / left radius / right radius
  ;; may be NA -- the overall closes the chain against the body, and
  ;; with both radii NA the two ends come out the same (the in-square
  ;; oval).  Only the total is re-asked when too much is missing.
  (defun qf:oval ( / ans)
  (if (/= ptype "Oval")
      nil
      (progn
        ;; in-square ovals are symmetric, so the end radius is asked once
        (setq ans (pool:askseqb
                    (if pool:*insq*
                        (list (list 'tot 'NAX "Total pool length (arc tip to arc tip)"
                                    (cdr (assoc 'tot pv)))
                              (list 'lr 'NAX "End radius (both ends)"
                                    (append (cdr (assoc 'lrad pv))
                                            (cdr (assoc 'rrad pv)))))
                        (list (list 'tot 'NAX "Total pool length (arc tip to arc tip)"
                                    (cdr (assoc 'tot pv)))
                              (list 'lr 'NAX "LEFT oval end radius"
                                    (cdr (assoc 'lrad pv)))
                              (list 'rr 'NAX "RIGHT oval end radius"
                                    (cdr (assoc 'rrad pv)))))
                    t))
        (if (eq ans 'CAL-BACK)
            'CAL-BACK
            (progn
              (setq totl (pool:sq ans 'tot)
                    lrad (pool:sq ans 'lr)
                    rrad (if pool:*insq* lrad (pool:sq ans 'rr)))
              (if (and (null totl)
                       (or (null lrad) (null rrad) tpna bona))
                  (progn
                    (princ (if (or tpna bona)
                               "\nThe total length is needed when a side length is NA."
                               "\nThe total length is needed when an end radius is NA."))
                    (setq totl (pool:askh "Total pool length (arc tip to arc tip)"
                                          (cdr (assoc 'tot pv))))
                    (pool:pvnote 'tot totl)))
              (if (or tpna bona) (qf:ovalsides))
              nil)))))

  ;; -------- sides that were never taped.  An oval spends its overall
  ;; on the two end bulges plus the straight body, so a side that was
  ;; NA reads back out of the overall and the ends (pool:ovalaxis --
  ;; a radius that was not given is taken tangent, i.e. a semicircle,
  ;; so overall - width is the side).  BOTH NA -> the body is that
  ;; length and the oval comes out symmetric; ONE NA -> the overall
  ;; pins the MIDLINE between the ends, so the missing side is the
  ;; derived length mirrored about the one that was measured.
  (defun qf:ovalsides ( / ax v)
    (setq ax (pool:ovalaxis totl lrad rrad le ri))
    (cond
      ;; the overall does not even reach past the two ends -- nothing
      ;; to read the side out of, so it has to be measured
      ((null ax)
       (princ "\nThe total length does not reach past the ends -- measure the side.")
       (if pool:*insq*
           (setq tp (pool:askh "Side length (top & bottom)"
                               (append (cdr (assoc 'dc pv))
                                       (cdr (assoc 'ab pv))))
                 bo tp)
           (progn
             (if tpna (setq tp (pool:askh "Side length TOP (D-C)"
                                          (cdr (assoc 'dc pv)))))
             (if bona (setq bo (pool:askh "Side length BOTTOM (A-B)"
                                          (cdr (assoc 'ab pv)))))))
       (setq tpna nil bona nil))
      ((and tpna bona)
       (setq tp ax bo ax)
       (princ (strcat "\nSide length not measured -- " (pool:fmtlen ax)
                      " off the overall and the ends.")))
      (t
       (setq v (- (* 2.0 ax) (if tpna bo tp)))
       (if (<= v 1.0e-6)
           (progn
             (pool:valnote "SIDE AND TOTAL LENGTH DISAGREE - MISSING SIDE TAKEN OFF THE TOTAL")
             (setq v ax)))
       (if tpna (setq tp v) (setq bo v))
       (princ (strcat "\n" (if tpna "TOP" "BOTTOM") " side not measured -- "
                      (pool:fmtlen v) " closes the overall against the other side."))))
    ;; the guide takes the read-back sides too, so it closes up the
    ;; way the drawn pool will
    (pool:pvnote 'tp tp)
    (pool:pvnote 'bo bo))

  ;; -------- corner treatments (rectangle only; side lengths are to
  ;; the TRUE corner, treatments cut inward)
  (defun qf:corners ( / i lbls out back)
    (if (/= ptype "Rectangle")
        (progn
          (setq corners (list (list "Square" 0.0) (list "Square" 0.0)
                              (list "Square" 0.0) (list "Square" 0.0)))
          (qf:aftercorners)
          nil)
        (if pool:*insq*
            (progn                      ; in-square: one answer for all 4
              (setq cc (pool:askcorner "all four corners" nil nil
                                       (pool:lbl pv '(lA lB lC lD))
                                       (* 0.5 (min tp le)) nil t))
              (if (eq cc 'CAL-BACK)
                  'CAL-BACK
                  (progn (setq corners (list cc cc cc cc))
                         (qf:aftercorners)
                         nil)))
            (progn                      ; out-of-square: per corner, Enter reuses
              (princ "\n(per-corner treatment; press Enter to reuse the previous corner)")
              (setq lbls (list (list "A" bo le) (list "B" bo ri)
                               (list "C" tp ri) (list "D" tp le))
                    corners nil prevty nil prevsz nil i 0 back nil)
              (while (and (< i 4) (not back))
                (setq cc (pool:askcorner
                           (strcat "Corner " (car (nth i lbls))) prevty prevsz
                           (pool:lbl pv (list (pool:lblkey (car (nth i lbls)))))
                           (* 0.5 (min (cadr (nth i lbls)) (caddr (nth i lbls))))
                           nil t))
                (if (eq cc 'CAL-BACK)
                    (if (= i 0)
                        (setq back t)   ; back out of the whole stage
                        (setq i (1- i)
                              corners (cdr corners)
                              ;; the reuse default is the corner BEFORE
                              ;; the one being re-asked
                              prevty (if corners (car (car corners)) nil)
                              prevsz (if corners (cadr (car corners)) nil)))
                    (setq prevty (car cc) prevsz (cadr cc)
                          corners (cons cc corners)
                          i (1+ i))))
              (if back
                  'CAL-BACK
                  (progn (setq corners (reverse corners))
                         (qf:aftercorners)
                         nil))))))

  ;; everything the corner answers determine: the cut flag and the
  ;; guide redraw.  Re-runnable, so backing in and out is safe.  The
  ;; guide sits on the live quad qf:geo keeps in gq, so the treatments
  ;; are drawn at their real sizes -- pool:askcorner has already
  ;; capped each against its own walls.
  (defun qf:aftercorners ( / c)
    (setq anycut nil)
    (foreach c corners (if (pool:cutp (car c)) (setq anycut t)))
    (setq gcorners corners)
    (if anycut (setq pv (pool:pvcorners pv gq gcorners)))
    (princ))

  ;; -------- cross-dim reference mode (only when corners are cut and
  ;; the pool is out-of-square)
  (defun qf:cmode ( / v)
    (setq cmode "Corner")
    (if (and (not pool:*insq*) anycut)
        (progn
          ;; a bare "Cut corners" would now read as the Cut keyword, and
          ;; this gate covers Radius corners too -- but NOT NotGiven,
          ;; which has no treatment ends to tape between
          (setq v (pool:askkwf 'cmode
                               "Radius/Cut corners -- cross dims measured from"
                               "Corner Middle Ends" "Corner/Middle/Ends" nil t))
          (if (eq v 'CAL-BACK) v (progn (setq cmode v) nil)))
        nil))

  ;; -------- cross dims (out-of-square only), per the reference mode.
  ;; The corner-to-corner guide diagonals are retired and one dashed
  ;; guide line is drawn per measurement between its actual reference
  ;; points, so Middle/Ends prompts highlight exactly what gets taped.
  (defun qf:cross ( / )
    (setq xmeas nil xg nil)
    (if pool:*insq*
        (progn
          (princ "\nIn-square: building true to the side measurements (no cross dims).")
          nil)
        (progn
          ;; sides are all in -- the cross dims appear now, one guide
          ;; line per measurement, between its actual reference points,
          ;; then the block runs as one Back-able sequence.  xg holds
          ;; the lines in template order so qf:more can walk them onto
          ;; the quad as their own answers reshape it.
          (setq xitems nil k 0)
          (foreach tm (pool:crosstemplate cmode)
            (setq rpa (pool:cornerpoint gq gcorners (nth 3 tm) (nth 4 tm))
                  rpb (pool:cornerpoint gq gcorners (nth 5 tm) (nth 6 tm))
                  hl (pool:pvadd (pool:pvlined rpa rpb))
                  xg (cons hl xg)
                  xitems (cons (list (read (strcat "x" (itoa k))) 'NAX (cadr tm)
                                     (cons hl (pool:lbl pv
                                       (list (pool:lblkey (nth (nth 3 tm) '("A" "B" "C" "D")))
                                             (pool:lblkey (nth (nth 5 tm) '("A" "B" "C" "D")))))))
                               xitems)
                  k (1+ k)))
          (setq xg (reverse xg)
                ans (pool:askseqb (reverse xitems) t))
          (if (eq ans 'CAL-BACK)
              ;; drop this round's guide lines so a re-entry redraws
              ;; them cleanly for whatever mode is chosen next
              (progn (pool:pvdel xg) (setq xg nil) 'CAL-BACK)
              (progn
                (setq k 0)
                (foreach tm (pool:crosstemplate cmode)
                  (setq xmeas (cons (append tm
                                            (list (pool:sq ans (read (strcat "x" (itoa k))))))
                                    xmeas)
                        k (1+ k)))
                (setq xmeas (reverse xmeas))
                nil)))))

  ;; ---- the input phase, with Back working right across it
  (pool:stages (list 'qf:sides 'qf:oval 'qf:corners 'qf:cmode 'qf:cross))


  ;; the guide has served its purpose -- replace it with the true pool
  (pool:pvkill)

  ;; ------------------------------------------------ fit the body
  ;; bootstrap the true-corner cross targets from the raw measurements,
  ;; then (for cut corners) refine them against the fitted corner
  ;; reference points and re-fit.
  (princ "\nFitting pool body to the measurements ...")
  (setq dac (pool:rawavg xmeas 'ac)
        dbd (pool:rawavg xmeas 'bd)
        fitres (pool:fitquad bo tp le ri dac dbd pool:*side-tol* pool:*cross-tol*)
        quad (car fitres)
        failed (cadr fitres))
  (if (/= cmode "Corner")
      (progn
        (setq pass 0)
        (while (< pass 2)
          (setq dac (pool:effcross quad corners xmeas 'ac)
                dbd (pool:effcross quad corners xmeas 'bd)
                fitres (pool:fitquad bo tp le ri dac dbd pool:*side-tol* pool:*cross-tol*)
                quad (car fitres)
                failed (cadr fitres)
                pass (1+ pass)))))
  (setq a (car quad) b (cadr quad) c (caddr quad) d (cadddr quad)
        cen (cal:v* (cal:v+ (cal:v+ a b) (cal:v+ c d)) 0.25)
        meas (pool:quadmeas quad)
        notes nil)

  ;; dashed linetype + scale for the reference lines
  (setq pool:*dashlt* (pool:ltload "DASHED"))

  ;; -------------------------------- pool body / perimeter (layer POOL)
  ;; Rectangle draws its perimeter with corner treatments.  The oval's
  ;; end chords are construction, not pool, so only the two sides are
  ;; drawn and the perimeter closes through the end arcs.
  (if (= ptype "Rectangle")
      (setq arcs (pool:drawrect quad corners))
      (progn
        (pool:line a b "POOL")
        (pool:line c d "POOL")))

  ;; -------------------------------------- exact two-triangle check
  ;; Computed only (needs the A-C cross dim -- skipped when it was NA);
  ;; the result feeds the TRI CHECK B-D report row.  The check figure
  ;; itself is no longer drawn so out-of-square pools leave a clean
  ;; drawing behind.
  (setq tri (if dac (pool:triquad bo tp le ri dac) nil))
  (if (and dac (not tri))
      (setq notes (cons "TRIANGLE CHECK IMPOSSIBLE - VERIFY MEASUREMENTS" notes)))

  (setq doff (max 12.0 (/ (max bo tp le ri) 18.0))
        th (max 3.0 (/ (max bo tp le ri) 70.0)))

  ;; ------------------------------------------------ oval ends
  ;; The arcs are built from the resolved radii (sagitta off each end
  ;; chord), so dimensioning them reads back the radius that was typed.
  (if (= ptype "Oval")
      (progn
        (setq midl (cal:mid a d)
              ml (pool:unit (cal:perp (cal:v- d a))))
        (if (< (cal:dot (cal:v- midl cen) ml) 0.0)
            (setq ml (cal:v* ml -1.0)))
        (setq midr (cal:mid b c)
              mr (pool:unit (cal:perp (cal:v- c b))))
        (if (< (cal:dot (cal:v- midr cen) mr) 0.0)
            (setq mr (cal:v* mr -1.0)))
        (setq ores (pool:ovalends totl lrad rrad (distance midl midr)
                                  (distance a d) (distance b c))
              lrfit (car ores) rrfit (cadr ores)
              notes (append (nth 5 ores) notes)
              tipl (cal:v+ midl (cal:v* ml (caddr ores)))
              tipr (cal:v+ midr (cal:v* mr (cadddr ores))))
        (pool:arc3p a tipl d "POOL")
        (setq larc (entlast))
        (pool:arc3p b tipr c "POOL")
        (setq rarc (entlast))))

  ;; ------------------------------------------------ extents
  (setq allpts (append quad
                       (if tipl (list tipl tipr) nil))
        xmax (apply 'max (mapcar 'car allpts))
        ymax (apply 'max (mapcar 'cadr allpts))
        ymin (apply 'min (mapcar 'cadr allpts)))

  ;; ------------------------------------------------ dimensions
  (setvar "CLAYER" "DIMENSION")
  (if (= ptype "Rectangle")
      ;; per the reference: only the northern and western perimeter
      ;; dims, hooked to the wall endpoints (object-bounded) and
      ;; rotated along the side directions
      (progn
        (pool:dimrot (pool:cornerpoint quad corners 3 'next)   ; left wall top
                     (pool:cornerpoint quad corners 2 'prev)   ; right wall top
                     (angle d c)
                     (pool:outoff d c cen doff))
        (pool:dimrot (pool:cornerpoint quad corners 0 'next)   ; bottom wall left
                     (pool:cornerpoint quad corners 3 'prev)   ; top wall left
                     (angle a d)
                     (pool:outoff a d cen doff)))
      (if pool:*insq*
          ;; oval in-square, per the field sheet: T above the top side
          ;; and A outside the left arc -- the bottom side and right
          ;; chord repeat them, so they are not dimensioned (B joins
          ;; from the tip-to-tip dim below).  T subdivides B, so it
          ;; reads in SIDE STANDARD; A is an overall and stays put.
          (progn
            (pool:dimalgs d c (pool:outoff d c cen doff))
            (pool:dimalg a d (list (- (car tipl) (* 1.2 doff))
                                   (cadr (cal:mid a d)))))
          (progn
            (setq endoff (* -0.6 doff))
            (pool:dimalgs a b (pool:outoff a b cen doff))
            (pool:dimalgs d c (pool:outoff d c cen doff))
            (pool:dimalg a d (pool:outoff a d cen endoff))
            (pool:dimalg b c (pool:outoff b c cen endoff)))))
  ;; corner annotations: one "Typ." at B when in-square, every corner
  ;; individually when out-of-square
  (if (= ptype "Rectangle")
      (pool:dimcorners quad corners arcs cen doff))
  ;; oval: radius dims read on the ARC from outside it (no line back to
  ;; the circle centre), plus the tip-to-tip overall.  End radii are
  ;; sheet letters -> SIDE STANDARD, like the roman reference.
  (if (= ptype "Oval")
      (progn
        (pool:dimrads larc tipl ml doff)
        (pool:dimrads rarc tipr mr doff)
        ;; B tip-to-tip: on top per the field sheet when in-square,
        ;; below the pool (clear of the 4 side dims) out-of-square
        (pool:dimalg tipl tipr (list (car (cal:mid tipl tipr))
                                     (if pool:*insq*
                                         (+ ymax (* 1.9 doff))
                                         (- ymin (* 1.5 doff)))))))
  ;; provided cross dims, between their reference points, in the CROSS
  ;; DIMENSION style when the drawing has one
  (setq odim (pool:dimxbegin) k 0)
  (foreach m xmeas
    (if (nth 7 m)
        (progn
          (setq rpa (pool:cornerpoint quad corners (nth 3 m) (nth 4 m))
                rpb (pool:cornerpoint quad corners (nth 5 m) (nth 6 m)))
          (pool:dimalg rpa rpb
                       (cal:v+ (cal:mid rpa rpb)
                                (cal:v* (pool:unit (cal:perp (cal:v- rpb rpa)))
                                         (* (if (= 0 (rem k 2)) 0.2 -0.2) doff))))))
    (setq k (1+ k)))
  (pool:dimxend odim)
  (setvar "CLAYER" oldclay)

  ;; corner letters live on the mini-model beside the report, not in
  ;; the corners of the drawing itself -- see the pool:minimap call

  ;; ------------------------------------------------ report table
  ;; a side that was read back out of the overall was never measured,
  ;; so it reports N/A like any other NA -- the ACTUAL column shows
  ;; what it came out at
  (setq rows (list (list "TOP SIDE (D-C)" (if tpna nil tp) (cadr meas))
                   (list "BOTTOM SIDE (A-B)" (if bona nil bo) (car meas))
                   (list "LEFT END (A-D)" le (caddr meas))
                   (list "RIGHT END (B-C)" ri (cadddr meas))))
  ;; each cross measurement vs the actual distance between its
  ;; reference points in the fitted drawing
  (foreach m xmeas
    (setq rows (append rows
                       (list (list (nth 2 m) (nth 7 m)
                                   (distance (pool:cornerpoint quad corners (nth 3 m) (nth 4 m))
                                             (pool:cornerpoint quad corners (nth 5 m) (nth 6 m))))))))
  (if tri
      (setq rows (append rows
                         (list (list "TRI CHECK B-D" dbd
                                     (distance (cadr tri) (cadddr tri)))))))
  (if (= ptype "Oval")
      (setq rows (append rows
                         (list (list "TOTAL LENGTH" totl (distance tipl tipr))
                               (list "LEFT RADIUS" lrad lrfit)
                               (list "RIGHT RADIUS" rrad rrfit)))))
  ;; -------------------------------- pool bottom (interior pipeline)
  (cond
    ((= ptype "Rectangle")
     (setq rows (append rows (pool:hopper quad corners doff th))))
    ((= ptype "Oval")
     (setq rows (append rows (pool:hopovaldsp quad tipl tipr doff th)))))
  ;; corner treatments
  ;; corner treatments.  Gated on pool:anytreat, not on anycut: anycut
  ;; asks the GEOMETRY question and so misses a NotGiven corner, which
  ;; is the one the report most needs to carry -- nothing else on the
  ;; sheet records it.  A NotGiven row has no size, so both number
  ;; columns read N/A rather than a fabricated 0.
  (if (and (= ptype "Rectangle") (pool:anytreat corners))
      (if pool:*insq*
          (setq rows (append rows
                             (list (list (strcat "CORNERS " (car (car corners)))
                                         (if (pool:cutp (car (car corners)))
                                             (cadr (car corners)) nil)
                                         (if (pool:cutp (car (car corners)))
                                             (cadr (car corners)) nil)))))
          (foreach lbl (list (list "A" 0) (list "B" 1) (list "C" 2) (list "D" 3))
            (if (/= (car (nth (cadr lbl) corners)) "Square")
                (setq rows (append rows
                                   (list (list (strcat "COR " (car lbl) " " (car (nth (cadr lbl) corners)))
                                               (if (pool:cutp (car (nth (cadr lbl) corners)))
                                                   (cadr (nth (cadr lbl) corners)) nil)
                                               (if (pool:cutp (car (nth (cadr lbl) corners)))
                                                   (cadr (nth (cadr lbl) corners)) nil)))))))))
  (if failed (setq notes (cons "CROSS DIMS FAILED" notes)))
  (setq notes (append notes pool:*valnotes*))
  (setq rbox (pool:report rows notes (+ xmax (* 2.0 doff)) ymax th "POOL-NOTES"))
  ;; perimeter mini-model with the corner letters, right of the report
  (setq mprims (list (list 'l a b) (list 'l d c)))
  (if (= ptype "Oval")
      (setq mprims (append mprims (list (list 'a a tipl d)
                                        (list 'a b tipr c))))
      (setq mprims (append mprims (list (list 'l a d) (list 'l b c)))))
  (pool:minimap mprims quad
                (list (cons a "A") (cons b "B") (cons c "C") (cons d "D"))
                (+ (car rbox) (* 3.0 th)) (cadr rbox) (* 24.0 th) th)
  (if failed
      (princ "\n*** CROSS DIMS FAILED -- sides held true, see report table ***")
      (princ "\nPool layout complete -- see the report table."))
  (princ))

;;; -------------------- round pools ------------------------------------
;;;
;;;  A round pool is a circle when it is in square and an ellipse when
;;;  the two overalls disagree -- B across, A up, both measured through
;;;  the middle.  There are no corners to best-fit, so the perimeter is
;;;  drawn exactly to the overalls and the report shows them as-drawn.
;;;
;;;  The interior is the True Oval hopper / sport bottom set, measured
;;;  off the pool's own extremes: H from the left edge, E to the right
;;;  edge, M/K off the top and bottom -- so H+G+F+E = B and M+L+K = A,
;;;  exactly like the field sheet.

;; Circle (a = b) or axis-aligned ellipse, on layer lay.
(defun pool:roundbody (cen b a lay)
  (if (< (abs (- a b)) 1.0e-6)
      (entmake (list '(0 . "CIRCLE")
                     (cons 8 lay)
                     (cons 10 (pool:wp cen))
                     (cons 40 (* 0.5 b))))
      (entmake (list '(0 . "ELLIPSE")
                     '(100 . "AcDbEntity")
                     (cons 8 lay)
                     '(100 . "AcDbEllipse")
                     (cons 10 (pool:wp cen))
                     (cons 11 (list (* 0.5 b) 0.0 0.0))   ; major axis, relative
                     (cons 210 '(0.0 0.0 1.0))
                     (cons 40 (/ a b))                    ; minor / major
                     (cons 41 0.0)
                     (cons 42 (* 2.0 pi))))))

;; Full guided flow for round pools.
(defun pool:roundflow ( / oldclay pv ans braw araw b a cen quad tipl tipr
                          doff th rows notes xmax ymax rbox)
  (setq oldclay (getvar "CLAYER"))
  ;; The live guide geometry (see "live guide reshaping"): a circle
  ;; until the two overalls part company, then the ellipse they make.
  ;; The guide body is always an ELLIPSE entity so it can be morphed
  ;; in place however the two answers land.
  (defun rd:geo ( / bov aov sc spec km)
    (setq bov (cond ((pool:pvdim 'b)) (360.0))
          aov (cond ((pool:pvdim 'a)) ((pool:pvdim 'b)) (360.0))
          sc (/ (max bov aov) 360.0)
          spec (append
                 (list (list "ELL" (list (* 0.5 bov) (* 0.5 aov)) bov aov))
                 (pool:pvtiespec (list 0.0 (+ aov (* 55.0 sc)))
                                 (list bov (+ aov (* 55.0 sc)))
                                 "B" (* 12.0 sc))
                 (pool:pvtiespec (list (- 0.0 (* 55.0 sc)) 0.0)
                                 (list (- 0.0 (* 55.0 sc)) aov)
                                 "A" (* 12.0 sc)))
          km (list (list "B" 1 2) (list "A" 3 4)))
    (list spec km (pool:pvspecbox spec)))
  (setq pv (pool:pvlive 'rd:geo))
  (princ "\nRound pool -- B across and A up, both through the middle.")
  (princ "\n(after the first answer, Back re-asks the previous one)")
  ;; in square, the two overalls are the same measurement
  (setq ans (pool:askseq
              (if pool:*insq*
                  (list (list 'b 'REQ "Overall diameter (A & B are equal)"
                              (append (cdr (assoc "B" pv)) (cdr (assoc "A" pv)))))
                  (list (list 'b 'REQ "B - overall length (across)"
                              (cdr (assoc "B" pv)))
                        (list 'a 'REQ "A - overall width (up)"
                              (cdr (assoc "A" pv))))))
        braw (pool:sq ans 'b)
        araw (if pool:*insq* braw (pool:sq ans 'a))
        b braw a araw)
  (pool:pvkill)

  (setq cen (list (* 0.5 b) (* 0.5 a))
        doff (max 12.0 (/ (max b a) 18.0))
        th (max 3.0 (/ (max b a) 70.0))
        notes nil
        pool:*dashlt* (pool:ltload "DASHED"))
  (pool:roundbody cen b a "POOL")
  (if (> (abs (- a b)) 1.0e-6)
      (princ "\nOut of square: the two overalls differ, so the pool is drawn as an ellipse.")
      (princ "\nIn square: A and B agree, so the pool is drawn as a true circle."))

  ;; the bounding box IS the hopper's frame: H/E off the left and right
  ;; extremes, M/K off the top and bottom
  (setq quad (list (list 0.0 0.0) (list b 0.0) (list b a) (list 0.0 a))
        tipl (list 0.0 (* 0.5 a))
        tipr (list b (* 0.5 a))
        xmax b ymax a)

  ;; per the field sheet: B across the top, A up the left side
  (setvar "CLAYER" "DIMENSION")
  (pool:dimalg tipl tipr (list (* 0.5 b) (+ a (* 1.4 doff))))
  (pool:dimalg (list (* 0.5 b) 0.0) (list (* 0.5 b) a)
               (list (- 0.0 (* 1.4 doff)) (* 0.5 a)))
  (setvar "CLAYER" oldclay)

  (setq rows (list (list "OV B" braw b) (list "OV A" araw a))
        rows (append rows (pool:hopovaldsp quad tipl tipr doff th)))
  (setq notes (append notes pool:*valnotes*))
  (setq rbox (pool:report rows notes (+ xmax (* 2.0 doff)) ymax th "POOL-NOTES"))
  ;; mini-model beside the report -- a round pool has no corner
  ;; letters, but the outline keeps the report set consistent
  (pool:minimap (list (list 'rb cen b a)) nil nil
                (+ (car rbox) (* 3.0 th)) (cadr rbox) (* 24.0 th) th)
  (princ "\nPool layout complete -- see the report table.")
  (princ))

;;; -------------------- roman pools ------------------------------------
;;;
;;;  Rectangle body of side length T and width A, with a radius end
;;;  behind corner drops at each side (per the Roman field sheet):
;;;  B/A overalls, S = tip setback past the side ends, S1 = corner
;;;  drop, V = end width between the arc springs, R1/R2 = end radii.
;;;  Letters close against the overalls like the grecian sheet
;;;  (S+T+S = B with T absorbing, S1+V+S1 = A with V absorbing).
;;;  Interior = the True Oval hopper / sport bottoms.

;; Per-end vertical resolution: returns (S1 V) against overall width.
(defun pool:romres (aov s1raw vraw)
  (cond
    (s1raw (list s1raw (- aov (* 2.0 s1raw))))
    (vraw (list (/ (- aov vraw) 2.0) vraw))
    (t (list (/ aov 6.0) (* aov (/ 2.0 3.0))))))

;; Build and draw one Roman end (per the reference drawing: straight
;; S1 stubs along the end line down to the arc springs, the arc
;; bulging S past the end line).  R is implied by S and V:
;; r = (S^2 + (V/2)^2) / 2S.  pb2/pt2 = where the stubs actually START
;; -- the body corners themselves normally, the corner-treatment ends
;; when those corners are rounded or chamfered (the geometry of the
;; end still springs off the TRUE corners pbot/ptop either way).
;; Returns (tip springT springB arcEname rImplied).
(defun pool:romend (pbot ptop pb2 pt2 m s v lay / u mide tip half st sb)
  (setq u (pool:unit (cal:v- ptop pbot))
        mide (cal:mid pbot ptop)
        tip (cal:v+ mide (cal:v* m s))
        half (* 0.5 v)
        st (cal:v+ mide (cal:v* u half))
        sb (cal:v- mide (cal:v* u half)))
  (if (> (distance pt2 st) 1.0e-6) (pool:line pt2 st lay))
  (if (> (distance pb2 sb) 1.0e-6) (pool:line pb2 sb lay))
  (pool:arc3p st tip sb lay)
  (list tip st sb (entlast)
        (/ (+ (* s s) (* half half)) (* 2.0 s))))

;; Gray nominal Roman guide, proportioned from the reference drawing:
;; full-length sides, vertical S1 stubs on the end lines, near-half-
;; round arcs, and the dashed tip-to-tip B centerline.
;; Cross-dim guide lines are NOT part of the preview: they are added by
;; pool:romancross once every side length is in, so the sheet stays
;; uncluttered while the perimeter is being measured.
;; the two body cross-dim guide lines (A-C, B-D), corner to corner of
;; the live guide body q -- so they land on the reshaped guide, not on
;; a fixed nominal box
(defun pool:romancross (pv q)
  (append pv
          (list (cons "XAC" (list (pool:pvadd (pool:pvlined (car q)
                                                            (caddr q)))))
                (cons "XBD" (list (pool:pvadd (pool:pvlined (cadr q)
                                                            (cadddr q))))))))

;; The Roman guide is built by rm:geo inside pool:romanflow (a
;; live-guide geometry function fed to pool:pvlive), so the body, the
;; two end arcs and every sheet tie reshape as the letters come in.

;; Full guided flow for Roman pools.
(defun pool:romanflow ( / oldclay perfect pv gq braw araw traw rombad ans
                          slraw srraw s1lraw s1rraw vlraw vrraw r1 r2
                          hres sl tv sr lres rres s1l vl s1r vr
                          dac dbd fq quad failed a b c d cen meas notes
                          ml mr lend rend tipl tipr doff th odim pr
                          rcs rce rcarcs
                          allpts xmax ymax ymin rows xcol xa rbox)
  (setq oldclay (getvar "CLAYER"))
  (defun rm:perfect ( / v)
    (if pool:*insq*
        (progn (setq perfect t) nil)
        (progn (setq perfect (pool:askynf 'perfect
                                          "Are both ends perfect (identical)"
                                          nil nil))
               nil)))
  ;; one end's tip setback for the live guide, from whatever the sheet
  ;; has so far: the taped S, else what T leaves of B, else the arc
  ;; sagitta of a given radius, else the nominal eighth of B
  (defun rm:geoext (sraw traw rraw v bv)
    (cond
      (sraw sraw)
      (traw (max 1.0 (* 0.5 (- bv traw))))
      ((and rraw (>= rraw (* 0.5 v)))
       (- rraw (sqrt (max 0.0 (- (* rraw rraw) (* 0.25 v v))))))
      (rraw (* 0.5 v))
      (t (/ bv 8.0))))
  ;; The live guide geometry (see "live guide reshaping"): the body
  ;; rectangle T x A with an arc end either side, every letter resolved
  ;; the way rm:resolve will resolve it -- measured where given, the
  ;; sheet's own derivation where not.  A perfect pool's right end
  ;; follows the left letters, exactly as the questions do.  gq keeps
  ;; the live body for pool:romancross.
  (defun rm:geo ( / bov aov res s1l2 vl2 s1r2 vr2 sl2 sr2 tvv sc th
                    st1 sb1 st2 sb2 tl tr xa x2 x3 yt spec km)
    (setq bov (cond ((pool:pvdim 'b)) (464.0))
          aov (cond ((pool:pvdim 'a)) (300.0))
          res (pool:romres aov (pool:pvdim 's1l) (pool:pvdim 'vl))
          s1l2 (car res) vl2 (cadr res)
          res (pool:romres aov
                           (cond ((pool:pvdim 's1r)) ((pool:pvdim 's1l)))
                           (cond ((pool:pvdim 'vr)) ((pool:pvdim 'vl))))
          s1r2 (car res) vr2 (cadr res))
    (if (<= vl2 1.0) (setq s1l2 (/ aov 6.0) vl2 (- aov s1l2 s1l2)))
    (if (<= vr2 1.0) (setq s1r2 (/ aov 6.0) vr2 (- aov s1r2 s1r2)))
    (setq sl2 (rm:geoext (pool:pvdim 'sl) (pool:pvdim 'tt)
                         (pool:pvdim 'r1) vl2 bov)
          sr2 (rm:geoext (cond ((pool:pvdim 'sr)) ((pool:pvdim 'sl)))
                         (pool:pvdim 'tt)
                         (cond ((pool:pvdim 'r2)) ((pool:pvdim 'r1)))
                         vr2 bov)
          tvv (- bov sl2 sr2))
    (if (<= tvv 1.0)
        (setq tvv (* 0.775 bov) sl2 (* 0.5 (- bov tvv)) sr2 sl2))
    (setq st1 (list 0.0 (- aov s1l2)) sb1 (list 0.0 s1l2)
          st2 (list tvv (- aov s1r2)) sb2 (list tvv s1r2)
          tl (list (- 0.0 sl2) (* 0.5 aov))
          tr (list (+ tvv sr2) (* 0.5 aov))
          sc (/ (max bov aov) 400.0)
          th (* 10.0 sc)
          yt (+ aov (* 30.0 sc))
          xa (- 0.0 sl2 (* 43.0 sc))
          x2 (- 0.0 sl2 (* 20.0 sc))
          x3 (+ tvv sr2 (* 20.0 sc))
          gq (list (list 0.0 0.0) (list tvv 0.0)
                   (list tvv aov) (list 0.0 aov))
          spec (append
                 (list (list "LINE" (list 0.0 0.0) (list tvv 0.0))
                       (list "LINE" (list 0.0 aov) (list tvv aov))
                       (list "LINE" (list 0.0 aov) st1)
                       (list "LINE" (list 0.0 0.0) sb1)
                       (list "LINE" (list tvv aov) st2)
                       (list "LINE" (list tvv 0.0) sb2)
                       (list "ARC" st1 tl sb1)
                       (list "ARC" st2 tr sb2))
                 (pool:pvtiespec tl tr "B" th)
                 (pool:pvtiespec (list 0.0 yt) (list tvv yt) "T" th)
                 (pool:pvtiespec (list (- 0.0 sl2) yt) (list 0.0 yt)
                                 "SL" th)
                 (pool:pvtiespec (list tvv yt) (list (+ tvv sr2) yt)
                                 "SR" th)
                 (pool:pvtiespec (list xa 0.0) (list xa aov) "A" th)
                 (pool:pvtiespec (list x2 (- aov s1l2)) (list x2 aov)
                                 "S1L" th)
                 (pool:pvtiespec (list x2 s1l2) (list x2 (- aov s1l2))
                                 "VL" th)
                 (pool:pvtiespec (list x3 (- aov s1r2)) (list x3 aov)
                                 "S1R" th)
                 (pool:pvtiespec (list x3 s1r2) (list x3 (- aov s1r2))
                                 "VR" th)
                 (pool:pvtiespec tl (cal:v+ tl (list (+ sl2 (* 40.0 sc))
                                                      (* 60.0 sc)))
                                 "R1" th)
                 (pool:pvtiespec tr (cal:v+ tr (list (- 0.0 sr2 (* 40.0 sc))
                                                      (* 60.0 sc)))
                                 "R2" th))
          km (list (list "B" 8 9) (list "T" 10 11) (list "SL" 12 13)
                   (list "SR" 14 15) (list "A" 16 17) (list "S1L" 18 19)
                   (list "VL" 20 21) (list "S1R" 22 23) (list "VR" 24 25)
                   (list "R1" 26 27) (list "R2" 28 29)))
    (list spec km (pool:pvspecbox spec)))
  (defun rm:guide ()
    (pool:pvkill)
    (setq pv (pool:pvlive 'rm:geo))
    (princ "\nRoman sheet -- the RED tie is the dimension being asked for.")
    (princ "\n(Back re-asks the previous question)")
    nil)
  (defun rm:letters ( / ans)
  (setq ans (pool:askseqb
              (append
                (list (list 'b 'REQ "B - overall length" (cdr (assoc "B" pv)))
                      (list 'a 'REQ "A - overall width" (cdr (assoc "A" pv)))
                      (list 'tt 'NAX "T - side length (top & bottom)"
                            (cdr (assoc "T" pv))))
                (if perfect
                    (list (list 'sl 'NAX "S - end setback (both ends)"
                                (append (cdr (assoc "SL" pv)) (cdr (assoc "SR" pv))))
                          (list 's1l 'NAX "S1 - corner drop (all corners)"
                                (append (cdr (assoc "S1L" pv)) (cdr (assoc "S1R" pv))))
                          (list 'vl 'NAX "V - end width (both ends)"
                                (append (cdr (assoc "VL" pv)) (cdr (assoc "VR" pv))))
                          (list 'r1 'NAX "R - end radius (both ends, check)"
                                (append (cdr (assoc "R1" pv)) (cdr (assoc "R2" pv)))))
                    (list (list 'sl 'NAX "S - LEFT end setback" (cdr (assoc "SL" pv)))
                          (list 'sr 'NAX "S - RIGHT end setback" (cdr (assoc "SR" pv)))
                          (list 's1l 'NAX "S1 - LEFT corner drop" (cdr (assoc "S1L" pv)))
                          (list 's1r 'NAX "S1 - RIGHT corner drop" (cdr (assoc "S1R" pv)))
                          (list 'vl 'NAX "V - LEFT end width" (cdr (assoc "VL" pv)))
                          (list 'vr 'NAX "V - RIGHT end width" (cdr (assoc "VR" pv)))
                          (list 'r1 'NAX "R1 - LEFT end radius (check)" (cdr (assoc "R1" pv)))
                          (list 'r2 'NAX "R2 - RIGHT end radius (check)"
                                (cdr (assoc "R2" pv))))))
              t))
  (if (eq ans 'CAL-BACK)
      'CAL-BACK
      (progn
  (setq braw (pool:sq ans 'b) araw (pool:sq ans 'a) traw (pool:sq ans 'tt)
        slraw (pool:sq ans 'sl) s1lraw (pool:sq ans 's1l)
        vlraw (pool:sq ans 'vl) r1 (pool:sq ans 'r1)
        srraw (if perfect slraw (pool:sq ans 'sr))
        s1rraw (if perfect s1lraw (pool:sq ans 's1r))
        vrraw (if perfect vlraw (pool:sq ans 'vr))
        r2 (if perfect r1 (pool:sq ans 'r2)))
      nil)))

  ;; every side length is in -- now the cross dims appear on the guide,
  ;; corner to corner of the live body the guide reshaped itself to
  (defun rm:cross ( / ans xg)
    (if pool:*insq*
        nil
        (progn
          (setq pv (pool:romancross pv gq)
                xg (append (cdr (assoc "XAC" pv)) (cdr (assoc "XBD" pv)))
                ans (pool:askseqb
                      (list (list 'ac 'NAX "Cross dim body A-C" (cdr (assoc "XAC" pv)))
                            (list 'bd 'NAX "Cross dim body B-D" (cdr (assoc "XBD" pv))))
                      t))
          (if (eq ans 'CAL-BACK)
              (progn (pool:pvdel xg) 'CAL-BACK)
              (progn (setq dac (pool:sq ans 'ac)
                           dbd (pool:sq ans 'bd))
                     nil)))))

  ;; resolve: per end S1/V vs A (V absorbs); then S + T + S = B with
  ;; T absorbing -- an NA S can come from the chain, or from the end
  ;; radius (arc sagitta: S = R - sqrt(R^2 - (V/2)^2)).
  ;; Lives at the top of rm:corners so the corner questions can be
  ;; capped against the resolved side and stub lengths; re-entered
  ;; after a Back it re-resolves from scratch (the valnotes it emits
  ;; are reset first so they cannot double up).
  (defun rm:resolve ()
  (setq pool:*valnotes* nil rombad nil)
  (setq lres (pool:romres araw s1lraw vlraw)
        s1l (car lres) vl (cadr lres)
        rres (pool:romres araw s1rraw vrraw)
        s1r (car rres) vr (cadr rres)
        sl (cond
             (slraw slraw)
             (traw (/ (- braw traw) 2.0))
             ((and r1 (>= r1 (* 0.5 vl)))
              (- r1 (sqrt (max 0.0 (- (* r1 r1) (* 0.25 vl vl))))))
             (t (/ braw 8.0)))
        sr (cond
             (srraw srraw)
             (traw (/ (- braw traw) 2.0))
             ((and r2 (>= r2 (* 0.5 vr)))
              (- r2 (sqrt (max 0.0 (- (* r2 r2) (* 0.25 vr vr))))))
             (t (/ braw 8.0)))
        tv (- braw sl sr))

  ;; every letter must close POSITIVE against the overalls -- warned
  ;; NOW, before the pool is drawn or the bottom letters asked, and
  ;; red in the report after
  (if (<= s1l 1.0e-6)
      (progn (setq s1l (min 12.0 (* 0.125 araw)) vl (- araw s1l s1l) rombad t)
             (pool:valnote "ROMAN S1 LEFT NOT POSITIVE - ADJUSTED")))
  (if (<= s1r 1.0e-6)
      (progn (setq s1r (min 12.0 (* 0.125 araw)) vr (- araw s1r s1r) rombad t)
             (pool:valnote "ROMAN S1 RIGHT NOT POSITIVE - ADJUSTED")))
  (if (<= vl 1.0e-6)
      (progn (setq vl (min 12.0 (* 0.5 araw)) s1l (/ (- araw vl) 2.0) rombad t)
             (pool:valnote "ROMAN S1 + V + S1 LEFT DOES NOT FIT A - ADJUSTED")))
  (if (<= vr 1.0e-6)
      (progn (setq vr (min 12.0 (* 0.5 araw)) s1r (/ (- araw vr) 2.0) rombad t)
             (pool:valnote "ROMAN S1 + V + S1 RIGHT DOES NOT FIT A - ADJUSTED")))
  (if (<= sl 1.0e-6)
      (progn (setq sl (min 12.0 (/ braw 8.0)) rombad t)
             (pool:valnote "ROMAN S LEFT NOT POSITIVE - ADJUSTED")))
  (if (<= sr 1.0e-6)
      (progn (setq sr (min 12.0 (/ braw 8.0)) rombad t)
             (pool:valnote "ROMAN S RIGHT NOT POSITIVE - ADJUSTED")))
  (if (<= (setq tv (- braw sl sr)) 1.0e-6)
      (progn
        (setq tv (min 12.0 (* 0.25 braw))
              sl (/ (- braw tv) 2.0) sr sl rombad t)
        (pool:valnote "ROMAN S + T + S DOES NOT FIT B - ADJUSTED")))
  (princ))

  ;; -------- corner treatments: the four TRUE corners A/B/C/D, where
  ;; a side runs into an end line above/below the arc's corner drop
  ;; (the arc springs are not corners a builder treats).  One answer
  ;; for all four in square, each asked on its own out of square --
  ;; the rectangle's split exactly, and like the rectangle the corner
  ;; angles are assumed square: the roman body IS a rectangle, within
  ;; a degree of 90 even out of square.  Sizes are capped at half the
  ;; side and at the S1 corner drop, so a treatment can never cross
  ;; the arc spring on the stub below it.
  (defun rm:corners ( / v cc)
    (rm:resolve)
    (setq rcs (list (list "Square" 0.0) (list "Square" 0.0)
                    (list "Square" 0.0) (list "Square" 0.0)))
    (setq v (pool:askynf 'crec
                         "Anything to record about the corners (radius / cut / not given)?"
                         "No" t))
    (cond
      ((eq v 'CAL-BACK) 'CAL-BACK)
      ((not v) nil)
      (pool:*insq*
       (setq cc (pool:askcorner "all four corners" nil nil nil
                                (min (* 0.5 tv) s1l s1r) nil t))
       (if (eq cc 'CAL-BACK)
           'CAL-BACK
           (progn (setq rcs (list cc cc cc cc)) nil)))
      (t
       (princ "\n(per-corner treatment; press Enter to reuse the previous corner)")
       (princ "\nCorners: A bottom-left, B bottom-right, C top-right, D top-left.")
       (setq v (pool:askcorners
                 (list "Corner A" "Corner B" "Corner C" "Corner D")
                 (list (min (* 0.5 tv) s1l) (min (* 0.5 tv) s1r)
                       (min (* 0.5 tv) s1r) (min (* 0.5 tv) s1l))
                 (list nil nil nil nil)
                 (list nil nil nil nil)))
       (if (eq v 'CAL-BACK)
           'CAL-BACK
           (progn (setq rcs v) nil)))))

  (pool:stages (list 'rm:perfect 'rm:guide 'rm:letters 'rm:cross 'rm:corners))
  (pool:pvkill)

  ;; body fit (sides T, ends A) + roman ends; sl/tv/s1l... were
  ;; resolved at the top of rm:corners
  (princ "\nFitting pool body to the measurements ...")
  (setq fq (pool:fitquad tv tv araw araw dac dbd pool:*side-tol* pool:*cross-tol*)
        quad (car fq) failed (cadr fq)
        a (car quad) b (cadr quad) c (caddr quad) d (cadddr quad)
        cen (cal:v* (cal:v+ (cal:v+ a b) (cal:v+ c d)) 0.25)
        meas (pool:quadmeas quad)
        notes nil
        doff (max 12.0 (/ (max tv araw) 18.0))
        th (max 3.0 (/ (max tv araw) 70.0))
        pool:*dashlt* (pool:ltload "DASHED"))
  ;; sides run between the corner-treatment ends (the true corners
  ;; when the corners are square); the dashed body chords stay on the
  ;; true corners -- they are construction, not walls
  (setq rce (pool:ringends quad rcs))
  (pool:line (cadr (nth 0 rce)) (car (nth 1 rce)) "POOL")
  (pool:line (cadr (nth 2 rce)) (car (nth 3 rce)) "POOL")
  (pool:lined b c)
  (pool:lined d a)
  (setq rcarcs (pool:ringarcs rce rcs "POOL"))
  (setq ml (pool:unit (cal:perp (cal:v- d a))))
  (if (< (cal:dot (cal:v- (cal:mid a d) cen) ml) 0.0)
      (setq ml (cal:v* ml -1.0)))
  (setq mr (pool:unit (cal:perp (cal:v- c b))))
  (if (< (cal:dot (cal:v- (cal:mid b c) cen) mr) 0.0)
      (setq mr (cal:v* mr -1.0)))
  ;; the S1 stubs spring from the treatment ends down the end lines
  ;; (ePrev at A and C, eNext at B and D -- the stub side of each)
  (setq lend (pool:romend a d (car (nth 0 rce)) (cadr (nth 3 rce)) ml sl vl "POOL")
        rend (pool:romend b c (cadr (nth 1 rce)) (car (nth 2 rce)) mr sr vr "POOL")
        tipl (car lend) tipr (car rend))

  ;; dims
  (setq allpts (append quad (list tipl tipr (cadr lend) (caddr lend)
                                  (cadr rend) (caddr rend)))
        xmax (apply 'max (mapcar 'car allpts))
        ymax (apply 'max (mapcar 'cadr allpts))
        ymin (apply 'min (mapcar 'cadr allpts)))
  (setvar "CLAYER" "DIMENSION")
  (if pool:*insq*
      ;; in-square, per the field sheet: S+T+S share a row along the
      ;; top with B outboard of them (S shows at BOTH ends), and
      ;; S1+V+S1 share a column beside the left end with A outboard
      ;; (S1 shows at BOTH corners); the bottom side repeats T and is
      ;; not dimensioned.  The stacked letters (S, T, S1, V) subdivide
      ;; their overalls, so they read in SIDE STANDARD; B and A stay
      ;; in the standard style.
      (progn
        (setq xcol (- (car tipl) (* 0.9 doff))
              xa (- (car tipl) (* 1.9 doff)))
        ;; row 1: S (left tip to side start), T, S (side end to right tip)
        (pool:dimalgs (list (car tipl) ymax) d
                      (list (* 0.5 (+ (car tipl) (car d))) (+ ymax doff)))
        (pool:dimalgs d c (list (car (cal:mid d c)) (+ ymax doff)))
        (pool:dimalgs c (list (car tipr) ymax)
                      (list (* 0.5 (+ (car c) (car tipr))) (+ ymax doff)))
        ;; row 2: B, tip to tip
        (pool:dimalg tipl tipr (list (car (cal:mid tipl tipr))
                                     (+ ymax (* 1.9 doff))))
        ;; column 1: S1, V, S1 down the left end line
        (pool:dimalgs d (cadr lend)
                      (list xcol (* 0.5 (+ (cadr d) (cadr (cadr lend))))))
        (pool:dimalgs (cadr lend) (caddr lend)
                      (list xcol (cadr (cal:mid (cadr lend) (caddr lend)))))
        (pool:dimalgs (caddr lend) a
                      (list xcol (* 0.5 (+ (cadr (caddr lend)) (cadr a)))))
        ;; column 2: A, the overall width
        (pool:dimalg a d (list xa (cadr (cal:mid a d)))))
      (progn
        (pool:dimalgs a b (pool:outoff a b cen doff))
        (pool:dimalgs d c (pool:outoff d c cen doff))
        (pool:dimalg tipl tipr (list (car (cal:mid tipl tipr))
                                     (- ymin (* 1.5 doff))))
        (pool:dimalg a d (list (- (car tipl) (* 1.2 doff))
                               (cadr (cal:mid a d))))))
  ;; end radii are sheet letters too -> SIDE STANDARD, per the example
  (pool:dimrads (nth 3 lend) tipl ml doff)
  (pool:dimrads (nth 3 rend) tipr mr doff)
  (setq odim (pool:dimxbegin))
  (if dac
      (pool:dimalg a c (cal:v+ (cal:mid a c)
                                (cal:v* (pool:unit (cal:perp (cal:v- c a)))
                                         (* 0.2 doff)))))
  (if dbd
      (pool:dimalg b d (cal:v+ (cal:mid b d)
                                (cal:v* (pool:unit (cal:perp (cal:v- d b)))
                                         (* -0.2 doff)))))
  (pool:dimxend odim)
  ;; corner treatments: one Typ. at B in square, each treated corner
  ;; its own dim out of square (collapsing back to Typ. when Enter
  ;; reused one answer all the way round)
  ;; B leads out of square too, so the all-same Typ. mark lands on the
  ;; same corner as it does in square
  (pool:dimringcorners quad rcs rce rcarcs cen doff
                       (if pool:*insq*
                           (list '(1 0 2 3))
                           (mapcar 'list '(1 0 2 3))))
  (setvar "CLAYER" oldclay)

  ;; corner letters live on the mini-model beside the report, not in
  ;; the corners of the drawing itself -- see the pool:minimap call

  ;; report
  (setq rows (list
    (list "OV B" braw (distance tipl tipr))
    (list "OV A" araw (distance a d))
    (append (list "T TOP" traw (distance d c)) (if rombad (list t) nil))
    (append (list "T BOT" traw (distance a b)) (if rombad (list t) nil))
    (append (list "S LEFT" slraw (distance tipl (cal:mid a d)))
            (if rombad (list t) nil))
    (append (list "S RIGHT" srraw (distance tipr (cal:mid b c)))
            (if rombad (list t) nil))
    (append (list "S1 LEFT" s1lraw (/ (- (distance a d)
                                         (distance (cadr lend) (caddr lend))) 2.0))
            (if rombad (list t) nil))
    (append (list "S1 RIGHT" s1rraw (/ (- (distance b c)
                                          (distance (cadr rend) (caddr rend))) 2.0))
            (if rombad (list t) nil))
    (append (list "V LEFT" vlraw (distance (cadr lend) (caddr lend)))
            (if rombad (list t) nil))
    (append (list "V RIGHT" vrraw (distance (cadr rend) (caddr rend)))
            (if rombad (list t) nil))
    (list "R1" r1 (nth 4 lend))
    (list "R2" r2 (nth 4 rend))))
  (if (not pool:*insq*)
      (setq rows (append rows
                         (list (list "CROSS A-C" dac (nth 4 meas))
                               (list "CROSS B-D" dbd (nth 5 meas))))))
  ;; corner treatments: one row in square, per corner out of square
  (setq rows (append rows
    (if pool:*insq*
        (pool:cornerrows (list "CORNER") (list (nth 0 rcs)))
        (pool:cornerrows (list "CORNER A" "CORNER B" "CORNER C" "CORNER D")
                         rcs))))
  ;; interior: the True Oval hopper / sport bottoms
  (setq rows (append rows (pool:hopovaldsp quad tipl tipr doff th)))
  (if failed (setq notes (cons "CROSS DIMS FAILED" notes)))
  (setq notes (append notes pool:*valnotes*))
  (setq rbox (pool:report rows notes (+ xmax (* 2.0 doff)) ymax th "POOL-NOTES"))
  ;; perimeter mini-model with the corner letters, right of the report:
  ;; the two sides, the S1 stubs and the end arcs
  (pool:minimap
    (list (list 'l a b) (list 'l d c)
          (list 'l d (cadr lend)) (list 'l a (caddr lend))
          (list 'a (cadr lend) tipl (caddr lend))
          (list 'l c (cadr rend)) (list 'l b (caddr rend))
          (list 'a (cadr rend) tipr (caddr rend)))
    quad
    (list (cons a "A") (cons b "B") (cons c "C") (cons d "D"))
    (+ (car rbox) (* 3.0 th)) (cadr rbox) (* 24.0 th) th)
  (if failed
      (princ "\n*** CROSS DIMS FAILED -- sides held true, see report table ***")
      (princ "\nPool layout complete -- see the report table."))
  (princ))

;;; -------------------- mutt pools -------------------------------------
;;;
;;;  A "mutt" is a rectangle body whose DEEP end (left) and SHALLOW
;;;  end (right) are picked independently -- a roman deep end with a
;;;  grecian shallow end, a grecian deep end with an oval shallow end,
;;;  and so on.  End styles:
;;;    Square  -- plain wall (the rectangle end)
;;;    Grecian -- corner cuts: S setback / S1 drop / S2 face (check)
;;;    ROman   -- S1 stubs + arc bulging S past the end line (V, R)
;;;    Oval    -- full-width arc (R, NA = half round)
;;;  B is the tip-to-tip overall, A the overall width; each end's
;;;  letters close against them exactly like their home sheets, and
;;;  the body length is what's left of B after the end bulges.
;;;  Interior = the standard rectangle bottom pipeline, anchored tip
;;;  to tip (no corner ties -- the ends are too varied to tie to).

;; Resolve one mutt end.  Returns (ext inset s1 v r bad):
;; ext = how far the end sticks out past the body end line, inset =
;; how far a grecian cut eats into the sides.  Emits valnotes on the
;; way out of anything that doesn't close.
(defun pool:muttres (style sraw s1raw vraw rraw aov bov nm / s s1 v ext
                                                            bad half res)
  (cond
    ((= style "Grecian")
     (setq s (if sraw sraw (/ bov 8.0))
           s1 (if s1raw s1raw (/ aov 6.0))
           v (- aov s1 s1))
     (if (<= v 1.0e-6)
         (progn
           (setq s1 (min 12.0 (* 0.125 aov)) v (- aov s1 s1) bad t)
           (pool:valnote (strcat nm " END S1 + V + S1 DOES NOT FIT A - ADJUSTED"))))
     (if (<= s 1.0e-6)
         (progn
           (setq s (min 12.0 (/ bov 8.0)) bad t)
           (pool:valnote (strcat nm " END S NOT POSITIVE - ADJUSTED"))))
     (list 0.0 s s1 v nil bad))
    ((= style "ROman")
     (setq res (pool:romres aov s1raw vraw)
           s1 (car res) v (cadr res))
     (if (<= v 1.0e-6)
         (progn
           (setq s1 (min 12.0 (* 0.125 aov)) v (- aov s1 s1) bad t)
           (pool:valnote (strcat nm " END S1 + V + S1 DOES NOT FIT A - ADJUSTED"))))
     (setq s (cond
               (sraw sraw)
               ((and rraw (>= rraw (* 0.5 v)))
                (- rraw (sqrt (max 0.0 (- (* rraw rraw) (* 0.25 v v))))))
               (t (/ bov 8.0))))
     (if (<= s 1.0e-6)
         (progn
           (setq s (min 12.0 (/ bov 8.0)) bad t)
           (pool:valnote (strcat nm " END S NOT POSITIVE - ADJUSTED"))))
     (list s 0.0 s1 v rraw bad))
    ((= style "Oval")
     (setq half (* 0.5 aov)
           ext (cond
                 ((and rraw (>= rraw half))
                  (- rraw (sqrt (max 0.0 (- (* rraw rraw) (* half half))))))
                 (rraw
                  (pool:valnote (strcat nm " END RADIUS SMALLER THAN A/2 - HALF ROUND DRAWN"))
                  (setq bad t)
                  half)
                 (t half)))
     (list ext 0.0 nil nil rraw bad))
    (t (list 0.0 0.0 nil nil nil nil))))

;; Draw one mutt end onto the fitted body.  pbot/ptop = the body
;; corners on this end line, pb2/pt2 = where the sides start (inset
;; for a grecian end), m = outward unit normal.
;; Returns (tip springT springB arcent rfit) -- tip is the extreme
;; point B is taped to; springs are the wall/stub ends (the body
;; corners themselves on a square or oval end).
(defun pool:muttend (pbot ptop pb2 pt2 m style s1 v ext lay / uu wb wt tip o)
  (setq uu (pool:unit (cal:v- ptop pbot)))
  (cond
    ((= style "Square")
     (pool:line pbot ptop lay)
     (list (cal:mid pbot ptop) ptop pbot nil nil))
    ((= style "Grecian")
     (setq wb (cal:v+ pbot (cal:v* uu s1))
           wt (cal:v- ptop (cal:v* uu s1)))
     (pool:line pb2 wb lay)
     (pool:line wb wt lay)
     (pool:line wt pt2 lay)
     (list (cal:mid pbot ptop) wt wb nil nil))
    ((= style "ROman")
     (pool:romend pbot ptop pbot ptop m ext v lay))
    (t                                  ; Oval
     (setq tip (cal:v+ (cal:mid pbot ptop) (cal:v* m ext)))
     (pool:arc3p ptop tip pbot lay)
     (setq o (pool:circum ptop tip pbot))
     (list tip ptop pbot (entlast) (if o (distance o tip) ext)))))

;; The mutt guide is built by mu:geo inside pool:muttflow (a live-guide
;; geometry function fed to pool:pvlive): the body and both styled ends
;; reshape as B, A and the end letters come in.

;; Full guided flow for mutt pools.
(defun pool:muttflow ( / oldclay pv gq dstyle sstyle ans braw araw
                         dsraw ds1raw dvraw ds2raw drraw
                         ssraw ss1raw svraw ss2raw srraw
                         dres sres extl extr insl insr tv muttbad
                         dac dbd fq quad failed a b c d cen meas notes
                         uab udc ml mr lend rend tipl tipr
                         pab0 pab1 pdc0 pdc1 doff th odim
                         allpts xmax ymax ymin rows xcol xa rbox)
  (setq oldclay (getvar "CLAYER"))

  (defun mu:ends ( / v)
    (setq v (pool:askkwf 'dstyle "DEEP end (left) style"
                         "Square Grecian ROman Oval"
                         "Square/Grecian/ROman/Oval" nil t))
    (if (eq v 'CAL-BACK)
        v
        (progn
          (setq dstyle v
                v (pool:askkwf 'sstyle "SHALLOW end (right) style"
                               "Square Grecian ROman Oval"
                               "Square/Grecian/ROman/Oval" nil t))
          (if (eq v 'CAL-BACK)
              v
              (progn (setq sstyle v) nil)))))

  ;; ---- the live guide geometry (see "live guide reshaping").  The
  ;; helpers run inside mu:geo and read / extend its state the same
  ;; dynamic way the flow stages read the flow's own locals.

  ;; one end's live values (ext ins s1 v) from its answer keys, filled
  ;; with the same derivations pool:muttres will apply at the end
  (defun mu:geoval (style ks ks1 kv kr / s s1 v ext r res half)
    (cond
      ((= style "Grecian")
       (setq s (cond ((pool:pvdim ks)) ((/ bov 8.0)))
             s1 (cond ((pool:pvdim ks1)) ((/ aov 6.0)))
             v (- aov s1 s1))
       (if (<= v 1.0) (setq s1 (/ aov 6.0) v (- aov s1 s1)))
       (if (<= s 1.0) (setq s (/ bov 8.0)))
       (list 0.0 s s1 v))
      ((= style "ROman")
       (setq res (pool:romres aov (pool:pvdim ks1) (pool:pvdim kv))
             s1 (car res) v (cadr res))
       (if (<= v 1.0) (setq s1 (/ aov 6.0) v (- aov s1 s1)))
       (setq r (pool:pvdim kr)
             ext (cond ((pool:pvdim ks))
                       ((and r (>= r (* 0.5 v)))
                        (- r (sqrt (max 0.0 (- (* r r) (* 0.25 v v))))))
                       (r (* 0.5 v))
                       (t (/ bov 8.0))))
       (if (<= ext 1.0) (setq ext (/ bov 8.0)))
       (list ext 0.0 s1 v))
      ((= style "Oval")
       (setq r (pool:pvdim kr)
             half (* 0.5 aov)
             ext (if (and r (>= r half))
                     (- r (sqrt (max 0.0 (- (* r r) (* half half)))))
                     half))
       (list ext 0.0 nil nil))
      (t (list 0.0 0.0 nil nil))))

  ;; push one outline primitive / one keyed tie onto the spec
  (defun mu:spec (pr) (setq spec (append spec (list pr)) n (1+ n)))
  (defun mu:tie (p q lbl)
    (setq spec (append spec (pool:pvtiespec p q lbl th))
          km (cons (list lbl n (1+ n)) km)
          n (+ n 2)))

  ;; one end's outline and ties at live size.  A grecian end's cut runs
  ;; INBOARD from the setback corner to the end line -- the shape
  ;; pool:muttend really draws.  Returns the tip B is taped to.
  (defun mu:geoend (wx sgn style sfx ev / tip ext insv s1 v tx)
    (setq ext (car ev) insv (cadr ev) s1 (caddr ev) v (cadddr ev)
          tip (list wx (* 0.5 aov)))
    (cond
      ((= style "Square")
       (mu:spec (list "LINE" (list wx 0.0) (list wx aov))))
      ((= style "Grecian")
       (mu:spec (list "LINE" (list (- wx (* sgn insv)) 0.0) (list wx s1)))
       (mu:spec (list "LINE" (list wx s1) (list wx (- aov s1))))
       (mu:spec (list "LINE" (list wx (- aov s1))
                      (list (- wx (* sgn insv)) aov)))
       (mu:tie (list (- wx (* sgn insv)) 0.0) (list wx s1)
               (strcat "S2" sfx)))
      ((= style "ROman")
       (setq tip (list (+ wx (* sgn ext)) (* 0.5 aov)))
       (mu:spec (list "LINE" (list wx aov) (list wx (- aov s1))))
       (mu:spec (list "LINE" (list wx 0.0) (list wx s1)))
       (mu:spec (list "ARC" (list wx (- aov s1)) tip (list wx s1)))
       (mu:tie tip (cal:v+ tip (list (* sgn -40.0 sc) (* 60.0 sc)))
               (strcat "R" sfx)))
      (t                                ; Oval
       (setq tip (list (+ wx (* sgn ext)) (* 0.5 aov)))
       (mu:spec (list "ARC" (list wx aov) tip (list wx 0.0)))
       (mu:tie tip (cal:v+ tip (list (* sgn -40.0 sc) (* 60.0 sc)))
               (strcat "R" sfx))))
    ;; grecian and roman ends share the S / S1 / V letters
    (if (member style '("Grecian" "ROman"))
        (progn
          (setq tx (+ wx (* sgn 72.0 sc)))
          (mu:tie (list (car tip) (+ aov (* 30.0 sc)))
                  (list (- wx (* sgn insv)) (+ aov (* 30.0 sc)))
                  (strcat "S" sfx))
          (mu:tie (list tx (- aov s1)) (list tx aov) (strcat "S1" sfx))
          (mu:tie (list tx s1) (list tx (- aov s1)) (strcat "V" sfx))))
    tip)

  ;; the guide itself: end lines at 0 and tvv, ends in their chosen
  ;; styles, the body between the grecian insets, and the B / A tapes.
  ;; gq keeps the live body for pool:romancross.
  (defun mu:geo ( / bov aov sc th el er tvv spec km n tipl2 tipr2 xa2)
    (setq bov (cond ((pool:pvdim 'b)) (464.0))
          aov (cond ((pool:pvdim 'a)) (300.0))
          sc (/ (max bov aov) 400.0)
          th (* 10.0 sc)
          el (mu:geoval dstyle 'dsl 'ds1 'dv 'dr)
          er (mu:geoval sstyle 'ssl 'ss1 'sv 'sr)
          tvv (- bov (car el) (car er)))
    (if (<= (- tvv (cadr el) (cadr er)) 1.0)
        (setq tvv (+ (cadr el) (cadr er) (* 0.5 bov))))
    (setq spec nil km nil n 0
          gq (list (list 0.0 0.0) (list tvv 0.0)
                   (list tvv aov) (list 0.0 aov))
          tipl2 (mu:geoend 0.0 -1.0 dstyle "L" el)
          tipr2 (mu:geoend tvv 1.0 sstyle "R" er)
          xa2 (- 0.0 (car el) (* 70.0 sc)))
    (mu:spec (list "LINE" (list (cadr el) 0.0) (list (- tvv (cadr er)) 0.0)))
    (mu:spec (list "LINE" (list (cadr el) aov) (list (- tvv (cadr er)) aov)))
    (mu:tie tipl2 tipr2 "B")
    (mu:tie (list xa2 0.0) (list xa2 aov) "A")
    (list spec km (pool:pvspecbox spec)))

  (defun mu:guide ()
    (pool:pvkill)
    (setq pv (pool:pvlive 'mu:geo))
    (princ "\nMutt sheet -- deep end LEFT, shallow end RIGHT; the RED tie is the dimension being asked for.")
    (princ "\n(Back re-asks the previous question)")
    nil)

  ;; the letter items one end contributes, per its style
  (defun mu:enditems (style sfx nm ks ks1 kv ks2 kr)
    (cond
      ((= style "Grecian")
       (list (list ks 'NAX (strcat nm " end S - corner setback")
                   (cdr (assoc (strcat "S" sfx) pv)))
             (list ks1 'NAX (strcat nm " end S1 - corner drop")
                   (cdr (assoc (strcat "S1" sfx) pv)))
             (list ks2 'NAX (strcat nm " end S2 - corner face (check)")
                   (cdr (assoc (strcat "S2" sfx) pv)))))
      ((= style "ROman")
       (list (list ks 'NAX (strcat nm " end S - tip setback")
                   (cdr (assoc (strcat "S" sfx) pv)))
             (list ks1 'NAX (strcat nm " end S1 - corner drop")
                   (cdr (assoc (strcat "S1" sfx) pv)))
             (list kv 'NAX (strcat nm " end V - width between springs")
                   (cdr (assoc (strcat "V" sfx) pv)))
             (list kr 'NAX (strcat nm " end R - radius (check)")
                   (cdr (assoc (strcat "R" sfx) pv)))))
      ((= style "Oval")
       (list (list kr 'NAX (strcat nm " end R - radius (NA = half round)")
                   (cdr (assoc (strcat "R" sfx) pv)))))
      (t nil)))

  (defun mu:letters ( / ans)
    (setq ans (pool:askseqb
                (append
                  (list (list 'b 'REQ "B - overall length (tip to tip)"
                              (cdr (assoc "B" pv)))
                        (list 'a 'REQ "A - overall width"
                              (cdr (assoc "A" pv))))
                  (mu:enditems dstyle "L" "Deep" 'dsl 'ds1 'dv 'ds2 'dr)
                  (mu:enditems sstyle "R" "Shallow" 'ssl 'ss1 'sv 'ss2 'sr))
                t))
    (if (eq ans 'CAL-BACK)
        'CAL-BACK
        (progn
          (setq braw (pool:sq ans 'b) araw (pool:sq ans 'a)
                dsraw (pool:sq ans 'dsl) ds1raw (pool:sq ans 'ds1)
                dvraw (pool:sq ans 'dv) ds2raw (pool:sq ans 'ds2)
                drraw (pool:sq ans 'dr)
                ssraw (pool:sq ans 'ssl) ss1raw (pool:sq ans 'ss1)
                svraw (pool:sq ans 'sv) ss2raw (pool:sq ans 'ss2)
                srraw (pool:sq ans 'sr))
          nil)))

  ;; body cross dims, out-of-square only (the ends ride on the body),
  ;; corner to corner of the live body the guide reshaped itself to
  (defun mu:cross ( / ans xg)
    (if pool:*insq*
        nil
        (progn
          (setq pv (pool:romancross pv gq)
                xg (append (cdr (assoc "XAC" pv)) (cdr (assoc "XBD" pv)))
                ans (pool:askseqb
                      (list (list 'ac 'NAX "Cross dim body A-C"
                                  (cdr (assoc "XAC" pv)))
                            (list 'bd 'NAX "Cross dim body B-D"
                                  (cdr (assoc "XBD" pv))))
                      t))
          (if (eq ans 'CAL-BACK)
              (progn (pool:pvdel xg) 'CAL-BACK)
              (progn (setq dac (pool:sq ans 'ac)
                           dbd (pool:sq ans 'bd))
                     nil)))))

  (pool:stages (list 'mu:ends 'mu:guide 'mu:letters 'mu:cross))
  (pool:pvkill)

  ;; -------- resolve the ends, then the body against B
  (setq dres (pool:muttres dstyle dsraw ds1raw dvraw drraw araw braw "DEEP")
        sres (pool:muttres sstyle ssraw ss1raw svraw srraw araw braw "SHALLOW")
        extl (car dres) insl (cadr dres)
        extr (car sres) insr (cadr sres)
        muttbad (or (nth 5 dres) (nth 5 sres))
        tv (- braw extl extr))
  (if (<= (- tv insl insr) 1.0e-6)
      (progn
        (setq tv (+ insl insr (min 12.0 (* 0.25 braw))) muttbad t)
        (pool:valnote "MUTT ENDS DO NOT FIT B - BODY ADJUSTED")))

  ;; -------- fit the body, draw sides and ends
  (princ "\nFitting pool body to the measurements ...")
  (setq fq (pool:fitquad tv tv araw araw dac dbd pool:*side-tol* pool:*cross-tol*)
        quad (car fq) failed (cadr fq)
        a (car quad) b (cadr quad) c (caddr quad) d (cadddr quad)
        cen (cal:v* (cal:v+ (cal:v+ a b) (cal:v+ c d)) 0.25)
        meas (pool:quadmeas quad)
        notes nil
        doff (max 12.0 (/ (max braw araw) 18.0))
        th (max 3.0 (/ (max braw araw) 70.0))
        pool:*dashlt* (pool:ltload "DASHED")
        uab (pool:unit (cal:v- b a))
        udc (pool:unit (cal:v- c d)))
  (setq ml (pool:unit (cal:perp (cal:v- d a))))
  (if (< (cal:dot (cal:v- (cal:mid a d) cen) ml) 0.0)
      (setq ml (cal:v* ml -1.0)))
  (setq mr (pool:unit (cal:perp (cal:v- c b))))
  (if (< (cal:dot (cal:v- (cal:mid b c) cen) mr) 0.0)
      (setq mr (cal:v* mr -1.0)))
  (setq pab0 (cal:v+ a (cal:v* uab insl))
        pab1 (cal:v- b (cal:v* uab insr))
        pdc0 (cal:v+ d (cal:v* udc insl))
        pdc1 (cal:v- c (cal:v* udc insr)))
  (pool:line pab0 pab1 "POOL")
  (pool:line pdc0 pdc1 "POOL")
  (setq lend (pool:muttend a d pab0 pdc0 ml dstyle
                           (caddr dres) (nth 3 dres) extl "POOL")
        rend (pool:muttend b c pab1 pdc1 mr sstyle
                           (caddr sres) (nth 3 sres) extr "POOL")
        tipl (car lend) tipr (car rend))

  ;; -------- extents / dims
  (setq allpts (append quad (list tipl tipr (cadr lend) (caddr lend)
                                  (cadr rend) (caddr rend)))
        xmax (apply 'max (mapcar 'car allpts))
        ymax (apply 'max (mapcar 'cadr allpts))
        ymin (apply 'min (mapcar 'cadr allpts)))
  (setvar "CLAYER" "DIMENSION")
  (if pool:*insq*
      ;; field-sheet set: each end's letters where its home sheet puts
      ;; them -- S row + top side under B along the top, S1/V columns
      ;; beside their ends, A outboard left, S2 on grecian cuts, R on
      ;; the arcs (below).  The stacked letters (S, the top side, S1,
      ;; V) subdivide the overalls and read in SIDE STANDARD; B, A and
      ;; the S2 cut faces stay in the standard style, per the example.
      (progn
        (if (or (= dstyle "Grecian") (= dstyle "ROman"))
            (pool:dimalgs (list (car tipl) ymax) pdc0
                          (list (* 0.5 (+ (car tipl) (car pdc0)))
                                (+ ymax doff))))
        (pool:dimalgs pdc0 pdc1
                      (list (car (cal:mid pdc0 pdc1)) (+ ymax doff)))
        (if (or (= sstyle "Grecian") (= sstyle "ROman"))
            (pool:dimalgs pdc1 (list (car tipr) ymax)
                          (list (* 0.5 (+ (car pdc1) (car tipr)))
                                (+ ymax doff))))
        (pool:dimalg tipl tipr (list (car (cal:mid tipl tipr))
                                     (+ ymax (* 1.9 doff))))
        (setq xcol (- (car tipl) (* 0.9 doff))
              xa (- (car tipl) (* 1.9 doff)))
        (if (or (= dstyle "Grecian") (= dstyle "ROman"))
            (progn
              (pool:dimalgs d (cadr lend)
                            (list xcol (* 0.5 (+ (cadr d) (cadr (cadr lend))))))
              (pool:dimalgs (cadr lend) (caddr lend)
                            (list xcol (cadr (cal:mid (cadr lend) (caddr lend)))))))
        (if (or (= sstyle "Grecian") (= sstyle "ROman"))
            (progn
              (pool:dimalgs c (cadr rend)
                            (list (+ (car tipr) (* 0.9 doff))
                                  (* 0.5 (+ (cadr c) (cadr (cadr rend))))))
              (pool:dimalgs (cadr rend) (caddr rend)
                            (list (+ (car tipr) (* 0.9 doff))
                                  (cadr (cal:mid (cadr rend) (caddr rend)))))))
        (pool:dimalg a d (list xa (cadr (cal:mid a d))))
        (if (= dstyle "Grecian")
            (pool:dimalg pab0 (caddr lend)
                         (pool:outoffp pab0 (caddr lend)
                                       (list pab0 pab1 pdc1 pdc0) doff)))
        (if (= sstyle "Grecian")
            (pool:dimalg pab1 (caddr rend)
                         (pool:outoffp pab1 (caddr rend)
                                       (list pab0 pab1 pdc1 pdc0) doff))))
      ;; out-of-square: the simple roman-style set + dashed crosses
      (progn
        (pool:dimalgs pab0 pab1 (pool:outoff pab0 pab1 cen doff))
        (pool:dimalgs pdc0 pdc1 (pool:outoff pdc0 pdc1 cen doff))
        (pool:dimalg tipl tipr (list (car (cal:mid tipl tipr))
                                     (- ymin (* 1.5 doff))))
        (pool:dimalg a d (list (- (car tipl) (* 1.2 doff))
                               (cadr (cal:mid a d))))))
  ;; end radii are sheet letters -> SIDE STANDARD, like the roman
  (pool:dimrads (nth 3 lend) tipl ml doff)
  (pool:dimrads (nth 3 rend) tipr mr doff)
  (if (not pool:*insq*)
      (progn
        (setq odim (pool:dimxbegin))
        (if dac
            (pool:dimalg a c (cal:v+ (cal:mid a c)
                                      (cal:v* (pool:unit (cal:perp (cal:v- c a)))
                                               (* 0.2 doff)))))
        (if dbd
            (pool:dimalg b d (cal:v+ (cal:mid b d)
                                      (cal:v* (pool:unit (cal:perp (cal:v- d b)))
                                               (* -0.2 doff)))))
        (pool:dimxend odim)))
  (setvar "CLAYER" oldclay)

  ;; corner letters live on the mini-model beside the report, not in
  ;; the corners of the drawing itself -- see the pool:minimap call

  ;; -------- report: one block per end, in its own sheet's letters
  (defun mu:endrows (nm style res ends pbot ptop pb2 sraw s1raw vraw
                     s2raw rraw / bad out)
    (setq bad (if (nth 5 res) (list t) nil)
          out nil)
    (if (or (= style "Grecian") (= style "ROman"))
        (setq out (append out (list
          (append (list (strcat nm " S") sraw
                        (if (= style "Grecian")
                            (distance pbot pb2)
                            (distance (car ends) (cal:mid pbot ptop))))
                  bad)
          (append (list (strcat nm " S1") s1raw
                        (distance ptop (cadr ends))) bad)
          (append (list (strcat nm " V") vraw
                        (distance (cadr ends) (caddr ends))) bad)))))
    (if (= style "Grecian")
        (setq out (append out (list
          (append (list (strcat nm " S2") s2raw
                        (distance pb2 (caddr ends))) bad)))))
    (if (or (= style "ROman") (= style "Oval"))
        (setq out (append out (list
          (append (list (strcat nm " R") rraw (nth 4 ends)) bad)))))
    out)

  (setq rows (append
    (list (append (list "OV B" braw (distance tipl tipr))
                  (if muttbad (list t) nil))
          (list "OV A" araw (distance a d))
          (list "T SIDE" (- tv insl insr) (distance pdc0 pdc1)))
    (mu:endrows "DEEP" dstyle dres lend a d pab0
                dsraw ds1raw dvraw ds2raw drraw)
    (mu:endrows "SHAL" sstyle sres rend b c pab1
                ssraw ss1raw svraw ss2raw srraw)))
  (if (not pool:*insq*)
      (setq rows (append rows
                         (list (list "CROSS A-C" dac (nth 4 meas))
                               (list "CROSS B-D" dbd (nth 5 meas))))))

  ;; -------- interior: standard bottom pipeline, anchored tip to tip
  (setq rows (append rows (pool:hopmuttdsp quad tipl tipr doff th)))
  (if failed (setq notes (cons "CROSS DIMS FAILED" notes)))
  (setq notes (append notes pool:*valnotes*))
  (setq rbox (pool:report rows notes (+ xmax (* 2.0 doff)) ymax th "POOL-NOTES"))
  ;; perimeter mini-model with the corner letters, right of the
  ;; report: sides + each end in its own style
  (pool:minimap
    (append (list (list 'l pab0 pab1) (list 'l pdc0 pdc1))
            (pool:muttmmend dstyle a d pab0 pdc0 lend tipl)
            (pool:muttmmend sstyle b c pab1 pdc1 rend tipr))
    quad
    (list (cons a "A") (cons b "B") (cons c "C") (cons d "D"))
    (+ (car rbox) (* 3.0 th)) (cadr rbox) (* 24.0 th) th)
  (if failed
      (princ "\n*** CROSS DIMS FAILED -- sides held true, see report table ***")
      (princ "\nPool layout complete -- see the report table."))
  (princ))

;; One mutt end as mini-model primitives, per its style (ends =
;; muttend's (tip springT springB arcent rfit) return).
(defun pool:muttmmend (style pbot ptop pb2 pt2 ends tip)
  (cond
    ((= style "Grecian")
     (list (list 'l pb2 (caddr ends))
           (list 'l (caddr ends) (cadr ends))
           (list 'l (cadr ends) pt2)))
    ((= style "ROman")
     (list (list 'l ptop (cadr ends)) (list 'l pbot (caddr ends))
           (list 'a (cadr ends) tip (caddr ends))))
    ((= style "Oval")
     (list (list 'a ptop tip pbot)))
    (t (list (list 'l pbot ptop)))))

;; Mutt bottom dispatcher: the standard rectangle pipeline on the
;; tip-to-tip frame (H closes from the deep tip, E to the shallow
;; tip, like every home sheet), square hopper corners, no corner
;; ties -- the ends are too varied to tie the hopper back to.
(defun pool:hopmuttdsp (quad tipl tipr doff th / btype u v)
  (if (not (pool:askbottom))
      nil
      (progn
        (setq btype (pool:askkwf 'btype "Bottom type"
                                 pool:*btypes* pool:*btshown*
                                 "Normal" nil))
        (setq u (pool:unit (cal:v- tipr tipl))
              v (cal:perp u))
        (if (/= btype "Sport")
            (pool:hopnormal (pool:bodyquad (list tipl v) (list tipr v)
                                           (list (car quad)
                                                 (cal:v- (cadr quad) (car quad)))
                                           (list (cadddr quad)
                                                 (cal:v- (caddr quad) (cadddr quad))))
                            pool:*sq4* doff th nil btype
                            (min (car tipl) (car tipr))
                            (- (apply 'min (mapcar 'cadr quad)) (* 2.2 doff))
                            nil)
            (pool:hopsport (list tipl v) (list tipr v)
                           (list (car quad) (cal:v- (cadr quad) (car quad)))
                           (list (cadddr quad)
                                 (cal:v- (caddr quad) (cadddr quad)))
                           (cal:v* (cal:v+ (cal:v+ (car quad) (cadr quad))
                                             (cal:v+ (caddr quad) (cadddr quad)))
                                    0.25)
                           (distance tipl tipr)
                           (min (car tipl) (car tipr))
                           (- (apply 'min (mapcar 'cadr quad)) (* 2.2 doff))
                           (apply 'max (mapcar 'cadr quad))
                           doff th)))))

;; UNDO grouping that copes with drawings where undo is limited or
;; off, and with an error firing before the group was ever opened.
(defun pool:undobegin ()
  (if (= 1 (logand 1 (getvar "UNDOCTL")))
      (progn
        (command "_.UNDO" "_Begin")
        (setq pool:*undogrp* t))))

(defun pool:undoend ()
  (if pool:*undogrp* (command "_.UNDO" "_End"))
  (setq pool:*undogrp* nil))

;;; -------------------- sysvar save / restore --------------------------
;;; The snapshot of the user's settings lives in a GLOBAL and is taken
;;; only when no snapshot is already pending: if a previous run died
;;; before restoring (hard crash, failure inside the error handler),
;;; the stale snapshot still holds the user's TRUE settings.  Saving
;;; again at that point would capture the zeroed OSMODE and every
;;; later run would faithfully "restore" 0 -- the user's object snaps
;;; would look permanently wiped by the command.  Restoring clears the
;;; snapshot so the next run saves fresh.

;;; -------------------- main command -----------------------------------

(defun c:POOL ( / *error* ptype base)

  (defun *error* (msg)
    (if (and msg
             (not (wcmatch (strcase msg) "*BREAK*,*CANCEL*,*QUIT*,*EXIT*")))
        (princ (strcat "\nPOOL error: " msg)))
    ;; user settings come back FIRST so nothing below can skip them
    (cal:sysrestore)
    ;; DIMSTYLE is read-only to setvar, so it is put back the only way
    ;; it can be: dying inside a small-dim, cross-dim or SIDE STANDARD
    ;; block must not leave that style current in the user's drawing
    (setq pool:*sideon* nil)
    (pool:dimsend pool:*dimstyle0*)
    (pool:pvkill)
    ;; a form must never outlive the run it was given to: left behind,
    ;; the next POOL typed at the command line would answer itself with
    ;; last time's numbers and draw a wrong pool with no error at all.
    ;; Cover mode is the same hazard, quieter: a leaked flag draws the
    ;; next pool with no bottom and never asks why
    (pool:fclear)
    (setq pool:*nobottom* nil)
    (pool:undoend)
    (if *pop-error-mode* (*pop-error-mode*))
    (princ))

  ;; AutoCAD 2012+ requires this so *error* may call (command);
  ;; harmless no-op guard on older releases where it doesn't exist
  (if *push-error-using-command* (*push-error-using-command*))

  (cal:syssave '("OSMODE" "LUNITS" "CMDECHO" "CLAYER"))
  (setq pool:*valnotes* nil
        pool:*smallwarned* nil
        pool:*profents* nil
        pool:*sideon* nil
        pool:*dimstyle0* (getvar "DIMSTYLE")
        ;; report lengths follow the units the DRAWING was in before
        ;; POOL switches to architectural for its prompts: a crew whose
        ;; drawing is in feet-inches gets a feet-inches report
        pool:*ftin* (member (cdr (assoc "LUNITS" cal:*sysold*)) '(3 4)))
  (setvar "CMDECHO" 0)
  (pool:undobegin)
  ;; architectural units while prompting so every distance can be
  ;; typed as 25'6", 25'-6-1/2" or 25'6.5 as well as plain inches
  (setvar "LUNITS" 4)
  (princ "\nDistances may be typed as 25'6\", 25'-6-1/2\" or 25'6.5 (plain numbers = inches).")

  ;; In-square pools are built true to the side measurements and need
  ;; no diagonals; out-of-square pools take the usual cross-dim route.
  (setq pool:*insq*
        (= "Insquare"
           (pool:askkwf 'insq "Is the pool in-square or out-of-square"
                        "Insquare Outofsquare" "Insquare/Outofsquare" nil nil)))
  (if pool:*insq*
      (princ "\nIn-square: building true to the side measurements (no cross dims needed)."))

  ;; L = true L; LAzyl = lazy L (type LA); ROman = roman (type RO)
  ;; the six common shapes first, then the rarely-used ones; type RO
  ;; for a roman, ROU for a round, MU for a mutt (mixed ends).
  (setq ptype (pool:fshape))

  ;; the base point is picked with the user's own snaps still live;
  ;; only afterwards do snaps drop for the command-fed drawing work
  (setq base (if (pool:fhas 'base)
                 (pool:ftake 'base)
                 (getpoint "\nInsertion base point <0,0>: "))
        pool:*base* (if (and base (listp base))
                        (list (car base) (cadr base))
                        (list 0.0 0.0)))
  (setvar "OSMODE" 0)

  ;; ------------------------------------------------ layers
  (pool:layer "POOL" 4)
  (pool:layer "DIMENSION" 2)
  (pool:layer "POOL-NOTES" 3)

  ;; dashed linetype up front so the guide's cross dims draw dashed
  ;; patterns are defined in inches and scaled to cancel LTSCALE, so
  ;; they show the same in any drawing
  (setq pool:*dashlt* (pool:ltload "DASHED")
        pool:*dotlt* (pool:ltload "DOT"))

  (cond
    ((= ptype "L") (pool:hexflow nil))
    ((= ptype "LAzyl") (pool:hexflow t))
    ((= ptype "Grecian") (pool:grecflow nil))
    ((= ptype "OCtagon") (pool:grecflow t))
    ((= ptype "ROman") (pool:romanflow))
    ((= ptype "ROUnd") (pool:roundflow))
    ((= ptype "MUtt") (pool:muttflow))
    (t (pool:quadflow ptype)))

  ;; ------------------------------------------------ finish
  (command "_.ZOOM" "_Extents")
  (pool:undoend)
  (cal:sysrestore)
  (pool:fclear)
  (setq pool:*nobottom* nil)
  (if *pop-error-mode* (*pop-error-mode*))
  (princ))


;; POOL for a cover sheet: the same command, with the pool-bottom gate
;; already answered No.  A cover records the perimeter and nothing
;; below it, so the depth chain -- C, C2, D, the hopper type and its
;; corner method -- is work the sheet has no answers for and no room
;; to show.
;;
;; It is a command of its own rather than a mode the panel switches on,
;; so that clicking a button still runs exactly the command named on it
;; and typing POOLCOVER does the same thing as clicking it.  The flag
;; is cleared by c:POOL on both its exits, so this cannot leak into the
;; next pool even if this run is cancelled half way.
(defun c:POOLCOVER ()
  (setq pool:*nobottom* t)
  (princ "\nPOOLCOVER: cover sheet - no pool bottom will be asked for.")
  (c:POOL)
  (princ))

(defun c:POOLVER ()
  (princ (strcat "\nPOOL " pool:*version*))
  (princ (strcat "\nDemo: "
                 (if pooldemo:*version* pooldemo:*version* "not loaded")))
  (princ (strcat "\nTutorial: "
                 (if tutorial:*version* tutorial:*version* "not loaded")))
  (princ))

(princ (strcat "\nPOOL " pool:*version*
               " loaded.  POOL to lay out a pool, POOLVER for the version"
               (if tutorial:*version* ", TUTORIALPOOL to learn it" "")
               "."))
(princ)


;;; ======================================================================
;;; >>> POOLDEMO.lsp
;;; ======================================================================

;;; ===================================================================
;;;  POOLDEMO.LSP -- install check + reference sheet for POOL.LSP
;;; ===================================================================
;;;
;;;  Type POOLDEMO to draw one canned example of every shape, every
;;;  pool bottom and every drawing feature POOL.LSP can produce, from
;;;  hardcoded numbers -- no prompts.  It answers, in your own AutoCAD
;;;  and in about a second:
;;;
;;;    * did POOL.LSP actually load?
;;;    * do the layers and the dashed/dotted linetypes come out right?
;;;    * do the dimension commands work in this drawing's dim style?
;;;    * do arcs, text, the report table and the red failure marking
;;;      all render as intended?
;;;
;;;  It is also a reference sheet: every shape and bottom side by side,
;;;  captioned, at real-world sizes.
;;;
;;;  Nothing here prompts, so it is safe to run in a scratch drawing at
;;;  any time.  It draws on the same layers POOL uses -- run it in a
;;;  NEW drawing, not over live work.
;;;
;;;  Load POOL.LSP first (POOLDEMO uses its geometry), then this file.
;;;
;;;  This file ships twice under two names with IDENTICAL contents:
;;;      POOLDEMO.LSP                 the static name
;;;      POOLDEMO_MMDDYY_REV##.LSP    named for its revision
;;; ===================================================================

;;; SHARED BUILD: requires CALOFIN-LIB.lsp (load via CALOFIN-LOADER.lsp).
;;; Generic helpers live there under cal: - see STANDARDS.md.
;;;

(setq pooldemo:*version* "082726 REV03")

(setq pooldemo:*colw* 760.0)            ; grid cell width
(setq pooldemo:*rowh* 900.0)            ; grid cell height

;; Caption above a cell.
(defun pooldemo:cap (org txt)
  (setq pool:*base* org)
  (pool:text (list 0.0 470.0) 22.0 txt "POOL-NOTES"))

;; Standard-hopper bottom inside quad, in a named style, with its
;; profile when the style has one.  Mirrors what pool:hopnormal draws
;; once the prompting is done.
(defun pooldemo:bottom (quad corners style h g f e m k wh dp c2 / gg sp toth)
  (setq sp (pool:btmspec style)
        toth (distance (car quad) (cadr quad))
        gg (pool:hopcalc quad corners h g e m k))
  (pool:hopdraw gg "POOL" t)
  (if (caddr sp)
      (pool:profdraw 0.0 -150.0 toth wh
                     (pool:btmbrks style h g f wh dp c2) "POOL" nil))
  gg)

;; Chain dims for a hopper, red on the flagged indices.
(defun pooldemo:hopdims (gg fixed / tl k)
  (setvar "CLAYER" "DIMENSION")
  (setq k 0)
  (foreach tl (list (list 'pl 'phl nil) (list 'phl 'phr nil)
                    (list 'phr 'pbrk nil) (list 'pbrk 'pr nil)
                    (list 'pht 'pt t) (list 'phb 'pht t) (list 'pb 'phb t))
    (if (> (distance (cadr (assoc (car tl) gg)) (cadr (assoc (cadr tl) gg)))
           1.0e-6)
        (progn
          (pool:dimalg (cadr (assoc (car tl) gg)) (cadr (assoc (cadr tl) gg))
                       (cal:v+ (cal:mid (cadr (assoc (car tl) gg))
                                          (cadr (assoc (cadr tl) gg)))
                                (if (caddr tl) (cadr (assoc 'voff gg))
                                    (list 0.0 0.0))))
          (if (member k fixed) (pool:dimred))))
    (setq k (1+ k)))
  (setvar "CLAYER" "POOL"))

;;; -------------------- the cells --------------------------------------

;; 1. in-square rectangle, square corners, standard hopper
(defun pooldemo:c1 (org / q sq gg)
  (pooldemo:cap org "1  RECTANGLE in-square / square corners / NORMAL hopper")
  (setq q (list (list 0.0 0.0) (list 480.0 0.0) (list 480.0 240.0) (list 0.0 240.0))
        sq pool:*sq4*)
  (pool:drawrect q sq)
  (setvar "CLAYER" "DIMENSION")
  (pool:dimrot (nth 3 q) (nth 2 q) (angle (nth 3 q) (nth 2 q))
               (list 240.0 300.0))
  (pool:dimrot (nth 0 q) (nth 3 q) (angle (nth 0 q) (nth 3 q))
               (list -60.0 120.0))
  (setvar "CLAYER" "POOL")
  (setq gg (pooldemo:bottom q sq "Normal" 60.0 90.0 210.0 120.0 60.0 60.0
                            nil nil nil))
  (pooldemo:hopdims gg nil))

;; 2. out-of-square rectangle, radius corners, WEDGE bottom + profile
(defun pooldemo:c2 (org / q cs arcs cen gg od)
  (pooldemo:cap org "2  RECTANGLE out-of-square / radius corners / WEDGE + section")
  (setq q (list (list 0.0 0.0) (list 482.0 3.0) (list 479.0 243.0) (list 2.0 239.0))
        cs (list (list "Radius" 36.0) (list "Radius" 36.0)
                 (list "Radius" 36.0) (list "Radius" 36.0))
        cen (cal:v* (cal:v+ (cal:v+ (nth 0 q) (nth 1 q))
                              (cal:v+ (nth 2 q) (nth 3 q))) 0.25)
        arcs (pool:drawrect q cs))
  (setvar "CLAYER" "DIMENSION")
  (setq od (pool:dimxbegin))
  (pool:dimalg (nth 0 q) (nth 2 q) (cal:mid (nth 0 q) (nth 2 q)))
  (pool:dimxend od)
  (pool:dimcorners q cs arcs cen 30.0)
  (setvar "CLAYER" "POOL")
  (setq gg (pooldemo:bottom q cs "Wedge" 60.0 0.0 420.0 0.0 60.0 60.0
                            40.0 60.0 40.0))
  (pooldemo:hopdims gg nil))

;; 3. oval, SPORT bottom (full-width breaks + V-less deep flat)
(defun pooldemo:c3 (org / q ores tipl tipr gg cen)
  (pooldemo:cap org "3  OVAL / true-radius ends / SPORT bottom + section")
  (setq q (list (list 60.0 0.0) (list 420.0 0.0) (list 420.0 240.0) (list 60.0 240.0))
        cen (list 240.0 120.0)
        ores (pool:ovalends 480.0 nil nil 360.0 240.0 240.0)
        tipl (list (- 60.0 (caddr ores)) 120.0)
        tipr (list (+ 420.0 (cadddr ores)) 120.0))
  (pool:line (nth 0 q) (nth 1 q) "POOL")
  (pool:line (nth 3 q) (nth 2 q) "POOL")
  (pool:arc3p (nth 0 q) tipl (nth 3 q) "POOL")
  (setvar "CLAYER" "DIMENSION")
  (pool:dimrad (entlast) tipl (list -1.0 0.0) 30.0)
  (setvar "CLAYER" "POOL")
  (pool:arc3p (nth 1 q) tipr (nth 2 q) "POOL")
  (setvar "CLAYER" "DIMENSION")
  (pool:dimrad (entlast) tipr (list 1.0 0.0) 30.0)
  (pool:dimalg tipl tipr (list 240.0 -60.0))
  (setvar "CLAYER" "POOL")
  (setq gg (pool:hopsportc (list tipl (list 0.0 1.0)) (list tipr (list 0.0 1.0))
                           (list (nth 0 q) (list 1.0 0.0))
                           (list (nth 3 q) (list 1.0 0.0))
                           cen 48.0 60.0 120.0 144.0 108.0 24.0 24.0))
  (pool:hopsportdraw gg nil "POOL" nil)
  (pool:profdraw 0.0 -150.0 480.0 40.0
                 (list (cons 48.0 40.0) (cons 108.0 72.0)
                       (cons 228.0 72.0) (cons 372.0 40.0))
                 "POOL" nil))

;; 4. grecian, six-sided hopper
(defun pooldemo:c4 (org / pts lend rend gg)
  (pooldemo:cap org "4  GRECIAN / 45-deg ends / SIX-SIDED hopper")
  (setq lend (pool:grecendp (list 0.0 0.0) (list 0.0 240.0) (list -1.0 0.0)
                            70.0 70.0 140.0)
        rend (pool:grecendp (list 480.0 0.0) (list 480.0 240.0) (list 1.0 0.0)
                            70.0 70.0 140.0)
        pts (list (list 0.0 0.0) (list 480.0 0.0)
                  (cadr rend) (car rend)
                  (list 480.0 240.0) (list 0.0 240.0)
                  (car lend) (cadr lend)))
  (pool:line (nth 0 pts) (nth 1 pts) "POOL")
  (pool:line (nth 1 pts) (nth 2 pts) "POOL")
  (pool:line (nth 2 pts) (nth 3 pts) "POOL")
  (pool:line (nth 3 pts) (nth 4 pts) "POOL")
  (pool:line (nth 4 pts) (nth 5 pts) "POOL")
  (pool:line (nth 5 pts) (nth 6 pts) "POOL")
  (pool:line (nth 6 pts) (nth 7 pts) "POOL")
  (pool:line (nth 7 pts) (nth 0 pts) "POOL")
  (setvar "CLAYER" "DIMENSION")
  (pool:dimalg (nth 0 pts) (nth 1 pts) (list 240.0 -60.0))
  (pool:dimalg (nth 7 pts) (nth 6 pts)
               (cal:v+ (cal:mid (nth 7 pts) (nth 6 pts)) (list -40.0 0.0)))
  (setvar "CLAYER" "POOL")
  ;; sheet letters: W 84 flat, L1 48 left edge on the 120 hopper width
  (setq gg (pool:hopgrecc pts 90.0 120.0 150.0 60.0 60.0
                          (list "Letters" 84.0 48.0 120.0)))
  (pool:hopgrecdraw gg "POOL" t nil))

;; 5. roman, oval (radius-end) hopper
(defun pooldemo:c5 (org / q lend rend tipl tipr gg)
  (pooldemo:cap org "5  ROMAN / stub ends + arcs / TRUE-OVAL hopper")
  (setq q (list (list 0.0 0.0) (list 400.0 0.0) (list 400.0 260.0) (list 0.0 260.0)))
  (pool:line (nth 0 q) (nth 1 q) "POOL")
  (pool:line (nth 3 q) (nth 2 q) "POOL")
  (pool:lined (nth 1 q) (nth 2 q))
  (pool:lined (nth 3 q) (nth 0 q))
  (setq lend (pool:romend (nth 0 q) (nth 3 q) (list -1.0 0.0) 45.0 160.0 "POOL")
        rend (pool:romend (nth 1 q) (nth 2 q) (list 1.0 0.0) 45.0 160.0 "POOL")
        tipl (car lend) tipr (car rend))
  (setvar "CLAYER" "DIMENSION")
  (pool:dimrad (nth 3 lend) tipl (list -1.0 0.0) 30.0)
  (pool:dimrad (nth 3 rend) tipr (list 1.0 0.0) 30.0)
  (pool:dimalg tipl tipr (list 200.0 -60.0))
  (setvar "CLAYER" "POOL")
  (setq gg (pool:hopovalc q tipl tipr 80.0 150.0 130.0 65.0 65.0 65.0))
  (pool:hopovaldraw gg "POOL" nil))

;; 6. true L, standard hopper in the main section
(defun pooldemo:c6 (org / pts dv mquad gg)
  (pooldemo:cap org "6  L / standard hopper in the main section")
  (setq pts (pool:hexguess (list 480.0 420.0 180.0 180.0 300.0 240.0) nil))
  (pool:line (nth 0 pts) (nth 1 pts) "POOL")
  (pool:line (nth 1 pts) (nth 2 pts) "POOL")
  (pool:line (nth 2 pts) (nth 3 pts) "POOL")
  (pool:line (nth 3 pts) (nth 4 pts) "POOL")
  (pool:line (nth 4 pts) (nth 5 pts) "POOL")
  (pool:line (nth 5 pts) (nth 0 pts) "POOL")
  (setq dv (pool:linex (nth 4 pts) (cal:v- (nth 5 pts) (nth 0 pts))
                       (nth 0 pts) (cal:v- (nth 1 pts) (nth 0 pts)))
        mquad (list (nth 0 pts) dv (nth 4 pts) (nth 5 pts))
        gg (pool:hopcalc mquad pool:*sq4* 60.0 90.0 0.0 60.0 60.0))
  (pool:hopdraw gg "POOL" t)
  (pooldemo:hopdims gg nil))

;; 7. lazy L
(defun pooldemo:c7 (org / pts)
  (pooldemo:cap org "7  LAZY L / 45-degree bend")
  (setq pts (pool:hexguess (list 296.0 167.6 167.6 99.0 226.0 168.0) t))
  (pool:line (nth 0 pts) (nth 1 pts) "POOL")
  (pool:line (nth 1 pts) (nth 2 pts) "POOL")
  (pool:line (nth 2 pts) (nth 3 pts) "POOL")
  (pool:line (nth 3 pts) (nth 4 pts) "POOL")
  (pool:line (nth 4 pts) (nth 5 pts) "POOL")
  (pool:line (nth 5 pts) (nth 0 pts) "POOL")
  (setvar "CLAYER" "DIMENSION")
  (pool:dimalg (nth 0 pts) (nth 1 pts)
               (cal:v+ (cal:mid (nth 0 pts) (nth 1 pts)) (list 0.0 -50.0)))
  (setvar "CLAYER" "POOL"))

;; 8. modified flat and sloping shallow end, side by side
(defun pooldemo:c8 (org / q sq gg)
  (pooldemo:cap org "8  MODIFIED FLAT (left) and SLOPING SHALLOW END (right)")
  (setq q (list (list 0.0 0.0) (list 480.0 0.0) (list 480.0 240.0) (list 0.0 240.0))
        sq (list (list "Cut" 34.0) (list "Cut" 34.0)
                 (list "Cut" 34.0) (list "Cut" 34.0)))
  (pool:drawrect q sq)
  (setq gg (pooldemo:bottom q sq "MOdflat" 24.0 432.0 24.0 0.0 24.0 24.0
                            40.0 60.0 40.0))
  (pooldemo:hopdims gg nil)
  ;; the sloping shallow end, one cell to the right
  (setq pool:*base* (list (+ (car org) pooldemo:*colw*) (cadr org)))
  (pool:drawrect q pool:*sq4*)
  (setq gg (pooldemo:bottom q pool:*sq4* "SHallow" 60.0 60.0 240.0 120.0
                            60.0 60.0 40.0 60.0 45.0))
  (pooldemo:hopdims gg nil))

;; 9. a FAILED bottom: G resolved negative, so it is drawn 1' long,
;;    F pays the difference, and both go red -- dims and report rows
(defun pooldemo:c9 (org / q sq cv vals fixed gg rows)
  (pooldemo:cap org "9  VALIDATION / negative G floored to 1', F trimmed, both RED")
  (setq q (list (list 0.0 0.0) (list 480.0 0.0) (list 480.0 240.0) (list 0.0 240.0))
        sq pool:*sq4*)
  (pool:drawrect q sq)
  ;; H 60 + G -20 + F 380 + E 60 cannot close: G floors at 12, F pays
  (setq cv (pool:chainval (list 60.0 -20.0 380.0 60.0) 480.0)
        vals (car cv) fixed (cadr cv)
        gg (pool:hopcalc q sq (nth 0 vals) (nth 1 vals) (nth 3 vals) 60.0 60.0))
  (pool:hopdraw gg "POOL" t)
  (pooldemo:hopdims gg fixed)
  (setq rows (list
    (pool:vrow "HOP H" 60.0 (nth 0 vals) 0 fixed)
    (pool:vrow "HOP G" -20.0 (nth 1 vals) 1 fixed)
    (pool:vrow "HOP F" 380.0 (nth 2 vals) 2 fixed)
    (pool:vrow "HOP E" 60.0 (nth 3 vals) 3 fixed)))
  (pool:report rows
               (list "BOTTOM LENGTHS FAILED - G/F ADJUSTED, VERIFY")
               540.0 240.0 9.0 "POOL-NOTES"))

;; 10. octagon drawn from A and B alone, with a square hopper
(defun pooldemo:c10 (org / c pts gg)
  (pooldemo:cap org "10  OCTAGON / drawn from A and B alone / square hopper")
  ;; A = B = 420 -> a regular octagon: c = A / (2 + root 2)
  (setq c (/ 420.0 3.41421356237)
        pts (list (list c 0.0) (list (- 420.0 c) 0.0)
                  (list 420.0 c) (list 420.0 (- 420.0 c))
                  (list (- 420.0 c) 420.0) (list c 420.0)
                  (list 0.0 (- 420.0 c)) (list 0.0 c)))
  (pool:line (nth 0 pts) (nth 1 pts) "POOL")
  (pool:line (nth 1 pts) (nth 2 pts) "POOL")
  (pool:line (nth 2 pts) (nth 3 pts) "POOL")
  (pool:line (nth 3 pts) (nth 4 pts) "POOL")
  (pool:line (nth 4 pts) (nth 5 pts) "POOL")
  (pool:line (nth 5 pts) (nth 6 pts) "POOL")
  (pool:line (nth 6 pts) (nth 7 pts) "POOL")
  (pool:line (nth 7 pts) (nth 0 pts) "POOL")
  (setvar "CLAYER" "DIMENSION")
  (pool:dimalg (list 0.0 0.0) (list 420.0 0.0) (list 210.0 -60.0))
  (pool:dimalg (nth 7 pts) (nth 0 pts)
               (cal:v+ (cal:mid (nth 7 pts) (nth 0 pts)) (list -30.0 -30.0)))
  (setvar "CLAYER" "POOL")
  (setq gg (pool:hopgrecc pts 90.0 110.0 130.0 90.0 90.0 nil))
  (pool:hopgrecdraw gg "POOL" nil nil))

;; 11. round pool: a true circle in square, with the radius-end hopper
(defun pooldemo:c11 (org / quad tipl tipr gg)
  (pooldemo:cap org "11  ROUND / in-square circle / TRUE-OVAL hopper")
  (pool:roundbody (list 210.0 210.0) 420.0 420.0 "POOL")
  (setq quad (list (list 0.0 0.0) (list 420.0 0.0)
                   (list 420.0 420.0) (list 0.0 420.0))
        tipl (list 0.0 210.0) tipr (list 420.0 210.0))
  (setvar "CLAYER" "DIMENSION")
  (pool:dimalg tipl tipr (list 210.0 -60.0))
  (setvar "CLAYER" "POOL")
  ;; H 70 + G 150 + F 110 + E 90 = 420 ; M 90 + L 240 + K 90 = 420
  (setq gg (pool:hopovalc quad tipl tipr 70.0 150.0 90.0 90.0 90.0 120.0))
  (pool:hopovaldraw gg "POOL" nil))

;; 12. mutt: roman deep end + grecian shallow end on one rectangle body
(defun pooldemo:c12 (org / quad lend rend tipl tipr hq gg)
  (pooldemo:cap org "12  MUTT / ROMAN deep end + GRECIAN shallow end / NORMAL hopper")
  ;; body 440 x 240; roman end sticks 40 out left, grecian cuts 50 in
  (setq quad (list (list 0.0 0.0) (list 440.0 0.0)
                   (list 440.0 240.0) (list 0.0 240.0)))
  (pool:line (list 0.0 0.0) (list 390.0 0.0) "POOL")
  (pool:line (list 0.0 240.0) (list 390.0 240.0) "POOL")
  (setq lend (pool:muttend (nth 0 quad) (nth 3 quad)
                           (list 0.0 0.0) (list 0.0 240.0)
                           (list -1.0 0.0) "ROman" 40.0 160.0 40.0 "POOL")
        rend (pool:muttend (nth 1 quad) (nth 2 quad)
                           (list 390.0 0.0) (list 390.0 240.0)
                           (list 1.0 0.0) "Grecian" 40.0 160.0 0.0 "POOL")
        tipl (car lend) tipr (car rend))
  (setvar "CLAYER" "DIMENSION")
  (pool:dimalg tipl tipr (list (car (cal:mid tipl tipr)) 300.0))
  (pool:dimrad (cadddr lend) tipl (list -1.0 0.0) 30.0)
  (setvar "CLAYER" "POOL")
  ;; bottom on the tip-to-tip frame, no corner ties (mixed ends)
  (setq hq (list (list -40.0 0.0) (list 440.0 0.0)
                 (list 440.0 240.0) (list -40.0 240.0))
        gg (pool:hopcalc hq pool:*sq4* 60.0 90.0 120.0 60.0 60.0))
  (pool:hopdraw gg "POOL" nil)
  (pooldemo:hopdims gg nil))

;;; -------------------- the command ------------------------------------

(defun c:POOLDEMO ( / *error* cells k org)

  (defun *error* (msg)
    (if (and msg (not (wcmatch (strcase msg) "*BREAK*,*CANCEL*,*QUIT*,*EXIT*")))
        (princ (strcat "\nPOOLDEMO error: " msg)))
    (cal:sysrestore)
    (pool:undoend)
    (if *pop-error-mode* (*pop-error-mode*))
    (princ))

  (if (not (member 'pool:hopcalc (atoms-family 0)))
      (princ "\nPOOL.LSP is not loaded -- APPLOAD it first, then run POOLDEMO.")
      (pooldemo:run))
  (princ))

(defun pooldemo:run ( / cells k org)
  (if *push-error-using-command* (*push-error-using-command*))
  (cal:syssave '("OSMODE" "LUNITS" "CMDECHO" "CLAYER"))
  (setq pool:*valnotes* nil
        pool:*smallwarned* nil)
  (setvar "CMDECHO" 0)
  (pool:undobegin)
  (setvar "OSMODE" 0)
  (setvar "LUNITS" 4)

  (pool:layer "POOL" 4)
  (pool:layer "DIMENSION" 2)
  (pool:layer "POOL-NOTES" 3)
  (setq pool:*dashlt* (pool:ltload "DASHED")
        pool:*dotlt* (pool:ltload "DOT"))
  (setvar "CLAYER" "POOL")

  (princ "\nPOOLDEMO -- drawing one example of every shape and bottom ...")
  (setq cells (list 'pooldemo:c1 'pooldemo:c2 'pooldemo:c3 'pooldemo:c4
                    'pooldemo:c5 'pooldemo:c6 'pooldemo:c7 'pooldemo:c8
                    'pooldemo:c9 'pooldemo:c10 'pooldemo:c11 'pooldemo:c12)
        k 0)
  (foreach fn cells
    (setq org (list (* pooldemo:*colw* (rem k 3))
                    (* pooldemo:*rowh* (- 0 (/ k 3)))))
    (setq pool:*base* org)
    (princ (strcat "\n  cell " (itoa (1+ k)) " ..."))
    (apply fn (list org))
    (setq pool:*base* org)              ; a cell may have moved the base
    (setq k (1+ k)))

  (command "_.ZOOM" "_Extents")
  (pool:undoend)
  (cal:sysrestore)
  (if *pop-error-mode* (*pop-error-mode*))
  (princ (strcat "\nPOOLDEMO complete -- " (itoa (length cells))
                 " cells drawn.  If every cell looks right, POOL.LSP is"
                 " working in this drawing."))
  (princ))

(princ (strcat "\nPOOLDEMO " pooldemo:*version*
               " loaded.  Type POOLDEMO to draw the install-check sheet."))
(princ)


;;; ======================================================================
;;; >>> TUTORIALPOOL.lsp
;;; ======================================================================

;;; ===================================================================
;;;  TUTORIALPOOL.LSP -- guided walkthrough for POOL.LSP
;;;
;;;  Command:  TUTORIALPOOL
;;;
;;; SHARED BUILD: requires CALOFIN-LIB.lsp (load via CALOFIN-LOADER.lsp).
;;; Generic helpers live there under cal: - see STANDARDS.md.
;;;
;;;  A paced, captioned tour of how POOL.LSP works: what it asks, why,
;;;  and what the drawing looks like at each stage.  Each topic prints
;;;  a short explanation (and, where it matters, a full checklist of
;;;  what the routine actually verifies), draws a small illustrative
;;;  example, and waits for you to read it -- press ENTER to move on,
;;;  or type X then ENTER to stop early.
;;;
;;;  This is a WALKTHROUGH, not a reference sheet: POOLDEMO draws one
;;;  example of every shape and bottom side by side for comparison;
;;;  this command draws a handful of focused examples, one concept at
;;;  a time, with the reasoning spelled out next to each.
;;;
;;;  Load POOL.LSP first (this file uses its geometry helpers), then
;;;  this file.  Safe to run in a scratch drawing at any time -- it
;;;  draws on the same layers POOL uses.
;;;
;;;  This file ships twice under two names with IDENTICAL contents:
;;;      TUTORIALPOOL.LSP                 the static name
;;;      TUTORIALPOOL_MMDDYY_REV##.LSP    named for its revision
;;; ===================================================================

(setq tutorial:*version* "082726 REV06")

(setq tutorial:*colw* 620.0)            ; horizontal spacing between topics

;; Caption above a topic's drawing (local coords -- pool:*base* is set
;; to that topic's origin before this is called).
(defun tutorial:cap (txt)
  (pool:text (list 0.0 260.0) 14.0 txt "POOL-NOTES"))

;; One bulleted line, wrapped to keep the command line readable.
(defun tutorial:bullet (txt)
  (princ (strcat "\n  - " txt)))

;; Frame this topic's drawing: lo/hi are LOCAL coordinates (pool:wp
;; applies the topic's own pool:*base* automatically).
(defun tutorial:frame (lo hi)
  (command "_.ZOOM" "_Window" (pool:wp lo) (pool:wp hi)))

;; Wait for the user to read the topic before moving on.  Returns NIL
;; if they typed X (quit early); T otherwise.  Scriptable: any script
;; value maps to a plain Enter except one starting with X/x.
(defun tutorial:pause ( / v)
  (setq v (getstring "\nPress ENTER for the next topic (X then ENTER to stop here): "))
  (/= (strcase (substr v 1 1)) "X"))

;;; -------------------- topic 1: welcome --------------------------------

(defun tutorial:c1 ()
  (princ "\n\n=== 1. WELCOME ===")
  (princ "\nPOOL.LSP lays out an as-built swimming-pool plan from real field")
  (princ "\nmeasurements: perimeter, cross dims, corner treatments, the pool")
  (princ "\nbottom (hopper), dimensions, and a target/actual/delta report --")
  (princ "\nall from typed numbers, no drawing by hand.")
  (princ "\n\nNine shapes: Rectangle, Grecian, ROman, L, LAzyl, Oval, OCtagon,")
  (princ "\nROUnd, MUtt (a rectangle body with independently chosen deep and")
  (princ "\nshallow ends).")
  (princ "\n\nThree commands:")
  (tutorial:bullet "POOL          -- run the real thing")
  (tutorial:bullet "POOLDEMO      -- one hardcoded example of every shape and bottom, side by side (install check)")
  (tutorial:bullet "TUTORIALPOOL  -- this walkthrough")
  (princ "\n\nDistances may be typed as 25'6\", 25'-6-1/2\" or 25'6.5, as well")
  (princ "\nas plain inches (306.5) -- POOL switches units for you while it runs.")
  (princ))

;;; -------------------- topic 2: guided input ----------------------------

(defun tutorial:c2 ( / a b c d)
  (tutorial:cap "2  THE GUIDED INPUT")
  (setq a (list 0.0 0.0) b (list 300.0 0.0)
        c (list 300.0 180.0) d (list 0.0 180.0))
  (pool:line a b "POOL-NOTES")
  (pool:setcol (entlast) pool:*pv-col*)
  (pool:line b c "POOL-NOTES")
  (pool:setcol (entlast) pool:*pv-col*)
  (pool:line c d "POOL-NOTES")
  (pool:setcol (entlast) pool:*pv-col*)
  ;; the side currently "being asked about" -- drawn RED, same colour
  ;; and convention the real guide uses while prompting
  (pool:line d a "POOL-NOTES")
  (pool:setcol (entlast) pool:*hi-col*)
  (pool:text (list -14.0 0.0) 10.0 "A" "POOL-NOTES")
  (pool:text (list 300.0 -18.0) 10.0 "B" "POOL-NOTES")
  (pool:text (list 314.0 180.0) 10.0 "C" "POOL-NOTES")
  (pool:text (list -14.0 198.0) 10.0 "D" "POOL-NOTES")
  (pool:textc (list 0.0 90.0) 10.0 "<- being asked now" "POOL-NOTES" 1)
  (tutorial:frame (list -40.0 -40.0) (list 400.0 300.0))
  (princ "\n\n=== 2. THE GUIDED INPUT ===")
  (princ "\nAs soon as you pick the shape, a gray guide (like the three")
  (princ "\nsides above) is drawn at the base point and the view zooms to it.")
  (tutorial:bullet "The element being asked about right now turns RED (the D-A side, here) -- there is never any doubt which measurement you are answering.")
  (tutorial:bullet "The guide is LIVE: every answer reshapes it on the spot -- type the bottom side and the box stretches to it, type a cross dim and the pool leans out of square -- so you watch the real pool take shape instead of a fixed cartoon.")
  (tutorial:bullet "When a prompt names corners (a side, a cross dim, a corner treatment) the corner LETTERS turn red too.")
  (tutorial:bullet "Object snaps stay LIVE the whole time you are answering, including the very first base-point pick, so you can snap to the real site.")
  (tutorial:bullet "Back (type B -- or U for Undo, its unlisted synonym) re-asks the previous question, from ANYWHERE in the process, right back to the very first one.")
  (tutorial:bullet "Your own snap settings come back exactly as they were once POOL finishes, even if you cancel or it hits an error.")
  (princ))

;;; -------------------- topic 3: in-square vs out-of-square -------------

(defun tutorial:c3 ( / q1 q2)
  (tutorial:cap "3  IN-SQUARE vs OUT-OF-SQUARE")
  (setq q1 (list (list 0.0 0.0) (list 240.0 0.0)
                 (list 240.0 140.0) (list 0.0 140.0)))
  (pool:drawrect q1 pool:*sq4*)
  (pool:text (list 20.0 -20.0) 10.0 "IN-SQUARE: built true, no diagonals" "POOL-NOTES")
  (setq q2 (list (list 320.0 4.0) (list 562.0 0.0)
                 (list 558.0 138.0) (list 322.0 142.0)))
  (pool:drawrect q2 pool:*sq4*)
  (pool:lined (nth 0 q2) (nth 2 q2))
  (pool:lined (nth 1 q2) (nth 3 q2))
  (pool:text (list 330.0 -20.0) 10.0 "OUT-OF-SQUARE: cross dims taped" "POOL-NOTES")
  (tutorial:frame (list -40.0 -40.0) (list 600.0 300.0))
  (princ "\n\n=== 3. IN-SQUARE vs OUT-OF-SQUARE ===")
  (princ "\nAsked FIRST, before the shape itself.")
  (tutorial:bullet "In-square: built true to the side/end lengths you give -- no diagonals asked, no diagonals drawn.")
  (tutorial:bullet "Out-of-square: perimeter first, THEN cross dims (dashed above) -- the guide draws no diagonals until every side is in.")
  (princ "\nHow the body is fit to what does not quite agree (tapes always")
  (princ "\ncarry a little human error):")
  (tutorial:bullet "1. Sides held EXACTLY true; the body is skewed to bring the cross dims as close as possible. Within 2\"? Done.")
  (tutorial:bullet "2. Otherwise the sides may flex inside their own +/-1\" band to pull the cross dims in.")
  (tutorial:bullet "3. Still can't be met? Sides held true, cross dims as close as possible, and CROSS DIMS FAILED is written in red under the report.")
  (princ))

;;; -------------------- topic 4: corner treatments -----------------------

(defun tutorial:c4 ( / q cs arcs cen k c)
  (tutorial:cap "4  CORNER TREATMENTS")
  (setq q (list (list 0.0 0.0) (list 300.0 0.0)
               (list 300.0 180.0) (list 0.0 180.0))
        cs (list (list "Radius" 30.0) (list "Cut" 40.0)
                 (list "NotGiven" 0.0) (list "Square" 0.0))
        cen (cal:v* (cal:v+ (cal:v+ (nth 0 q) (nth 1 q))
                              (cal:v+ (nth 2 q) (nth 3 q))) 0.25)
        arcs (pool:drawrect q cs))
  ;; one pane showing all four treatments at once: the radius dim, the
  ;; cut-face dim, the circled "?" with its Not Given note, and the
  ;; circled 90 on the plain square corner
  (setvar "CLAYER" "DIMENSION")
  (setq k 0)
  (foreach c cs
    (pool:dimtreat1 (pool:cornerends (nth k q)
                                     (nth (rem (+ k 3) 4) q)
                                     (nth (rem (+ k 1) 4) q)
                                     (car c) (cadr c) nil)
                    (car c) (nth k arcs) (nth k q)
                    (pool:unit (cal:v- (nth k q) cen)) 20.0 ""
                    (pool:polywedge q k))
    (setq k (1+ k)))
  (setvar "CLAYER" "POOL")
  (tutorial:frame (list -40.0 -40.0) (list 400.0 300.0))
  (princ "\n\n=== 4. CORNER TREATMENTS ===")
  (princ "\nRectangle, Grecian/Octagon, Roman and L/Lazy L corners can each be:")
  (tutorial:bullet "Square   -- a true sharp corner; circled on the drawing with a 90%%d leader (top-left, above).")
  (tutorial:bullet "Radius   -- you give the RADIUS; a fillet arc is drawn (bottom-left, above).")
  (tutorial:bullet "Cut      -- you give the CUT FACE length; a straight chamfer is drawn (bottom-right, above).")
  (tutorial:bullet "NotGiven -- the order sheet never said. Built square, but circled with a \"?\" and a Not Given note (top-right, above) so nobody reads it as a measured 90.")
  (princ "\nSide lengths always read to the TRUE (sharp) corner -- the")
  (princ "\ntreatment cuts inward from there, so a measured wall length never")
  (princ "\nchanges because you added a radius.")
  (tutorial:bullet "In-square: all four (or five, for L/Lazy L) corners get ONE answer, with a single \"Typ.\" callout in the drawing.")
  (tutorial:bullet "Out-of-square: every corner is asked individually -- but if all four answers come back the same type and size, they collapse to that same single \"Typ.\" callout instead of four separate dims.")
  (tutorial:bullet "Sizes are capped so two treatments on the same wall can never overlap and fold it -- too-large answers are re-asked with the max shown.")
  (tutorial:bullet "L/Lazy L: the five OUTER corners take one answer, the INNER corner (E) is asked separately since it's usually different (Enter reuses the outer answer).")
  (tutorial:bullet "Grecian/Octagon: the four BODY corners (A/B/C/D, where a side runs into a cut face) take one answer and the four END TIPS (LT/LB/RT/RB) another, Enter on the tips reusing the body answer.")
  (tutorial:bullet "Roman: the four true corners A/B/C/D take one answer; the S1 stubs then spring from the cut, and sizes are capped at the corner drop so a treatment cannot run past the arc spring.")
  (tutorial:bullet "Every shape except the rectangle asks 'Anything to record about the corners (radius / cut / not given)?' first, defaulting to No -- square is always the assumption.")
  (tutorial:bullet "The pool bottom's hopper ties connect to the ACTUAL corner cut on the deep-end wall, not the sharp corner behind it -- see topic 5.")
  (princ))

;;; -------------------- topic 5: the hopper ------------------------------

(defun tutorial:c5 ( / q gg tl)
  (tutorial:cap "5  THE POOL BOTTOM (HOPPER)")
  (setq q (list (list 0.0 0.0) (list 360.0 0.0)
               (list 360.0 200.0) (list 0.0 200.0)))
  (pool:drawrect q pool:*sq4*)
  (setq gg (pool:hopcalc q pool:*sq4* 50.0 90.0 120.0 40.0 40.0))
  (pool:hopdraw gg "POOL-NOTES" t)
  (setvar "CLAYER" "DIMENSION")
  (foreach tl (list (list 'pl 'phl nil) (list 'phl 'phr nil)
                    (list 'phr 'pbrk nil) (list 'pbrk 'pr nil)
                    (list 'pht 'pt t) (list 'phb 'pht t) (list 'pb 'phb t))
    (pool:dimalg (cadr (assoc (car tl) gg)) (cadr (assoc (cadr tl) gg))
                 (cal:v+ (cal:mid (cadr (assoc (car tl) gg))
                                    (cadr (assoc (cadr tl) gg)))
                          (if (caddr tl) (cadr (assoc 'voff gg)) (list 0.0 0.0)))))
  (setvar "CLAYER" "POOL")
  (tutorial:frame (list -40.0 -40.0) (list 460.0 260.0))
  (princ "\n\n=== 5. THE POOL BOTTOM (HOPPER) ===")
  (princ "\nOffered after the perimeter is drawn and dimensioned.  The")
  (princ "\nprimary letters are OFFSETS from the perimeter:")
  (tutorial:bullet "H / G / F / E along the main run: left end -> hopper start (H), hopper length (G), hopper -> slope break (F), break -> right end (E).")
  (tutorial:bullet "M / L / K across the width: top -> hopper (M), hopper width (L), hopper -> bottom (K).")
  (tutorial:bullet "F and L are redundant with the others and reported as CHECKS, with their delta against the perimeter.")
  (tutorial:bullet "The floor guide is LIVE too: each letter answered moves the hopper on the spot, the open letters splitting what the pool has left -- so the chain always closes against the walls and a wrong offset is visible immediately.  The side-profile styles dig their section live as C and D come in.")
  (princ "\nEvery other bottom is this SAME chain, just with letters pinned:")
  (tutorial:bullet "Wedge    -- G=0, E=0 (deep line at H, floor rises all the way to the far wall)")
  (tutorial:bullet "SLope    -- G=0 (deep line at H, rises to a full-width break, then flat)")
  (tutorial:bullet "MOdflat  -- E=0 (one flat pad, sloping up to every wall, no shallow flat)")
  (tutorial:bullet "SHallow  -- full hopper, but the shallow floor slopes from C2 up to C")
  (tutorial:bullet "Sport    -- the symmetric full-width bottom (E2/F2/G/F1/E1, no offsets)")
  (princ "\nGrecian/Octagon SIX-sided hoppers cut the deep pad's corners two")
  (princ "\nways: Offsets (every hopper line parallel to its wall, cut faces")
  (princ "\nparallel to the pool's own corner cuts) or Letters (the sheet's")
  (princ "\nW/X/L/L1 -- W is the flat, L1 the left edge, the faces just")
  (princ "\nconnect the corners and need not be parallel to anything).")
  (princ))

;;; -------------------- topic 6: validation & safety checks --------------

(defun tutorial:c6 ( / q cv vals fixed gg rows k tl)
  (tutorial:cap "6  VALIDATION -- G floored to 1', F pays, both RED")
  (setq q (list (list 0.0 0.0) (list 360.0 0.0)
               (list 360.0 180.0) (list 0.0 180.0)))
  (pool:drawrect q pool:*sq4*)
  ;; H 50 + G -30 + F 300 + E 40 cannot close on a 360-wide body:
  ;; G floors at a positive minimum and F, the largest OTHER member,
  ;; pays the difference -- exactly what pool:chainval does for real
  (setq cv (pool:chainval (list 50.0 -30.0 300.0 40.0) 360.0)
        vals (car cv) fixed (cadr cv)
        gg (pool:hopcalc q pool:*sq4* (nth 0 vals) (nth 1 vals) (nth 3 vals) 40.0 40.0))
  (pool:hopdraw gg "POOL" t)
  (setvar "CLAYER" "DIMENSION")
  (setq k 0)
  (foreach tl (list (list 'pl 'phl) (list 'phl 'phr)
                    (list 'phr 'pbrk) (list 'pbrk 'pr))
    (pool:dimalg (cadr (assoc (car tl) gg)) (cadr (assoc (cadr tl) gg))
                 (cal:mid (cadr (assoc (car tl) gg)) (cadr (assoc (cadr tl) gg))))
    (if (member k fixed) (pool:dimred))
    (setq k (1+ k)))
  (setvar "CLAYER" "POOL")
  (setq rows (list
    (pool:vrow "HOP H" 50.0 (nth 0 vals) 0 fixed)
    (pool:vrow "HOP G" -30.0 (nth 1 vals) 1 fixed)
    (pool:vrow "HOP F" 300.0 (nth 2 vals) 2 fixed)
    (pool:vrow "HOP E" 40.0 (nth 3 vals) 3 fixed)))
  (pool:report rows (list "BOTTOM LENGTHS FAILED - G/F ADJUSTED, VERIFY")
               420.0 180.0 8.0 "POOL-NOTES")
  (tutorial:frame (list -40.0 -40.0) (list 900.0 260.0))
  (princ "\n\n=== 6. VALIDATION & SAFETY CHECKS ===")
  (princ "\nField numbers do not always close.  POOL never just crashes or")
  (princ "\nsilently draws something wrong -- every check below adjusts,")
  (princ "\nflags RED (both in the dims and the report table), and writes a")
  (princ "\nplain-English note under the report so you know exactly what to")
  (princ "\nverify on site.  The example above: G resolved negative, so it's")
  (princ "\nfloored to a positive minimum and F -- the largest OTHER member")
  (princ "\n-- gives up the difference.")
  (princ "\n\nEverything POOL.LSP checks:")
  (tutorial:bullet "Negative chain members (H/G/F/E or M/L/K) are floored positive; the largest other member in the same chain pays the difference; both go red.")
  (tutorial:bullet "Grecian/Roman overall-sheet letters (S+T+S=B, S1+V+S1=A) must close positive -- warned BEFORE the bottom is even asked, reported red after.")
  (tutorial:bullet "Grecian/Octagon overall sheet: a measured WALL letter (T, V) is held true over its CORNER letter (S, S1) when the two disagree -- a wall is far easier to tape accurately than a virtual corner.")
  (tutorial:bullet "Corner-treatment sizes are capped so two treatments can never overlap and fold a wall.")
  (tutorial:bullet "Rectangle out-of-square Sport/SHallow depths: D must beat C, and C2 must land between C and D -- re-asked live until it does.")
  (tutorial:bullet "Oval/Roman end radius vs. width/offset (R3+W=G, or S from R and V) is checked and flagged if it does not close within tolerance.")
  (tutorial:bullet "SIX-sided hopper: W can't exceed G, L1 can't exceed L (floored + flagged); X is checked against the derived diagonal.")
  (tutorial:bullet "Cross dims: ordinary diagonals fit within +/-2\"; a Grecian tip-to-tip width or body-end chord is held like a WALL instead, within +/-1\" -- CROSS DIMS FAILED if neither can be met.")
  (tutorial:bullet "In-square lazy L: A-B stays exactly parallel to E-F, and B-C to D-E; any closure error lands in the E-F/F-A lengths, never in bent angles.")
  (tutorial:bullet "Back works from anywhere, one question (or one stage) at a time, all the way to the very first prompt.")
  (princ))

;;; -------------------- topic 7: dimension styles -------------------------

(defun tutorial:c7 ()
  (princ "\n\n=== 7. DIMENSION STYLES ===")
  (princ "\nThree named dim styles are used automatically WHEN YOUR DRAWING")
  (princ "\nDEFINES THEM -- the previous style always comes back right after,")
  (princ "\nand if a style is missing, POOL just quietly uses whatever style")
  (princ "\nwas already current (a one-time note for STANDARD INCHES, then")
  (princ "\nit stays quiet for the rest of the run).")
  (tutorial:bullet "CROSS DIMENSIONS -- every cross dim, on every shape. Pure ByLayer: no per-entity color/linetype/lineweight override, so the look comes entirely from that style and the DIMENSION layer.")
  (tutorial:bullet "STANDARD INCHES -- any dimension measuring UNDER 2' (24\"): corner radii, cut faces, short hopper offsets, end radii, profile depths. A dimension of EXACTLY 2' stays in the current style, not inches.")
  (tutorial:bullet "SIDE STANDARD -- the secondary sheet letters (Grecian/Octagon S/T/S1/V, Roman and Oval end radii, L wing and step sides, the six-sided hopper's W/L1/X). Wins over the under-24\" rule: a 19\" S1 stays in SIDE STANDARD, not inches.")
  (princ "\nThe styles nest correctly -- a small dimension drawn inside the")
  (princ "\ncross-dim block returns to CROSS DIMENSIONS afterward, not to")
  (princ "\nwhatever was current before the block opened.")
  (princ))

;;; -------------------- topic 8: report table & mirroring -----------------

(defun tutorial:c8 ( / rows elast a b c d e f)
  (tutorial:cap "8  THE REPORT TABLE, AND MIRRORING")
  (setq rows (list (list "SIDE A-B" 300.0 300.0)
                   (append (list "SIDE B-C" 180.0 181.4) (list t))
                   (list "HOP H" 50.0 50.0)))
  (pool:report rows nil 0.0 60.0 8.0 "POOL-NOTES")
  (princ "\n\n=== 8. THE REPORT TABLE, AND MIRRORING ===")
  (princ "\nEvery measurement you gave gets one row: TARGET (what you typed),")
  (princ "\nACTUAL (what was drawn) and DELTA.  A red row (like SIDE B-C,")
  (princ "\nabove) means a validator adjusted that value -- always double")
  (princ "\ncheck a red row against the site.  Failure notes print big and")
  (princ "\nred underneath the whole table.")
  (princ "\n\nWhen the drawing's units are Architectural or Engineering the")
  (princ "\nTARGET and ACTUAL columns read in feet-and-inches (DELTA stays")
  (princ "\nsigned decimal inches), and a small mini-model of the perimeter")
  (princ "\nis drawn beside the report carrying the measurement letters, so")
  (princ "\nthe letters never crowd the drawing itself.")
  (princ "\n\nL and Lazy L pools also offer to MIRROR the finished pool once")
  (princ "\nevery dimension is in -- the plan flips TOP-TO-BOTTOM about the")
  (princ "\npool's horizontal centreline (perimeter, dimensions AND hopper")
  (princ "\ntogether, text kept readable), so the wing swaps sides while the")
  (princ "\ndeep end stays on the left; the report itself is written")
  (princ "\nafterward, unmirrored.")
  (setq elast (entlast)
        a (list 480.0 0.0) b (list 780.0 0.0) c (list 780.0 240.0)
        d (list 630.0 240.0) e (list 630.0 120.0) f (list 480.0 120.0))
  (pool:line a b "POOL") (pool:line b c "POOL") (pool:line c d "POOL")
  (pool:line d e "POOL") (pool:line e f "POOL") (pool:line f a "POOL")
  (pool:mirrory elast (cadr (pool:wp (list 0.0 120.0))))
  (tutorial:frame (list -40.0 -40.0) (list 1120.0 300.0))
  (princ))

;;; -------------------- topic 9: wrap-up -----------------------------------

(defun tutorial:c9 ()
  (princ "\n\n=== 9. THAT'S THE TOUR ===")
  (princ (strcat "\nLoaded version: POOL " pool:*version*
                 " -- tutorial " tutorial:*version*))
  (princ "\nType POOLVER any time to check what's loaded in a drawing --")
  (princ "\nhandy for comparing what other people have in their stacks.")
  (princ "\n\nFull details on every shape, bottom, corner treatment, and")
  (princ "\nvalidation rule live in lisp/pool/README.md.")
  (princ "\n\nReady? Type POOL to lay out a real pool, or POOLDEMO for a")
  (princ "\nside-by-side reference sheet of every shape and bottom.")
  (princ))

;;; -------------------- the command ---------------------------------------

(defun c:TUTORIALPOOL ( / *error*)

  (defun *error* (msg)
    (if (and msg
             (not (wcmatch (strcase msg) "*BREAK*,*CANCEL*,*QUIT*,*EXIT*")))
        (princ (strcat "\nTUTORIALPOOL error: " msg)))
    (cal:sysrestore)
    (pool:undoend)
    (if *pop-error-mode* (*pop-error-mode*))
    (princ))

  (if (null pool:*version*)
      (progn
        (princ "\nLoad POOL.LSP first -- the tutorial draws with its geometry")
        (princ "\nhelpers, so it cannot run without it.")
        (princ))
      (tutorial:run))
  (princ))

(defun tutorial:run ( / topics textonly k org going fn)
  (if *push-error-using-command* (*push-error-using-command*))
  (cal:syssave '("OSMODE" "LUNITS" "CMDECHO" "CLAYER"))
  (setq pool:*valnotes* nil
        pool:*smallwarned* nil)
  (setvar "CMDECHO" 0)
  (pool:undobegin)
  (setvar "OSMODE" 0)
  (setvar "LUNITS" 4)

  (pool:layer "POOL" 4)
  (pool:layer "DIMENSION" 2)
  (pool:layer "POOL-NOTES" 3)
  (setq pool:*dashlt* (pool:ltload "DASHED")
        pool:*dotlt* (pool:ltload "DOT"))
  (setvar "CLAYER" "POOL")

  ;; topics 1, 7 and 9 are text-only -- no drawing, no origin needed
  (setq topics (list 'tutorial:c1 'tutorial:c2 'tutorial:c3 'tutorial:c4
                     'tutorial:c5 'tutorial:c6 'tutorial:c7 'tutorial:c8
                     'tutorial:c9)
        textonly (list 'tutorial:c1 'tutorial:c7 'tutorial:c9)
        k 0 going t)
  (foreach fn topics
    (if going
        (progn
          (if (member fn textonly)
              (apply fn nil)
              (progn
                (setq org (list (* tutorial:*colw* k) 0.0)
                      pool:*base* org)
                (apply fn nil)))
          (if (/= fn 'tutorial:c9) (setq going (tutorial:pause)))))
    (setq k (1+ k)))

  (command "_.ZOOM" "_Extents")
  (pool:undoend)
  (cal:sysrestore)
  (if *pop-error-mode* (*pop-error-mode*))
  (princ))

(princ (strcat "\nTUTORIALPOOL " tutorial:*version*
               " loaded.  Type TUTORIALPOOL for a guided walkthrough of POOL.LSP."))
(princ)


;;; ======================================================================
;;; >>> SPA.lsp
;;; ======================================================================

;;; ====================================================================
;;;  SPA.LSP -- Spa / hot-tub template layout tool
;;;
;;;  Command:  SPA
;;;
;;; SHARED BUILD: requires CALOFIN-LIB.lsp (load via CALOFIN-LOADER.lsp).
;;; Generic helpers live there under cal: - see STANDARDS.md.
;;;
;;;  Built from the same bones as POOL.LSP, cut down to the three
;;;  shapes a spa template actually needs:
;;;
;;;      Rectangle   four sides, every corner treated separately
;;;      Octagon     eight sides off the A / B overalls and the cuts
;;;      Round       circle, or an ellipse when the two overalls differ
;;;
;;;  WATER'S EDGE vs COVER SIZE
;;;  --------------------------
;;;  The first question asks which one is being drawn:
;;;
;;;    Watersedge  the perimeter is drawn DASHED on layer POOL and every
;;;                overall reads  <measurement> over  Water's Edge
;;;    Coversize   the perimeter is drawn on layer COVER and every
;;;                overall reads  <measurement> over  Cover Size
;;;
;;;  The note is stacked UNDER the measurement, across the dimension
;;;  line, the way the order sheet draws it:
;;;
;;;             95"
;;;       |--------------|
;;;          Cover Size
;;;
;;;  It goes on the OVERALLS only.  Corner callouts (radii, cut faces)
;;;  and the inboard flat dims are left plain, so a corner or a segment
;;;  note can never be mistaken for an overall.
;;;
;;;  BOTH OUTLINES
;;;  -------------
;;;  Once the first outline is drawn the command offers to add the other
;;;  one, either way round.  THE COVER IS ALWAYS THE LARGER of the two,
;;;  which settles the direction of travel:
;;;
;;;    Offset  ask how far the cover laps the water's edge and offset
;;;            OUTWARD (water's edge drawn first) or INWARD (cover drawn
;;;            first).  Radii grow and shrink with the offset, cut faces
;;;            by g * (2*sqrt2 - 2), and a treatment offset away to
;;;            nothing falls back to a 90 corner.
;;;    Dims    give the other outline as measured; the two are drawn
;;;            concentric.  The corner sizes are offered at whatever the
;;;            implied lap works out to, so Enter walks through when it
;;;            really is a parallel offset.
;;;
;;;  With both drawn, the COVER's overalls go outside -- across 2 ft
;;;  above it, up 3 ft to its left -- and the WATER'S EDGE's overalls go
;;;  a third of the way INTO the water's edge, hooked to points on the
;;;  dimension line itself so the arrows land on the outline.  A lone
;;;  outline always takes the outside pair.  One more dimension at the
;;;  bottom gives the OVERLAP: how far the cover laps the water's edge.
;;;
;;;  THERMO-LIGHT
;;;  ------------
;;;  Two rules make it a special case, so the Spa Cover Details block is
;;;  read BEFORE anything else is asked:
;;;    * its water's edge and cover size are the same, so that question
;;;      is skipped (drawn as COVER SIZE) and so is the offer to add the
;;;      other outline;
;;;    * every one of its hinges is velcro -- no dashed fold hinge.
;;;
;;;  AUTO-HINGE
;;;  ----------
;;;  After the cover is dimensioned the command offers to auto-hinge it.
;;;  Spillaways (corner or centred-on-a-wall) are asked first as no-go
;;;  zones, then the "Spa Cover Details" block supplies the grade and
;;;  taper, which set the foam width (max hinge spacing), foam length
;;;  (max hinge run) and the acceptable piece counts.  A taper can carry
;;;  MORE THAN ONE foam sheet and one may work where the other will not,
;;;  so every sheet is solved and scored before fewest pieces decides.
;;;  The longest hinge is then checked against the hinge-length chart
;;;  and velcro hinges / double C channel / hold down kit recommended.  The fewest hinges
;;;  that fit are placed evenly and nudged off the no-go zones; fold
;;;  vs velcro then follows the Hinge Arrangement Chart (pairs folding
;;;  from both ends), labels on the TEXT layer.  Anything out of spec --
;;;  foam length exceeded, piece count not acceptable, a zone that
;;;  could not be dodged -- is still drawn but flagged in the report.
;;;
;;;  DIMENSION STYLES
;;;  ----------------
;;;    cover size   "STANDARD INCHES"
;;;    water's edge "STANDARD INCHES 0.5"
;;;  A style the drawing already defines is used exactly as it stands --
;;;  the office template wins.  A missing one is built from the
;;;  standard-inches settings below, the water's edge at half the normal
;;;  furniture size.  The drawing's own current style is put back when
;;;  the command finishes.
;;;
;;;  STANDARD INCHES
;;;  ---------------
;;;  Every dimension is written in standard inches (fractional inches to
;;;  1/8" by default, with the inch mark appended) no matter how the host
;;;  drawing is set up, and every dimension line is placed OUTSIDE the
;;;  shape.  The dimension variables are set for the duration of the
;;;  command and restored afterwards; each dimension keeps the settings
;;;  as its own style override, so the numbers stay in inches after the
;;;  command is done.  See the adjustable constants below to change the
;;;  units or the precision.
;;;
;;;  DIMENSION LAYOUT
;;;  ----------------
;;;  The overall ACROSS goes on the TOP and the overall UP on the LEFT,
;;;  on every shape, with the text centred on its dimension line as
;;;  normal.  What else appears depends on the corners:
;;;
;;;    All four corners identical -- the two overalls plus ONE corner
;;;    callout with a Typ. suffix, at the bottom-right.  That is the
;;;    whole drawing for an all-radius or all-diagonal cover, and for a
;;;    true square octagon.  A plain 90-corner rectangle gets no corner
;;;    callout at all: the two overalls are the drawing.
;;;
;;;    Corners NOT identical -- each cut corner is called out on its own
;;;    (no Typ.), the square ones among them share one 90-degree mark,
;;;    and every side a cut has SHORTENED also gets its remaining FLAT
;;;    dimensioned, inboard of the overalls.  So a cover with one cut
;;;    top-right reads: overall across, overall up, the top flat, the
;;;    right flat, the cut face, and 90 Typ. on the square corners.
;;;
;;;  The round spa takes one overall; only an out-of-round one gets the
;;;  second.  An octagon whose eight sides come out unequal picks up the
;;;  bottom and right flats the same way the rectangle does.
;;;
;;;  RECTANGLE CORNERS
;;;  -----------------
;;;  A corner is Radius (sized by its radius), Diagonal (a cut, sized by
;;;  its face length) or 90 -- the sheet's own corner legend.  Side
;;;  lengths are always to the TRUE (sharp) corner; the treatment cuts
;;;  inward from there.  Corner A is asked first and its answer
;;;  AUTOFILLS corners B, C and D -- press Enter at each to accept it, or
;;;  type a different treatment for that corner, so a cover with two cut
;;;  corners and two square ones takes four different answers.
;;;
;;;  Callouts sit outside the corner on its 45-degree line: a radius dim
;;;  on a Radius corner (R12"), an aligned dim across a Diagonal cut
;;;  face (21"), and a circled corner point with a 90%%d leader on a 90
;;;  corner.
;;;
;;;  Corner naming (plan view):   D ---------- C
;;;                               |            |
;;;                               |            |
;;;                               A ---------- B
;;;
;;;  Octagon corner naming runs counter-clockwise from the left end of
;;;  the bottom flat:  A B (bottom flat), C D (right flat), E F (top
;;;  flat), G H (left flat); the four cuts are B-C, D-E, F-G and H-A.
;;;
;;;  Distances may be typed in the current drawing units, e.g. 6'10-1/2"
;;;  as well as plain inches -- or in MILLIMETRES by putting the unit on
;;;  the number: 600mm, 1524 MM.  Object snaps stay live, so a distance
;;;  can still be picked off existing geometry instead of typed.
;;;
;;;  Each outline is drawn as ONE CLOSED POLYLINE, so the cover and the
;;;  water's edge are each a single bounded entity: one click selects
;;;  either, each encloses an area, and either can be offset, hatched or
;;;  handed to the tools that work on a highlighted perimeter.  "Back" at any prompt after the first
;;;  re-asks the previous question.
;;;
;;;  Written in plain AutoLISP (entmake + classic commands, no
;;;  ActiveX/VLA), so it loads in AutoCAD 2018 as well as older releases.
;;; ====================================================================

;;; -------------------- version ----------------------------------------
;;;  This file ships twice under two names with IDENTICAL contents:
;;;
;;;      SPA.LSP                 the static name, for the APPLOAD stack
;;;      SPA_MMDDYY_REV##.LSP    the same file, named for its revision
;;;
;;;  Load either one.  The version below travels inside both, so a stack
;;;  that loaded the static name can still say which revision it holds:
;;;  type SPAVER.  Regenerate the pair with tools/release.py.

(setq spa:*version* "082726 REV09")

;;; -------------------- adjustable constants --------------------------

;; Dimension text units.  5 = Fractional inches (84-1/2), 2 = Decimal
;; inches (84.50).  Anything but 4 (Architectural) keeps the numbers in
;; standard inches instead of rolling them up into feet.
(setq spa:*dimlunit* 5)
(setq spa:*dimprec*  3)         ; 5 -> 1/8", 2 -> 3 decimal places
(setq spa:*dimpost*  "\"")      ; suffix stuck on every measurement

;; How far the dimension lines stand off the cover outline, and where
;; the Water's Edge / Cover Size note sits along its dimension line.
(setq spa:*dimoff*    36.0)     ; 3 ft: cover outline -> the LEFT overall dim
(setq spa:*topoff*    24.0)     ; 2 ft: cover outline -> the TOP overall dim
(setq spa:*flatoff*   18.0)     ; outline -> the inboard flat dims
(setq spa:*insetfrac* 0.3333)   ; water's edge dims, a third of the way in
(setq spa:*lapoff*    14.0)     ; how far under the cover the lap note sits

;; Hinge lettering and linework, matched to the office template's
;; before/after sample: labels are MTEXT in the Attributes style at a
;; fixed 5" height, bottom-centred 3" off the line; the fold hinge is
;; drawn in the stock DASHED2 linetype at an effective 5" dash.
(setq spa:*hingetxth*  5.0)     ; hinge label height
(setq spa:*hingetxw*  60.0)     ; hinge label MTEXT frame width
(setq spa:*hingestyle* "Attributes")  ; label style (Standard when absent)
(setq spa:*hdashmult* 20.0)     ; DASHED2 0.25" dash x 20 = 5" on paper

(setq spa:*sfx-water* "Water's Edge")
(setq spa:*sfx-cover* "Cover Size")
(setq spa:*lay-water* "POOL")   ; water's edge perimeter layer (dashed)
(setq spa:*lay-cover* "COVER")  ; cover size perimeter layer

;; Dimension styles, one per outline.  A style the drawing already
;; defines is used exactly as it stands -- the office template wins --
;; and one that is missing is built from the standard-inches settings
;; below, the water's edge at spa:*wefactor* of the normal furniture
;; size (the 0.5 in its name).
(setq spa:*ds-cover*  "STANDARD INCHES")
(setq spa:*ds-water*  "STANDARD INCHES 0.5")
(setq spa:*wefactor*  0.5)
(setq spa:*gapdflt*   3.0)      ; suggested cover lap over the water's edge

(setq spa:*base*     (list 0.0 0.0))
(setq spa:*dashlt*   "CONTINUOUS")   ; resolved to SPADASH per run
(setq spa:*dotlt*    "CONTINUOUS")   ; resolved to SPADOT per run
(setq spa:*pvents*   nil)            ; live guide-preview entities
(setq spa:*valnotes* nil)            ; validation problems for the report
(setq spa:*undogrp*  nil)            ; an UNDO group of ours is open

(setq spa:*perlay*   "POOL")         ; active perimeter layer
(setq spa:*perdash*  t)              ; draw the perimeter dashed
(setq spa:*sfx*      "")             ; active dimension suffix
(setq spa:*modename* "WATER'S EDGE") ; note written under the drawing
(setq spa:*mode*     "Watersedge")   ; which outline is being drawn
(setq spa:*dstyle*   "STANDARD INCHES 0.5")   ; its dimension style
(setq spa:*dsfac*    0.5)                     ; its furniture factor
(setq spa:*turned*   nil)            ; the cover was turned 90 to lie long-ways
(setq spa:*hingerows* nil)           ; hinge/spillaway rows for the report
(setq spa:*advice*    nil)           ; hardware recommendations
(setq spa:*grade*     nil)           ; from the Spa Cover Details block
(setq spa:*taper*     nil)

;;; -------------------- small vector helpers --------------------------

(defun spa:unit (p / d)
  (setq d (sqrt (cal:dot p p)))
  (if (> d 1.0e-12) (cal:v* p (/ 1.0 d)) (list 0.0 0.0)))

;; local 2D point -> world 3D point (applies the insertion base)
(defun spa:wp (p)
  (list (+ (car p) (car spa:*base*))
        (+ (cadr p) (cadr spa:*base*))
        0.0))

;;; -------------------- geometry ---------------------------------------

;; Circumcenter of three points, or nil when collinear.
(defun spa:circum (p1 p2 p3 / ax ay bx by cx cy dd)
  (setq ax (car p1) ay (cadr p1)
        bx (car p2) by (cadr p2)
        cx (car p3) cy (cadr p3)
        dd (* 2.0 (+ (* ax (- by cy)) (* bx (- cy ay)) (* cx (- ay by)))))
  (if (> (abs dd) 1.0e-9)
      (list (/ (+ (* (+ (* ax ax) (* ay ay)) (- by cy))
                  (* (+ (* bx bx) (* by by)) (- cy ay))
                  (* (+ (* cx cx) (* cy cy)) (- ay by)))
               dd)
            (/ (+ (* (+ (* ax ax) (* ay ay)) (- cx bx))
                  (* (+ (* bx bx) (* by by)) (- ax cx))
                  (* (+ (* cx cx) (* cy cy)) (- bx ax)))
               dd))))

;; Is p inside the polygon poly (crossing number)?
(defun spa:inpoly (p poly / n i j xi yi xj yj in x y)
  (setq x (car p) y (cadr p)
        n (length poly)
        i 0 j (1- n) in nil)
  (while (< i n)
    (setq xi (car (nth i poly)) yi (cadr (nth i poly))
          xj (car (nth j poly)) yj (cadr (nth j poly)))
    (if (and (or (and (> yi y) (<= yj y))
                 (and (> yj y) (<= yi y)))
             (< x (+ xi (* (- xj xi) (/ (- y yi) (- yj yi))))))
        (setq in (not in)))
    (setq j i i (1+ i)))
  in)

;; Midpoint of p->q offset by dist to the side that lies OUTSIDE poly --
;; every dimension in this file is placed with one of these two.
(defun spa:outoffp (p q poly dist / m n)
  (setq m (cal:mid p q)
        n (spa:unit (cal:perp (cal:v- q p))))
  (if (spa:inpoly (cal:v+ m (cal:v* n 1.0)) poly)
      (setq n (cal:v* n -1.0)))
  (cal:v+ m (cal:v* n dist)))

;; Point offset outward (away from cen) from the midpoint of p->q.
(defun spa:outoff (p q cen dist / m n)
  (setq m (cal:mid p q)
        n (spa:unit (cal:perp (cal:v- q p))))
  (if (< (cal:dot (cal:v- m cen) n) 0.0)
      (setq n (cal:v* n -1.0)))
  (cal:v+ m (cal:v* n dist)))

;; Corner-label position: away from the centroid, flipped when that
;; lands inside the shape.
(defun spa:lbloff (p cen poly dist / dir cand)
  (setq dir (spa:unit (cal:v- p cen))
        cand (cal:v+ p (cal:v* dir dist)))
  (if (spa:inpoly cand poly)
      (cal:v+ p (cal:v* dir (- dist)))
      cand))

(defun spa:centroid (pts / cen p)
  (setq cen (list 0.0 0.0))
  (foreach p pts (setq cen (cal:v+ cen p)))
  (cal:v* cen (/ 1.0 (float (length pts)))))

;;; -------------------- entity makers ----------------------------------

;; Create the output layer, or - when it already exists - make sure it
;; is on, thawed and unlocked (STANDARDS section 5).  Without the repair
;; a run onto a frozen or switched-off DIMENSION layer looks like the
;; command drew nothing.
(defun spa:layer (name color / rec ed flags col fixed)
  (if (not (tblsearch "LAYER" name))
      (entmake (list '(0 . "LAYER")
                     '(100 . "AcDbSymbolTableRecord")
                     '(100 . "AcDbLayerTableRecord")
                     (cons 2 name)
                     '(70 . 0)
                     (cons 62 color)
                     '(6 . "Continuous")))
      (progn
        (setq rec   (tblobjname "LAYER" name)
              ed    (entget rec)
              flags (cdr (assoc 70 ed))
              col   (cdr (assoc 62 ed))
              fixed nil)
        (if (/= 0 (logand 5 flags))          ; frozen (1) or locked (4)
            (setq ed    (subst (cons 70 (- flags (logand 5 flags)))
                               (assoc 70 ed) ed)
                  fixed T))
        (if (< col 0)                        ; layer switched off
            (setq ed    (subst (cons 62 (abs col)) (assoc 62 ed) ed)
                  fixed T))
        (if fixed
            (progn
              (entmod ed)
              (princ (strcat "\nSPA: layer " name
                             " was off, frozen or locked - restored so"
                             " the result is visible."))))))
  name)

;; Build a linetype from an explicit pattern (positive = dash length,
;; 0 = dot, negative = gap), all in drawing units (inches).  Done with
;; entmake rather than loading acad.lin so a failed load can never fall
;; back to CONTINUOUS silently.  Returns the linetype name.
(defun spa:ltmake (name descr pat / lst x)
  (if (not (tblsearch "LTYPE" name))
      (progn
        (setq lst (list '(0 . "LTYPE")
                        '(100 . "AcDbSymbolTableRecord")
                        '(100 . "AcDbLinetypeTableRecord")
                        (cons 2 name)
                        '(70 . 0)
                        (cons 3 descr)
                        '(72 . 65)
                        (cons 73 (length pat))
                        (cons 40 (apply '+ (mapcar 'abs pat)))))
        (foreach x pat
          (setq lst (append lst (list (cons 49 x) '(74 . 0)))))
        (entmake lst)))
  (if (tblsearch "LTYPE" name) name "CONTINUOUS"))

;; Per-entity linetype scale that cancels the drawing's LTSCALE, so a
;; pattern defined in inches always plots at that size.
(defun spa:ltsc ( / s)
  (setq s (getvar "LTSCALE"))
  (if (or (null s) (<= s 0.0)) 1.0 (/ 1.0 s)))

;; Spa-scale dash / dot patterns (a spa is a fraction of a pool's size,
;; so the pool's 12" dash would read as a solid line here).
(defun spa:ltload (name)
  (if (= name "DOT")
      (spa:ltmake "SPADOT" "Spa guide dot . . . . . . . ." '(0.0 -3.0))
      (spa:ltmake "SPADASH" "Spa dashed __ __ __ __" '(4.0 -3.0))))

;; extra = a list of extra DXF pairs (linetype override and friends).
(defun spa:line (p1 p2 lay extra)
  (entmake (append (list '(0 . "LINE")
                         (cons 8 lay)
                         (cons 10 (spa:wp p1))
                         (cons 11 (spa:wp p2)))
                   extra)))

;; Three-point arc through p1 -> p2 -> p3 (falls back to a line when
;; the points are collinear).
(defun spa:arc3p (p1 p2 p3 lay extra / o r a1 a2 a3 da2 da3 s e)
  (setq o (spa:circum p1 p2 p3))
  (if o
      (progn
        (setq r  (distance o p1)
              a1 (angle o p1)
              a2 (angle o p2)
              a3 (angle o p3)
              da2 (cal:angnorm (- a2 a1))
              da3 (cal:angnorm (- a3 a1)))
        (if (< da2 da3)
            (setq s a1 e a3)
            (setq s a3 e a1))
        (entmake (append (list '(0 . "ARC")
                               (cons 8 lay)
                               (cons 10 (spa:wp o))
                               (cons 40 r)
                               (cons 50 s)
                               (cons 51 e))
                         extra)))
      (spa:line p1 p3 lay extra)))

;; Circle (a = b) or axis-aligned ellipse.  The DXF ratio is minor over
;; MAJOR and must never exceed 1, so the axis that is actually longer
;; becomes the major one.
(defun spa:body-round (cen b a lay extra / maj rat)
  (if (< (abs (- a b)) 1.0e-6)
      (entmake (append (list '(0 . "CIRCLE")
                             (cons 8 lay)
                             (cons 10 (spa:wp cen))
                             (cons 40 (* 0.5 b)))
                       extra))
      (progn
        (if (>= b a)
            (setq maj (list (* 0.5 b) 0.0 0.0) rat (/ a b))
            (setq maj (list 0.0 (* 0.5 a) 0.0) rat (/ b a)))
        (entmake (append (list '(0 . "ELLIPSE")
                               '(100 . "AcDbEntity")
                               (cons 8 lay)
                               '(100 . "AcDbEllipse")
                               (cons 10 (spa:wp cen))
                               (cons 11 maj)              ; major axis, relative
                               (cons 210 '(0.0 0.0 1.0))
                               (cons 40 rat)              ; minor / major
                               (cons 41 0.0)
                               (cons 42 (* 2.0 pi)))
                         extra)))))

(defun spa:text (pt h str lay)
  (entmake (list '(0 . "TEXT")
                 (cons 8 lay)
                 (cons 10 (spa:wp pt))
                 (cons 40 h)
                 (cons 1 str))))

(defun spa:textc (pt h str lay col)
  (entmake (list '(0 . "TEXT")
                 (cons 8 lay)
                 (cons 62 col)
                 (cons 10 (spa:wp pt))
                 (cons 40 h)
                 (cons 1 str))))

;;; -------------------- which outline is being drawn -------------------
;;;
;;;  Everything that differs between the two outlines -- layer, linetype,
;;;  dimension note, dimension style -- hangs off one switch, so the
;;;  command can draw one, flip, and draw the other.

(defun spa:setmode (m)
  (setq spa:*mode* m)
  (if (= m "Watersedge")
      (setq spa:*perlay*   spa:*lay-water*
            spa:*perdash*  t
            spa:*sfx*      spa:*sfx-water*
            spa:*modename* "WATER'S EDGE"
            spa:*dstyle*   spa:*ds-water*
            spa:*dsfac*    spa:*wefactor*)
      (setq spa:*perlay*   spa:*lay-cover*
            spa:*perdash*  nil
            spa:*sfx*      spa:*sfx-cover*
            spa:*modename* "COVER SIZE"
            spa:*dstyle*   spa:*ds-cover*
            spa:*dsfac*    1.0))
  m)

(defun spa:othermode ()
  (if (= spa:*mode* "Watersedge") "Coversize" "Watersedge"))

(defun spa:modeword (m)
  (if (= m "Watersedge") "water's edge" "cover size"))

;;; -------------------- the perimeter itself ---------------------------
;;;  Water's edge -> dashed, on the POOL layer.
;;;  Cover size   -> solid, on the COVER layer.

(defun spa:perdxf ()
  (if (and spa:*perdash* (/= spa:*dashlt* "CONTINUOUS"))
      (list (cons 6 spa:*dashlt*) (cons 48 (spa:ltsc)))))

(defun spa:perline (p1 p2) (spa:line p1 p2 spa:*perlay* (spa:perdxf)))

(defun spa:perarc3p (p1 p2 p3) (spa:arc3p p1 p2 p3 spa:*perlay* (spa:perdxf)))

(defun spa:perround (cen b a) (spa:body-round cen b a spa:*perlay* (spa:perdxf)))

;; tan(theta/4) -- the DXF bulge of an arc segment sweeping theta.
(defun spa:bulge (th) (/ (sin (* 0.25 th)) (cos (* 0.25 th))))

;; The perimeter as ONE closed LWPOLYLINE rather than a handful of loose
;; lines and arcs, so each outline is a single bounded entity: it picks
;; in one click, encloses an area, and can be offset, hatched or handed
;; to the tools that expect a highlighted perimeter (STOCKCOVER, PADDLE,
;; AUTOBEAD).  verts is a list of (point . bulge) walked counter-
;; clockwise; a bulge of 0 is a straight run to the next vertex.
;; Returns the polyline's entity name.
(defun spa:perpoly (verts / lst v p)
  (setq lst (append (list '(0 . "LWPOLYLINE")
                          '(100 . "AcDbEntity")
                          (cons 8 spa:*perlay*)
                          '(100 . "AcDbPolyline")
                          (cons 90 (length verts))
                          '(70 . 1))          ; closed
                    (spa:perdxf)))
  (foreach v verts
    (setq p (spa:wp (car v))
          lst (append lst (list (cons 10 (list (car p) (cadr p)))
                                (cons 42 (cdr v))))))
  (entmake lst)
  (entlast))

;; Dotted WHITE guide line -- the measuring ties on the input screen.
(defun spa:linedot (p1 p2)
  (spa:line p1 p2 "SPA-NOTES"
            (append (list (cons 62 spa:*pvx-col*))
                    (if (/= spa:*dotlt* "CONTINUOUS")
                        (list (cons 6 spa:*dotlt*) (cons 48 (spa:ltsc)))))))

;;; -------------------- dimensions in standard inches ------------------
;;;
;;;  Every dimension this command makes is written in standard inches,
;;;  placed outside the shape, and (for overalls and sides, never for
;;;  corners) suffixed with the Water's Edge / Cover Size note.

(setq spa:*dimvars*
      '("DIMLUNIT" "DIMFRAC" "DIMDEC" "DIMZIN" "DIMPOST" "DIMTAD" "DIMTMOVE"
        "DIMTXT" "DIMASZ"
        "DIMEXE" "DIMEXO" "DIMGAP" "DIMSCALE" "DIMTIX" "DIMTOFL" "DIMATFIT"))

;; setvar that quietly skips a variable this release does not have.
(defun spa:setv (v val)
  (if (/= nil (getvar v)) (setvar v val)))

;; th = the drawing's note text height; the dimension furniture is sized
;; off it so the numbers read at any spa size.
(defun spa:dimsetup (th)
  (spa:setv "DIMLUNIT" spa:*dimlunit*)  ; 5 = fractional inches
  (spa:setv "DIMFRAC"  0)               ; 39 3/8, stacked fraction
  (spa:setv "DIMTAD"   0)               ; text straddles the dim line (\X)
  (spa:setv "DIMTMOVE" 2)               ; text may slide along without a leader
  (spa:setv "DIMDEC"   spa:*dimprec*)
  (spa:setv "DIMZIN"   8)               ; no trailing zeros
  (spa:setv "DIMPOST"  spa:*dimpost*)   ; the inch mark
  (spa:setv "DIMSCALE" 1.0)             ; sizes below are already real
  (spa:setv "DIMTXT"   th)
  (spa:setv "DIMASZ"   (* 0.8 th))
  (spa:setv "DIMEXE"   (* 0.6 th))
  (spa:setv "DIMEXO"   (* 0.6 th))
  (spa:setv "DIMGAP"   (* 0.4 th))
  (spa:setv "DIMTIX"   0)               ; text may go outside...
  (spa:setv "DIMTOFL"  1)               ; ...but keep the dimension line
  (spa:setv "DIMATFIT" 3)
  (princ))

;; The tail of an OVERALL dimension's text override.  \X splits the
;; text across the dimension line, so an overall reads as the order
;; sheet draws it -- the measurement on top, the note stacked under it:
;;        95"
;;     Cover Size
(defun spa:ovnote () (strcat "\\X" spa:*sfx*))

;; Put the outline's named dimension style in charge of the dims that
;; follow.  A style the drawing already defines is restored untouched --
;; the office template wins.  A missing one is built from the
;; standard-inches settings at `fac` times the normal furniture size and
;; saved under the name, so the drawing ends up carrying both styles.
(defun spa:dimstyle (name th fac)
  (if (tblsearch "DIMSTYLE" name)
      (command "_.-DIMSTYLE" "_Restore" name)
      (progn
        (spa:dimsetup (* th fac))
        (command "_.-DIMSTYLE" "_Save" name)))
  ;; whatever the style says, the note has to be free to slide along its
  ;; dimension line without dragging the line or growing a leader
  (spa:setv "DIMTMOVE" 2)
  (princ))

;; The style for whichever outline is being drawn right now.
(defun spa:dimstylenow (th) (spa:dimstyle spa:*dstyle* th spa:*dsfac*))

;; Aligned dimension between two points, dragged to pt.  note is appended
;; to the measurement inside a text override ("\\XCover Size" to stack it,
;; " Typ." to run it on); pass nil for a plain dimension.
(defun spa:dimalg (p1 p2 pt note)
  (if (and note (/= note ""))
      (command "_.DIMALIGNED" (spa:wp p1) (spa:wp p2)
               "_T" (strcat "<>" note) (spa:wp pt))
      (command "_.DIMALIGNED" (spa:wp p1) (spa:wp p2) (spa:wp pt))))

;; Park a dimension's text at an explicit point.  DXF 11 is the text
;; midpoint and bit 128 of DXF 70 marks it as user-placed.  Used only for
;; the overlap note, which is far too small to hold its own text.
(defun spa:dimtextat (e pt / ed f)
  (if (and e (setq ed (entget e)) (= "DIMENSION" (cdr (assoc 0 ed)))
           (assoc 11 ed) (assoc 70 ed))
      (progn
        (setq f  (cdr (assoc 70 ed))
              ed (subst (cons 11 (spa:wp pt)) (assoc 11 ed) ed)
              ed (subst (cons 70 (logior f 128)) (assoc 70 ed) ed))
        (entmod ed)
        (entupd e)))
  (princ))

;; An OVERALL dimension: the measurement over the Water's Edge / Cover
;; Size note, both centred on the dimension line as normal.
(defun spa:dimov (p1 p2 loc)
  (spa:dimalg p1 p2 loc (spa:ovnote)))

;; Radius dimension read from OUTSIDE the arc: the arc is picked at its
;; far point and the dimension line dragged further out along the same
;; direction, so the leader comes in from outside.
(defun spa:dimrad (ent tip outd doff sfx)
  (if (and ent (entget ent)
           (member (cdr (assoc 0 (entget ent))) '("ARC" "LWPOLYLINE")))
      (if (and sfx (/= sfx ""))
          (command "_.DIMRADIUS" (list ent (spa:wp tip))
                   "_T" (strcat "<>" sfx)
                   (spa:wp (cal:v+ tip (cal:v* outd (* 0.9 doff)))))
          (command "_.DIMRADIUS" (list ent (spa:wp tip))
                   (spa:wp (cal:v+ tip (cal:v* outd (* 0.9 doff))))))
      (princ "\n(radius dim skipped -- that corner came out flat, no arc)")))

;;; -------------------- user input -------------------------------------
;;;
;;;  The user's own object snaps stay LIVE during every measurement
;;;  prompt (typed input is unaffected; a picked point can snap onto
;;;  existing geometry).  OSMODE is zeroed only while the routine feeds
;;;  points to commands, where a snap would grab the wrong geometry.

;;; -------------------- measurement sequences (Back) -------------------
;;;
;;;  A block of related measurements runs through spa:askseqb so every
;;;  prompt after the first also offers *Back*, which re-asks the
;;;  previous question -- a typo no longer means Esc and start over.
;;;  Each item: (key kind msg ents dflt)
;;;    key   symbol the answer is stored under
;;;    kind  REQ  a value is required
;;;          NAX  NA accepted (returns nil)
;;;          SUG  NA accepted, suggested default (Enter takes it)
;;;    ents  guide entities highlighted while prompted
;;;    dflt  for SUG: a number, or a list of keys -- the first of those
;;;          keys with a non-nil answer supplies the suggestion

(defun spa:sq (ans key) (cdr (assoc key ans)))

(defun spa:sqput (ans key v / out p)
  (foreach p ans (if (not (eq (car p) key)) (setq out (cons p out))))
  (reverse (cons (cons key v) out)))

(defun spa:sqfirst (ans keys / out k)
  (foreach k keys
    (if (and (not out) (spa:sq ans k)) (setq out (spa:sq ans k))))
  out)

;; One prompt of a sequence.  Returns the value, nil for NA, or the
;; symbol CAL-BACK.
;;; -------------------- form answers -----------------------------------
;;;
;;;  A form -- the VB palette's spa tab -- can answer some or all of
;;;  SPA's questions before the run starts.  It leaves them in
;;;  spa:*form* as (key . value) and the ask sites below look there
;;;  first, so a filled-in sheet drives the whole run and a half-filled
;;;  one simply shortens it.  POOL.LSP grew this first; the contract
;;;  and the reasons are its "form answers" section, held to exactly
;;;  here so the two stores can never disagree:
;;;
;;;    key absent      the form did not answer it   -> ask, as usual
;;;    (key . nil)     the form answered NA         -> nil, no prompt
;;;    (key . 84.0)    the form answered it         -> 84.0, no prompt
;;;
;;;  AN ANSWER IS REMOVED AS IT IS USED.  Not marked used -- removed.
;;;  Otherwise Back deadlocks: step back onto a form-answered question,
;;;  it answers itself instantly and walks forward again, and there is
;;;  no key the user can press to get out.  Consuming also lets a value
;;;  a range check rejects be retyped at the keyboard instead of re-fed
;;;  for ever.

(setq spa:*form* nil)

;; Did the form answer KEY at all?  This is the absent/nil distinction
;; that (cdr (assoc ...)) throws away.
(defun spa:fhas (key) (if (assoc key spa:*form*) t nil))

;; The form's answer for KEY, removed from the store as it is read.
(defun spa:ftake (key / p)
  (setq p (assoc key spa:*form*))
  (setq spa:*form* (vl-remove p spa:*form*))
  (cdr p))

(defun spa:fclear () (setq spa:*form* nil))

;; V as the question would spell it, or nil when the question does not
;; accept it at all -- so a form answer the prompt would reject falls
;; through to the prompt, and the canonical SPELLING comes back rather
;; than the caller's (every test downstream compares exact strings).
(defun spa:fkword (v kws / i n c w out)
  (setq i 1 n (strlen kws) w "" v (strcase v))
  (while (<= i (1+ n))
    (setq c (if (<= i n) (substr kws i 1) " "))
    (if (= c " ")
        (progn
          (if (and (/= w "") (= (strcase w) v)) (setq out w))
          (setq w ""))
        (setq w (strcat w c)))
    (setq i (1+ i)))
  out)

;; The keyword question a form can answer.  Deliberately a WRAPPER and
;; not a sixth argument on spa:askkw: the grouped build swaps that
;; helper out for cal:askkw, which takes five, so widening it here
;; would have the twin call the library with an argument it does not
;; accept -- a build that loads cleanly and dies at the first keyword
;; question.  The mirror leaves this defun alone, while the spa:askkw
;; call inside it is rewritten like any other call site.
(defun spa:askkwf (key msg kws shown dflt back / v)
  (if (and (spa:fhas key)
           (setq v (spa:ftake key))
           (= (type v) 'STR)
           (setq v (spa:fkword v kws)))
      v
      (cal:askkw msg kws shown dflt back)))

;; The form-key stem for a corner question, from the label every flow
;; already passes spa:askcorner -- "Corner A" is cornera.  A label no
;; form addresses comes back nil and the corner is asked as always.
(defun spa:fckey (label / s)
  (setq s (strcase label t))
  (if (and (> (strlen s) 7) (= (substr s 1 7) "corner "))
      (strcat "corner" (substr s 8))))

;; The shape, from the form when it named one the dispatch knows, else
;; asked.  Checked against the same list the prompt offers: an unknown
;; shape would fall through the cond at the foot of c:SPA into the
;; rectangle branch and draw the wrong spa without saying so.
(defun spa:fshape ( / v)
  (if (spa:fhas 'shape) (setq v (spa:ftake 'shape)))
  ;; the shape word is matched WITHOUT case, and comes back in the
  ;; canonical spelling.  A chart or a palette written against the old
  ;; "ROund" keeps working (LAZSPA's dropdown still reads ROund), and
  ;; the routine still stores the one spelling the dispatch tests for.
  (if (and v (= (type v) 'STR))
      (setq v (spa:fkword v "Rectangle OCtagon ROUnd")))
  (if v
      v
      (progn
        ;; ROUnd, not ROund: one capitalisation repo-wide (POOL's list
        ;; needs RO for ROman, so the shared abbreviation is ROU)
        (initget 1 "Rectangle OCtagon ROUnd")
        (getkword "\nSpa shape [Rectangle/OCtagon/ROUnd]: "))))

;; THERMOLIGHT closes the water's-edge question the same way the block
;; does; spa:askdetails calls it again so a store armed past c:SPA's
;; own read still lands.  An answer that is not a grade/taper string is
;; consumed all the same -- and then ignored, so the run falls back to
;; asking exactly as if the box had been left empty.
(defun spa:formdetails ( / v)
  (if (spa:fhas 'grade)
      (progn
        (setq v (spa:ftake 'grade))
        (if (= (type v) 'STR)
            (setq spa:*grade* (spa:gradenorm v)))))
  (if (spa:fhas 'taper)
      (progn
        (setq v (spa:ftake 'taper))
        (if (and (= (type v) 'STR) (spa:tapernorm v))
            (setq spa:*taper* (spa:tapernorm v))))))

;; Run SPA with a form's answers already in hand.  Nothing happens
;; here that the direct path misses: a caller may equally set
;; spa:*form* itself and call c:SPA, which is what the tests do.
(defun spa:run-with-answers (answers)
  (setq spa:*form* answers)
  (c:SPA)
  (spa:fclear)
  (princ))

(defun spa:asks (kind msg ents dflt back / v cols kw e out)
  (setq cols (mapcar 'spa:getcol ents))
  (foreach e ents (spa:setcol e spa:*hi-col*))
  (cal:osup)
  ;; Undo is accepted everywhere Back is, as a hidden synonym
  (setq kw (cond ((eq kind 'REQ) (if back "Back Undo" nil))
                 (back "NA Back Undo")
                 (t "NA")))
  (while (null out)
    ;; 128 = arbitrary input, so a value typed in millimetres reaches us
    ;; as text for spa:mmval rather than being rejected by getdist
    (if kw
        (initget (+ (if (and (eq kind 'SUG) dflt) 6 7) 128) kw)
        (initget (+ 7 128)))
    (setq v (getdist
              (strcat "\n" msg
                      (cond ((eq kind 'REQ) "")
                            ((eq kind 'SUG)
                             (if dflt (strcat " <" (rtos dflt) "> (or NA)")
                                 " (or NA)"))
                            (t " (or NA if not measured)"))
                      (if back " [Back]" "")
                      ": ")))
    (cond
      ((and (= (type v) 'STR) (member v '("Back" "Undo"))) (setq out 'CAL-BACK))
      ((and (= (type v) 'STR) (= v "NA")) (setq out 'SPA-NA))
      ((and (null v) (eq kind 'SUG)) (setq out dflt))   ; Enter took it
      ((setq out (spa:dval v)))
      (t (princ "\nNot a measurement -- type inches, 6'10\", or 600mm."))))
  (cal:osdown)
  (mapcar '(lambda (e c) (spa:setcol e c)) ents cols)
  (if (eq out 'SPA-NA) nil out))

;; Millimetres, typed with the unit on the number: 600mm, 600 MM,
;; 1524.5mm.  The drawing is in inches, so the value is converted.
;; Returns the distance in inches, or nil when the text is not that --
;; which is how the callers tell a mm answer from a typo.
;;
;; getdist cannot parse this itself, so the prompts that accept it set
;; initget's bit 128 (arbitrary input): a value getdist understands
;; still comes back as a number, and anything else comes back as the
;; raw string for this to look at.  Point picking and architectural
;; input are both untouched.
(defun spa:mmval (s / n body v)
  (setq s (cal:trim s)
        n (strlen s))
  (if (and (> n 2) (= "MM" (strcase (substr s (1- n) 2))))
      (progn
        (setq body (cal:trim (substr s 1 (- n 2)))
              v (if (> (strlen body) 0) (distof body 2) nil))
        (if (and v (> v 0.0)) (/ v 25.4)))))

;; What a bit-128 getdist gave back: a number passes through, mm text
;; converts, and anything else is nil so the caller can re-ask.
(defun spa:dval (v)
  (cond ((= (type v) 'STR) (spa:mmval v))
        (t v)))

;; A typed distance prompt that follows the repo's Back convention: a
;; getdist DOES take keywords, so Back (and its unlisted synonym Undo)
;; are offered as keywords whenever there is a previous question to
;; return to, shown in the prompt's brackets like everywhere else.
;; xkw is any extra keyword to merge in, dflt an Enter answer.
;; Returns the distance, a matched keyword string, or CAL-BACK.
(defun spa:askd (msg xkw dflt back / kw v out)
  (setq kw (cond ((and xkw back) (strcat xkw " Back Undo"))
                 (back "Back Undo")
                 (t xkw)))
  (cal:osup)
  (while (null out)
    ;; 128 = arbitrary input, so a mm answer reaches us as text
    (if kw (initget (+ (if dflt 6 7) 128) kw)
        (initget (+ (if dflt 6 7) 128)))
    (setq v (getdist (strcat "\n" msg
                             (if dflt (strcat " <" (rtos dflt) ">") "")
                             (cond ((and xkw back) (strcat " [" xkw "/Back]"))
                                   (xkw (strcat " [" xkw "]"))
                                   (back " [Back]")
                                   (t ""))
                             ": ")))
    (cond
      ((and (= (type v) 'STR) (member v '("Back" "Undo"))) (setq out 'CAL-BACK))
      ((and (= (type v) 'STR) xkw (= v xkw)) (setq out v))
      ((and (null v) dflt) (setq out dflt))
      ((setq out (spa:dval v)))
      (t (princ "\nNot a measurement -- type inches, 6'10\", or 600mm."))))
  (cal:osdown)
  out)

;; The typed-distance question a form can answer, for the keyed
;; distances asked OUTSIDE the measurement sequences (the cover lap).
;; Same consume-once contract as the keyword wrapper above: only a
;; measurement the prompt itself would accept -- a positive number --
;; is taken, and anything else (an NA, a keyword, a wrong type) is
;; consumed and the question is asked as always.
(defun spa:askdf (key msg xkw dflt back / v)
  (if (and (spa:fhas key)
           (setq v (spa:ftake key))
           (numberp v)
           (> v 0.0))
      v
      (spa:askd msg xkw dflt back)))

;; Back typed like a value, for the one prompt that cannot take
;; keywords (getstring).  Any case, per the shared convention.
(defun spa:backstr (v)
  (member (strcase v) '("B" "BACK" "U" "UNDO")))

;; Run a list of input stages with Back between them: a stage that
;; returns CAL-BACK sends the user to the previous stage, which is
;; re-asked from scratch.  Each stage is a function of no arguments and
;; must be safely re-runnable (it recomputes from its own answers).
;; Stage 1 has nowhere to go back to, so its Back is suppressed.
(defun spa:stages (fns / i n v)
  (setq i 0 n (length fns))
  (while (< i n)
    (setq v (apply (nth i fns) nil))
    (if (eq v 'CAL-BACK)
        (if (> i 0) (setq i (1- i)))
        (setq i (1+ i))))
  (princ))

;; Run a whole block; returns the answers as an assoc list, or CAL-BACK
;; when the user backed out of its FIRST question (only offered when bk
;; is non-nil).
(defun spa:askseqb (items bk / ans i n it v dflt asked out)
  (setq ans nil i 0 n (length items) asked nil out nil)
  (while (and (< i n) (not out))
    (setq it (nth i items)
          dflt (nth 4 it))
    (if (and dflt (listp dflt))
        (setq dflt (spa:sqfirst ans dflt)))
    ;; the form answers first, and its answer is consumed -- see
    ;; "form answers" above for why removing beats marking
    (setq v (if (spa:fhas (car it))
                (spa:ftake (car it))
                (spa:asks (cadr it) (caddr it) (cadddr it) dflt
                          (if (or asked bk) t nil))))
    (if (eq v 'CAL-BACK)
        (if asked
            (setq i (car asked) asked (cdr asked))
            (setq out t))               ; backed out of the block
        (setq ans (spa:sqput ans (car it) v)
              asked (cons i asked)
              i (1+ i))))
  (if out 'CAL-BACK ans))

;;; -------------------- guide preview ----------------------------------
;;;  A gray nominal spa of the chosen shape is drawn as soon as the shape
;;;  is picked.  While each measurement is prompted for, the matching
;;;  element of the guide turns red so the user can see exactly which
;;;  dimension is being asked for.  Once all inputs are in, the guide
;;;  deletes itself and is replaced by the true spa.

(setq spa:*pv-col*  8)                  ; guide outline color (dark gray)
(setq spa:*pvx-col* 7)                  ; measuring-tie color (white)
(setq spa:*hi-col*  1)                  ; highlight color (red)

;; Override (or set) the color of an entity, refresh it, return it.
(defun spa:setcol (e col / ed old)
  (if (and e (setq ed (entget e)))
      (progn
        (setq old (assoc 62 ed))
        (if old
            (setq ed (subst (cons 62 col) old ed))
            (setq ed (append ed (list (cons 62 col)))))
        (entmod ed)
        (entupd e)))
  e)

;; Read an entity's current color (defaults to the outline gray).
(defun spa:getcol (e / ed)
  (if (and e (setq ed (entget e)) (assoc 62 ed))
      (cdr (assoc 62 ed))
      spa:*pv-col*))

;; Guide entities for a list of corner-label keys, e.g. '(lA lB).
(defun spa:lbl (pv keys / out k)
  (foreach k keys (setq out (append out (cdr (assoc k pv)))))
  out)

;; The guide's corner-label key for a letter string ("A" -> 'lA).
(defun spa:lblkey (s) (read (strcat "l" s)))

;; Track a freshly made guide entity so spa:pvkill / *error* find it.
(defun spa:pvadd (e)
  (setq spa:*pvents* (cons e spa:*pvents*))
  e)

(defun spa:pvline (p1 p2)
  (spa:line p1 p2 "SPA-NOTES" nil)
  (spa:setcol (entlast) spa:*pv-col*))

;; Guide measuring line, drawn WHITE and DOTTED so it stands out from
;; the gray outline.
(defun spa:pvlined (p1 p2)
  (spa:linedot p1 p2)
  (entlast))

;; A labelled measuring tie (the overall-sheet letters).  The tie AND
;; its letter highlight together while it is prompted for.
(defun spa:pvtie (p q lbl th / e et)
  (setq e (spa:pvadd (spa:pvlined p q)))
  (spa:text (cal:v+ (cal:mid p q) (list (* 0.5 th) (* 0.5 th)))
            (* 1.2 th) lbl "SPA-NOTES")
  (setq et (spa:pvadd (spa:setcol (entlast) spa:*pv-col*)))
  (cons lbl (list e et)))

;; Remove an item (by equality) from a list.
(defun spa:lremove (x lst / out i)
  (foreach i lst (if (not (equal i x)) (setq out (cons i out))))
  (reverse out))

;; Delete specific guide entities mid-flow and untrack them.
(defun spa:pvdel (ents / e)
  (foreach e ents
    (if (and e (entget e)) (entdel e))
    (setq spa:*pvents* (spa:lremove e spa:*pvents*))))

;; Delete all guide entities (tracked globally so the *error* handler
;; can clean up after a cancel mid-prompt).
(defun spa:pvkill ( / e)
  (foreach e spa:*pvents*
    (if (and e (entget e)) (entdel e)))
  (setq spa:*pvents* nil))

;;; -------------------- report table -----------------------------------

;; Report cell: red when the row is flagged.
(defun spa:rtext (pt h str lay red)
  (if red (spa:textc pt h str lay 1) (spa:text pt h str lay)))

(defun spa:valnote (msg)
  (setq spa:*valnotes* (append spa:*valnotes* (list msg)))
  (princ (strcat "\n" msg)))

;; An advisory -- a recommendation rather than a problem.  Printed under
;; the report table in cyan, so it reads apart from the red failures.
(defun spa:advise (msg)
  (setq spa:*advice* (append spa:*advice* (list msg)))
  (princ (strcat "\n" msg)))

;; rows  = list of (label target actual [red]); a nil target prints N/A
;; notes = list of failure strings (written big and red)
(defun spa:report (rows notes x y h lay / lh ytop y0 xr r tgt act dl ds n)
  (setq lh (* 2.2 h)
        ytop (+ y lh)
        xr (+ x (* 46.0 h))
        y ytop)
  (setq y (- y lh))
  (spa:text (list x y) (* 1.25 h) (strcat "SPA LAYOUT REPORT - " spa:*modename*) lay)
  (setq y (- y lh))
  (spa:text (list x y) h "MEASUREMENT" lay)
  (spa:text (list (+ x (* 20.0 h)) y) h "TARGET" lay)
  (spa:text (list (+ x (* 29.0 h)) y) h "ACTUAL" lay)
  (spa:text (list (+ x (* 38.0 h)) y) h "DELTA" lay)
  (foreach r rows
    (setq y (- y lh)
          tgt (cadr r)
          act (caddr r))
    (spa:rtext (list x y) h (car r) lay (nth 3 r))
    (if tgt
        (progn
          (setq dl (- act tgt)
                ds (strcat (if (< dl 0.0) "" "+") (rtos dl 2 2)))
          (spa:rtext (list (+ x (* 20.0 h)) y) h (rtos tgt 2 2) lay (nth 3 r))
          (spa:rtext (list (+ x (* 38.0 h)) y) h ds lay (nth 3 r)))
        (progn
          (spa:rtext (list (+ x (* 20.0 h)) y) h "N/A" lay (nth 3 r))
          (spa:rtext (list (+ x (* 38.0 h)) y) h "-" lay (nth 3 r))))
    (spa:rtext (list (+ x (* 29.0 h)) y) h (rtos act 2 2) lay (nth 3 r)))
  (foreach n notes
    (setq y (- y (* 1.5 lh)))
    (spa:textc (list x y) (* 1.4 h) n lay 1))
  (foreach n spa:*advice*
    (setq y (- y (* 1.3 lh)))
    (spa:textc (list x y) (* 1.15 h) n lay 4))
  (setq y0 (- y lh)
        ytop (+ ytop (* 0.6 lh)))
  (spa:line (list (- x h) y0) (list xr y0) lay nil)
  (spa:line (list xr y0) (list xr ytop) lay nil)
  (spa:line (list xr ytop) (list (- x h) ytop) lay nil)
  (spa:line (list (- x h) ytop) (list (- x h) y0) lay nil)
  (princ))

;; The Water's Edge / Cover Size note under the drawing, plus a line
;; saying so when the cover was turned to lie long-ways.
(defun spa:modenote (x y th)
  (spa:textc (list x y) (* 1.6 th)
             (strcat "SPA OUTLINE DRAWN AT " spa:*modename*) "SPA-NOTES" 7)
  (if spa:*turned*
      (spa:textc (list x (- y (* 2.2 th))) (* 1.2 th)
                 "TURNED A QUARTER TURN - LONG OVERALL RUNS ACROSS"
                 "SPA-NOTES" 7)))

;;; -------------------- water's edge <-> cover -------------------------
;;;
;;;  The COVER IS ALWAYS THE LARGER of the two -- it laps the water's
;;;  edge by the same gap the whole way round.  That single fact settles
;;;  which way the offset runs:
;;;
;;;    drew the water's edge, adding the cover   ->  offset OUTWARD
;;;    drew the cover, adding the water's edge   ->  offset INWARD
;;;
;;;  By dims the two outlines are simply concentric: the second is built
;;;  from its own measurements and centred on the first.
;;;
;;;  Offsetting a corner by g (positive outward) is not the same for
;;;  every treatment:
;;;    Radius    the arc stays concentric, so r -> r + g
;;;    Diagonal  the cut face lengthens, f -> f + g * (2*sqrt2 - 2)
;;;    90        stays a sharp 90
;;;  and a treatment offset inward past nothing falls back to a 90.

(setq spa:*diagoff* 0.82842712)         ; 2*sqrt 2 - 2

;; Which way the offset runs to get from the outline just drawn to the
;; other one: +1 outward (water's edge -> cover), -1 inward.
(defun spa:offsign ()
  (if (= spa:*mode* "Watersedge") 1.0 -1.0))

;; Offer the other outline once the first is drawn.  Returns the method
;; keyword ("Offset" / "Dims") or nil.
(defun spa:askother ( / v)
  (if (spa:thermop)
      (progn
        (princ "\nThermo-Light: the water's edge and the cover are the same -- nothing to add.")
        nil)
      (spa:askother2)))

(defun spa:askother2 ( / v)
  (princ (strcat "\nThe " (spa:modeword (spa:othermode))
                 " can be added now -- the cover is always the larger of the two."))
  ;; the Yes/No is this phase's first question -- the outline is already
  ;; drawn behind it, so there is nothing to go back to; the method
  ;; question after it backs up to the Yes/No like any second question
  (if (= "Yes" (spa:askkwf 'second
                           (strcat "Draw the " (spa:modeword (spa:othermode))
                                   " as well")
                           "Yes No" "Yes/No" "Yes" nil))
      (if (eq 'CAL-BACK
              (setq v (spa:askkwf 'method "Take it from" "Offset Dims"
                                  "Offset/Dims" "Offset" t)))
          (spa:askother2)
          v)))

;; The gap between the two outlines, asked as a positive lap and signed
;; for the direction of travel.
(defun spa:askgap ( / g)
  ;; Back here re-asks the question that chose Offset in the first
  ;; place, which spa:askother2 owns -- so it is returned as CAL-BACK
  ;; and the caller re-enters the offer.
  (setq g (spa:askdf 'gap "How far does the cover lap the water's edge"
                     nil spa:*gapdflt* t))
  (if (eq g 'CAL-BACK) g (* g (spa:offsign))))

;; Offset every corner treatment by g (positive = outward).
(defun spa:offcorners (corners g / out c sz)
  (foreach c corners
    (setq sz (cond ((= (car c) "Radius") (+ (cadr c) g))
                   ((= (car c) "Cut") (+ (cadr c) (* g spa:*diagoff*)))
                   (t 0.0)))
    ;; a treatment the offset erases collapses to Square -- except a
    ;; NotGiven, which stays un-recorded on the derived outline too
    (setq out (cons (cond ((and (spa:cutp c) (> sz 1.0e-6))
                           (list (car c) sz))
                          ((= (car c) "NotGiven") (list "NotGiven" 0.0))
                          (t (list "Square" 0.0)))
                    out)))
  (reverse out))

;; By dims, the corner sizes still have to come from somewhere.  Each is
;; offered with the size the implied lap works out to, so Enter walks
;; straight through when the second outline really is a parallel offset,
;; and a corner that was measured differently can be typed over.
(defun spa:askothercorners (corners lbls maxsb / out i cc any v)
  (setq any nil)
  (foreach cc corners (if (spa:cutp cc) (setq any t)))
  (if any
      (princ (strcat "\n" (spa:modeword (spa:othermode))
                     " corners -- Enter takes the size the overalls imply.")))
  ;; Back steps to the previous corner, like the main corner loop
  (setq out nil i 0)
  (while (< i (length corners))
    (setq cc (nth i corners))
    (if (not (spa:cutp cc))
        (setq out (cons cc out) i (1+ i))
        (progn
          (setq v (spa:askcorner (strcat "Corner " (nth i lbls))
                                 (car cc) (cadr cc) nil maxsb (> i 0)))
          (if (eq v 'CAL-BACK)
              (if (> i 0)
                  (setq i (1- i) out (cdr out))
                  (princ "\nAlready at the first corner."))
              (setq out (cons v out) i (1+ i))))))
  (reverse out))

;; A quad of width w by length l with its bottom-left at org.
(defun spa:quadat (org w l)
  (list org
        (cal:v+ org (list w 0.0))
        (cal:v+ org (list w l))
        (cal:v+ org (list 0.0 l))))

;; Bottom-left corner that puts a w x l shape concentric with cen.
(defun spa:orgfor (cen w l)
  (list (- (car cen) (* 0.5 w)) (- (cadr cen) (* 0.5 l))))

;; Dimension one outline's two overalls.
;;
;;   OUTSIDE -- the COVER's pair, and a lone outline's: the across dim
;;   2 ft above the cover and the up dim 3 ft to its left, clear of the
;;   whole drawing.
;;
;;   INSIDE -- the WATER'S EDGE's pair, when the cover is drawn as well:
;;   a third of the way into its own outline, hooked to points that sit
;;   ON the dimension line, so the arrows land on the outline itself
;;   rather than trailing extension lines across the cover.
;;
;;  cxlo / cyhi are the cover's left and top edges.
(defun spa:dimoveralls (outside ac1 ac2 up1 up2 cxlo cyhi)
  (if outside
      (progn
        (spa:dimov ac1 ac2 (list (* 0.5 (+ (car ac1) (car ac2)))
                                 (+ cyhi spa:*topoff*)))
        (spa:dimov up1 up2 (list (- cxlo spa:*dimoff*)
                                 (* 0.5 (+ (cadr up1) (cadr up2))))))
      (progn
        (spa:dimov ac1 ac2 (cal:mid ac1 ac2))
        (spa:dimov up1 up2 (cal:mid up1 up2))))
  (princ))

;; The four points an outline is dimensioned from when its pair goes
;; INSIDE: a third of the way up from the bottom for the across dim and
;; a third of the way in from the left for the up dim, each pair lying on
;; its own dimension line.  inx / iny push the station clear of a cut
;; corner, so the arrows always land on a straight run of the outline.
;; Returns (across1 across2 up1 up2).
(defun spa:insidepts (xlo xhi ylo yhi inx iny / xst yst)
  (setq xst (+ xlo (max (* (- xhi xlo) spa:*insetfrac*) (* 1.05 inx)))
        yst (+ ylo (max (* (- yhi ylo) spa:*insetfrac*) (* 1.05 iny))))
  (list (list xlo yst) (list xhi yst)
        (list xst ylo) (list xst yhi)))

;; The overlap between the two outlines, dimensioned at the BOTTOM: how
;; far the cover laps the water's edge.  The lap is far too small to hold
;; its own text, so the note is parked below the cover -- DIMTMOVE 1
;; gives it a leader back to the dimension.
(defun spa:dimlap (x ycov ywe / om)
  (setq om (getvar "DIMTMOVE"))
  (spa:setv "DIMTMOVE" 1)
  (spa:dimalg (list x ycov) (list x ywe) (list x (* 0.5 (+ ycov ywe)))
              " Overlap")
  (spa:dimtextat (entlast)
                 (list x (- (min ycov ywe) spa:*lapoff*)))
  (if om (spa:setv "DIMTMOVE" om))
  (princ))

;; Report rows for the second outline, tagged with which one it is.
(defun spa:otherrows (across up)
  (list (list (strcat (strcase (spa:modeword spa:*mode*)) " ACROSS") across across)
        (list (strcat (strcase (spa:modeword spa:*mode*)) " UP") up up)))


;;; -------------------- hinges -----------------------------------------
;;;
;;;  After the cover is drawn (and dimensioned) the command offers to
;;;  AUTO-HINGE it.  Hinges run north-south, splitting the cover into
;;;  side-by-side pieces along its west-east length.
;;;
;;;  1.  SPILLAWAYS -- places a hinge cannot go.  Asked in a loop that
;;;      always defaults to No: a CORNER spillaway blocks a typed length
;;;      from that (hypotenuse) corner along both of its walls; a WALL
;;;      spillaway is a typed overall length assumed centred on its
;;;      wall.  A left/right wall spillaway cannot collide with a
;;;      north-south hinge, so it is only recorded.
;;;
;;;  2.  The "Spa Cover Details" block supplies the GRADE and TAPER
;;;      (Enter types the taper instead; no grade given means
;;;      Standard).  Grade + taper give, from the foam sheets:
;;;        foam width   the widest a piece may be = max hinge spacing
;;;        foam length  the longest a hinge may run -- exceeded, the
;;;                     hinge is still drawn and the report says so
;;;        pieces       which piece counts are acceptable
;;;
;;;  3.  The FEWEST pieces that fit the foam width are used, spaced
;;;      evenly, then nudged off any spillaway zone.  A nudge keeps
;;;      every piece inside the foam width; when no nudge works the
;;;      piece count is bumped, and failing everything the even layout
;;;      is kept and the report says which hinge is in a zone.
;;;
;;;  Fold vs velcro follows the Hinge Arrangement Chart: the pieces
;;;  fold up in PAIRS from both ends -- a sewn FOLD hinge inside each
;;;  pair, Velcro between bundles -- so a 5-piece cover reads Hinge /
;;;  Velcro / Velcro / Hinge, and an odd count leaves one flat piece
;;;  at or beside the centre.  The leftmost hinge is always a fold and
;;;  no two folds are ever adjacent.  (Thermo-Light: all velcro.)
;;;
;;;  The linework matches the office template's sample: the fold hinge
;;;  is a DASHED2 line on COVER scaled to a 5" dash, velcro hinges are
;;;  ByLayer lines on COVER, and every label is a vertical MTEXT in
;;;  the Attributes style (Standard when absent) at a fixed 5" height,
;;;  bottom-centred 3" west of its hinge, on the TEXT layer.

;; Foam sheet: (grade taper ((foamW . foamL) ...) (piece counts, 5 = 5+))
;; A grade+taper with two width options (48" / 49-1/2") carries both;
;; the solver picks the one that needs the fewest hinges.
(setq spa:*foamtab*
  (list
    (list "ECONOMY"     "3-2"   (list (cons 48.0 96.0))                  (list 2))
    (list "STANDARD"    "3-2"   (list (cons 48.0 144.0) (cons 49.5 102.0)) (list 2))
    (list "STANDARD"    "4-2"   (list (cons 48.0 96.0)  (cons 49.5 102.0)) (list 2 3 4))
    (list "STANDARD"    "4-3"   (list (cons 48.0 144.0))                 (list 2 3 4))
    (list "STANDARD"    "5-3"   (list (cons 48.0 96.0))                  (list 2 3 4 5))
    (list "STANDARD"    "5-4"   (list (cons 48.0 96.0))                  (list 2 3 4 5))
    (list "STANDARD"    "3-3"   (list (cons 48.0 144.0))                 (list 2 3 4 5))
    (list "ULTRA"       "3-2"   (list (cons 48.0 144.0))                 (list 2))
    (list "ULTRA"       "4-3"   (list (cons 48.0 96.0))                  (list 2 3 4))
    (list "ULTRA"       "3-3"   (list (cons 48.0 144.0))                 (list 2 3 4 5))
    (list "THERMOLIGHT" "1-3/8" (list (cons 53.0 nil))                   (list 2 3 4 5))))

;; Hardware called for by the LONGEST hinge, per grade.  Each rule is
;; (OVER <inches>) | (ALWAYS) | (NEVER) | (REQUEST).
(setq spa:*hardtab*
  (list                 ;  grade          velcro        double C      hold down
    (list "ECONOMY"     '(REQUEST)    '(REQUEST)    '(REQUEST))
    (list "STANDARD"    '(OVER 120.0) '(OVER 108.0) '(OVER 120.0))
    (list "ULTRA"       '(OVER 108.0) '(NEVER)      '(OVER 96.0))
    (list "THERMOLIGHT" '(ALWAYS)     '(NEVER)      '(NEVER))))

;; A rule against the longest hinge -> (needed . reason), needed nil when
;; the item is not called for.
(defun spa:hardverdict (rule len / k v)
  (setq k (car rule) v (cadr rule))
  (cond
    ((eq k 'ALWAYS)  (cons t   "always for this grade"))
    ((eq k 'NEVER)   (cons nil "not used on this grade"))
    ((eq k 'REQUEST) (cons t   "upon request only"))
    ((> len v)       (cons t   (strcat "hinge " (rtos len 2 1)
                                       " over " (rtos v 2 0))))
    (t               (cons nil (strcat "hinge " (rtos len 2 1)
                                       " not over " (rtos v 2 0))))))

;;; ---------- small string helpers (plain AutoLISP, no VL) ----------

;; "Taper: 4-2" -> "4-2" (everything after the last colon, trimmed)
(defun spa:aftercolon (s / i out)
  (setq i (strlen s) out s)
  (while (> i 0)
    (if (= ":" (substr s i 1))
        (progn (setq out (substr s (1+ i))) (setq i 0))
        (setq i (1- i))))
  (cal:trim out))

;; Normalise a taper string to a foam-sheet key ("3-3 Flat" -> "3-3").
(defun spa:tapernorm (v / u)
  (setq u (strcase v))
  (cond ((wcmatch u "*3-2*") "3-2")
        ((wcmatch u "*4-2*") "4-2")
        ((wcmatch u "*4-3*") "4-3")
        ((wcmatch u "*5-3*") "5-3")
        ((wcmatch u "*5-4*") "5-4")
        ((wcmatch u "*3-3*") "3-3")
        ((wcmatch u "*3/8*") "1-3/8")))

;; Normalise a grade; anything unrecognised (or missing) is Standard.
(defun spa:gradenorm (v / u)
  (setq u (strcase (if v v "")))
  (cond ((wcmatch u "*ECON*") "ECONOMY")
        ((or (wcmatch u "*ULTRA*") (wcmatch u "*FRP*")) "ULTRA")
        ((wcmatch u "*THERMO*") "THERMOLIGHT")
        (t "STANDARD")))

(defun spa:gradeshort (g)
  (cond ((= g "ECONOMY") "ECO") ((= g "STANDARD") "STD")
        ((= g "ULTRA") "ULTRA") (t "THERMO")))

;; Attributes of a block reference, as ((TAG . value) ...).
(defun spa:attribs (ename / e ed out)
  (setq e (entnext ename))
  (while (and e (setq ed (entget e)) (= "ATTRIB" (cdr (assoc 0 ed))))
    (setq out (cons (cons (strcase (cdr (assoc 2 ed))) (cdr (assoc 1 ed))) out)
          e (entnext e)))
  (reverse out))

;;; ---------- geometry: the cover's north-south chord at x ----------

;; Does this corner carry a treatment that cuts real geometry -- a
;; Radius or a Cut with a size?  NotGiven does NOT: its corner is
;; built square, so everything that asks "is there a cut here" (the
;; setback caps, the second outline, the hinge ties) answers no; only
;; the corner marks care that it is not a plain Square.  (pool:cutp is
;; the donor.)
(defun spa:cutp (cc)
  (and (member (car cc) '("Radius" "Cut")) (> (cadr cc) 1.0e-6)))

;; How far a corner treatment sets back along its walls.
(defun spa:cornsb (cc)
  (cond ((= (car cc) "Radius") (cadr cc))
        ((= (car cc) "Cut") (* (cadr cc) 0.70711))
        (t 0.0)))

;; Offset of a treated edge INTO the shape at rx along a wall of length
;; wlen; c1 is the corner at rx = 0, c2 the corner at rx = wlen.
(defun spa:edgeoff (rx wlen c1 c2 / sb r)
  (cond
    ((< rx (setq sb (spa:cornsb c1)))
     (if (= (car c1) "Radius")
         (progn (setq r (cadr c1))
                (- r (sqrt (max 0.0 (- (* r r) (* (- rx r) (- rx r)))))))
         (- sb rx)))
    ((> rx (- wlen (setq sb (spa:cornsb c2))))
     (setq rx (- wlen rx))
     (if (= (car c2) "Radius")
         (progn (setq r (cadr c2))
                (- r (sqrt (max 0.0 (- (* r r) (* (- rx r) (- rx r)))))))
         (- sb rx)))
    (t 0.0)))

;; (ybot ytop) of the rectangle (with corner treatments) at x, or nil.
(defun spa:chordrect (quad corners x / x0 y0 wlen hlen rx offb offt)
  (setq x0 (car (car quad)) y0 (cadr (car quad))
        wlen (- (car (cadr quad)) x0)
        hlen (- (cadr (cadddr quad)) y0)
        rx (- x x0))
  (if (and (> rx 1.0e-6) (< rx (- wlen 1.0e-6)))
      (progn
        (setq offb (spa:edgeoff rx wlen (nth 0 corners) (nth 1 corners))
              offt (spa:edgeoff rx wlen (nth 3 corners) (nth 2 corners)))
        (if (< (+ offb offt) hlen)
            (list (+ y0 offb) (- (+ y0 hlen) offt))))))

;; (ybot ytop) of a polygon at x, or nil.
(defun spa:chordpoly (pts x / n i p q tt ys)
  (setq n (length pts) i 0 ys nil)
  (while (< i n)
    (setq p (nth i pts) q (nth (rem (1+ i) n) pts))
    (if (or (and (<= (car p) x) (> (car q) x))
            (and (<= (car q) x) (> (car p) x)))
        (setq tt (/ (- x (car p)) (- (car q) (car p)))
              ys (cons (+ (cadr p) (* tt (- (cadr q) (cadr p)))) ys)))
    (setq i (1+ i)))
  (if (>= (length ys) 2)
      (list (apply 'min ys) (apply 'max ys))))

;; (ybot ytop) of the circle / ellipse at x, or nil.
(defun spa:chordell (cen b a x / dx q dy)
  (setq dx (/ (- x (car cen)) (* 0.5 b))
        q (- 1.0 (* dx dx)))
  (if (> q 1.0e-9)
      (progn
        (setq dy (* 0.5 a (sqrt q)))
        (list (- (cadr cen) dy) (+ (cadr cen) dy)))))

;; desc = ("RECT" quad corners) | ("OCT" pts) | ("ROUND" cen b a)
(defun spa:chordat (desc x)
  (cond
    ((= (car desc) "RECT") (spa:chordrect (cadr desc) (caddr desc) x))
    ((= (car desc) "OCT")  (spa:chordpoly (cadr desc) x))
    (t (spa:chordell (cadr desc) (caddr desc) (cadddr desc) x))))

;;; ---------- the placement solver ----------

(defun spa:ceilv (v / f)
  (setq f (fix v))
  (if (> v (+ f 1.0e-6)) (1+ f) f))

;; The forbidden interval x falls inside, or nil.  Intervals are open,
;; so a hinge sitting exactly on a zone's edge is allowed.
(defun spa:inforb (x forb / hit f)
  (foreach f forb
    (if (and (> x (car f)) (< x (cadr f))) (setq hit f)))
  hit)

;; Even hinge stations for n pieces across [x1 x2].
(defun spa:heven (x1 x2 n / i out)
  (setq i 1 out nil)
  (while (< i n)
    (setq out (cons (+ x1 (* (- x2 x1) (/ (float i) n))) out)
          i (1+ i)))
  (reverse out))

;; Place the n-1 hinges of an n-piece layout, dodging the forbidden
;; zones.  Each hinge starts at its even station; one that lands in a
;; zone moves to the nearer zone edge that still leaves every piece --
;; taken and to come -- inside the foam width fw.  Returns the x list,
;; or nil when this piece count cannot dodge the zones.
(defun spa:hplace (x1 x2 n fw forb / i xs prev x lo hi f cand e ok)
  (setq prev x1 xs nil i 1 ok t)
  (while (and ok (< i n))
    (setq x (+ x1 (* (- x2 x1) (/ (float i) n)))
          lo (max (+ prev 0.01) (- x2 (* fw (- n i))))
          hi (min (+ prev fw) (- x2 0.01)))
    (if (> lo hi)
        (setq ok nil)
        (progn
          (if (< x lo) (setq x lo))
          (if (> x hi) (setq x hi))
          (setq f (spa:inforb x forb))
          (if f
              (progn
                (setq cand nil)
                (foreach e (if (< (- x (car f)) (- (cadr f) x))
                               (list (car f) (cadr f))
                               (list (cadr f) (car f)))
                  (if (and (not cand) (>= e lo) (<= e hi)
                           (not (spa:inforb e forb)))
                      (setq cand e)))
                (if cand (setq x cand) (setq ok nil))))
          (if ok (setq xs (cons x xs) prev x i (1+ i))))))
  (if (and ok (<= (- x2 prev) (+ fw 0.01)))
      (reverse xs)))

;; The longest hinge a station list would produce.
(defun spa:hmaxchord (desc xs / m ch x)
  (setq m 0.0)
  (foreach x xs
    (if (setq ch (spa:chordat desc x))
        (setq m (max m (- (cadr ch) (car ch))))))
  m)

;; Fewest pieces first: try n up to n+3 for a layout that dodges every
;; zone.  Returns (n x-list solvedflag); when nothing dodges, the even
;; minimum-count layout with the flag down.
(defun spa:hsolve (x1 x2 fw forb nmin / n xs)
  (setq n nmin)
  (while (and (<= n (+ nmin 3)) (not xs))
    (setq xs (spa:hplace x1 x2 n fw forb))
    (if (not xs) (setq n (1+ n))))
  (if xs
      (list n xs t)
      (list nmin (spa:heven x1 x2 nmin) nil)))

(defun spa:hallow (n allowed)
  (if (>= n 5) (member 5 allowed) (member n allowed)))

;; Fold or velcro for each hinge, per the Hinge Arrangement Chart.
;; The chart's P is the HINGE COUNT (pieces - 1), positions 0-indexed
;; west to east.  Fold ("Normal") hinges land on even positions and
;; velcro on odd -- across the whole row when pieces mod 4 is 0 or 2,
;; and only up to the chart's cutoff when it is 1 or 3, with the rest
;; MIRRORING the left half:
;;
;;     2  H              5  H V V H          8  H V H V H V H
;;     3  H V            6  H V H V H       9  H V H V V H V H
;;     4  H V H          7  H V H V V H
;;
;; Read as bundles: the pieces fold up in PAIRS from both ends (a fold
;; hinge inside each pair, velcro between bundles), an odd count leaving
;; one flat piece at or beside the centre.  The leftmost hinge is always
;; a fold, no two folds are ever adjacent, and 2- and 3-piece covers
;; come out exactly as they always have.  allvel (Thermo-Light) forces
;; every hinge to velcro.  Returns a list of "H" / "V", west to east.
(defun spa:hingetypes (n allvel / hc m zone p out)
  (setq hc (1- n)
        m (rem n 4)
        zone (cond ((or (= m 0) (= m 2)) hc)
                   ((= m 1) (/ hc 2))
                   (t (/ (+ hc 2) 2)))
        p 0 out nil)
  ;; built west to east, so the mirror lookup (nth (hc-1-p)) always
  ;; lands on a position already decided
  (while (< p hc)
    (setq out (append out
                      (list (cond (allvel "V")
                                  ((< p zone) (if (= 0 (rem p 2)) "H" "V"))
                                  (t (nth (- hc 1 p) out)))))
          p (1+ p)))
  out)

;;; ---------- drawing ----------

;; The fold hinge draws in the stock DASHED2 pattern (0.25 dash, 0.125
;; gap), defined here when the drawing lacks it, and scaled so the dash
;; plots 5" long no matter how the host drawing's LTSCALE is set --
;; ent-scale x LTSCALE x 0.25 = 5.  In the office template (LTSCALE 50)
;; that lands the sample drawing's exact 0.4.
(defun spa:hdash ( / lt)
  (setq lt (spa:ltmake "DASHED2"
                       "Dashed (.5x) _ _ _ _ _ _ _ _ _ _ _ _ _ _ _ _ _"
                       '(0.25 -0.125)))
  (if (/= lt "CONTINUOUS")
      (list (cons 6 lt) (cons 48 (* spa:*hdashmult* (spa:ltsc))))))

;; Label beside a hinge, per the template sample: MTEXT in the
;; Attributes style (Standard when the drawing has no such style),
;; fixed 5" height, reading upward via the (0 1) direction vector,
;; bottom-centred so its underside faces the hinge line, inserted 3"
;; west of the line at the hinge's midpoint.
(defun spa:htext (x ymid str)
  (entmake (list '(0 . "MTEXT")
                 '(100 . "AcDbEntity")
                 '(8 . "TEXT")
                 '(100 . "AcDbMText")
                 (cons 10 (spa:wp (list (- x (* 0.6 spa:*hingetxth*)) ymid)))
                 (cons 40 spa:*hingetxth*)
                 (cons 41 spa:*hingetxw*)
                 '(71 . 8)              ; bottom centre
                 '(72 . 5)              ; drawing direction: by style
                 (cons 1 str)
                 (cons 7 (if (tblsearch "STYLE" spa:*hingestyle*)
                             spa:*hingestyle* "Standard"))
                 (cons 11 '(0.0 1.0 0.0)))))

;;; ---------- the guided flow ----------

(defun spa:hask (msg back)
  (spa:askd msg nil nil back))

;; Ask the spillaways.  Returns the forbidden x-intervals.
;;
;; This is one of the repo's commit-as-you-go loops, so Back follows
;; that convention: it steps back a question within a spillaway, and
;; from the first question of one it REMOVES the spillaway just
;; committed -- its zone and its report row -- before re-asking.  The
;; feedback wording is the shared one.
(defun spa:askspill (x1 x2 / forb loc cnr d wall len v stage done)
  (setq forb nil done nil)
  (while (not done)
    (setq v (cal:askkw "Is there a spillaway" "Yes No" "Yes/No" "No"
                       (if forb t nil)))
    (cond
      ;; Back from the top question: drop the last spillaway and re-ask
      ((eq v 'CAL-BACK)
       (if forb
           (progn
             (princ "\nStepping back one spillaway.")
             (setq forb (cdr forb)
                   spa:*hingerows* (reverse (cdr (reverse spa:*hingerows*)))))
           (princ "\nAlready at the first spillaway.")))
      ((= v "No") (setq done t))
      (t
       ;; one spillaway, its own questions Back-able among themselves
       (setq stage 0)
       (while (and stage (< stage 3))
         (cond
           ((= stage 0)
            (setq loc (cal:askkw "Spillaway location" "Corner Wall"
                                 "Corner/Wall(centred)" "Wall" t))
            (setq stage (if (eq loc 'CAL-BACK) nil 1)))
           ((= stage 1)
            (if (= loc "Corner")
                (setq cnr (cal:askkw "Which corner"
                                     "BottomLeft BottomRight TopRight TopLeft"
                                     "BottomLeft/BottomRight/TopRight/TopLeft"
                                     nil t))
                (setq wall (cal:askkw "On which wall" "Top Bottom Left Right"
                                      "Top/Bottom/Left/Right" nil t)))
            (setq stage (if (eq (if (= loc "Corner") cnr wall) 'CAL-BACK) 0 2)))
           (t
            (setq d (spa:hask (if (= loc "Corner")
                                  "Length from the corner to keep clear of hinges"
                                  "Overall length of the spillaway (centred)")
                              t))
            (if (eq d 'CAL-BACK)
                (setq stage 1)
                (progn
                  ;; commit it
                  (if (= loc "Corner")
                      (progn
                        (if (member cnr '("BottomLeft" "TopLeft"))
                            (setq forb (cons (list x1 (+ x1 d)) forb))
                            (setq forb (cons (list (- x2 d) x2) forb)))
                        (setq spa:*hingerows*
                              (append spa:*hingerows*
                                      (list (list (strcat "SPILLWAY "
                                                          (strcase cnr))
                                                  nil d)))))
                      (progn
                        (if (member wall '("Top" "Bottom"))
                            (setq forb
                                  (cons (list (- (* 0.5 (+ x1 x2)) (* 0.5 d))
                                              (+ (* 0.5 (+ x1 x2)) (* 0.5 d)))
                                        forb))
                            (princ "\n(a left/right wall spillaway cannot meet a north-south hinge; recorded only)"))
                        (setq spa:*hingerows*
                              (append spa:*hingerows*
                                      (list (list (strcat "SPILLWAY "
                                                          (strcase wall) " WALL")
                                                  nil d))))))
                  (setq stage 3)))))))))
  forb)

;; Is this a Thermo-Light cover?  Its water's edge and cover size are
;; the same thing, and every one of its hinges is velcro.
(defun spa:thermop ()
  (and spa:*grade* (= spa:*grade* "THERMOLIGHT")))

;; Try to read GRADE and TAPER off a Spa Cover Details block.  Sets the
;; globals; either may be left nil.  Returns T when something was read.
(defun spa:readblock ( / sel ed bn att v got)
  (cal:osup)
  (setq sel (entsel "\nSelect the Spa Cover Details block <Enter to skip>: "))
  (cal:osdown)
  (if sel
      (progn
        (setq ed (entget (car sel)))
        (if (= "INSERT" (cdr (assoc 0 ed)))
            (progn
              (setq bn (cdr (assoc 2 ed)))
              (if (/= (strcase bn) "SPA COVER DETAILS")
                  (princ (strcat "\n(block is named \"" bn
                                 "\", not Spa Cover Details -- reading its tags anyway)")))
              (setq att (spa:attribs (car sel)))
              (if (setq v (cdr (assoc "GRADE" att)))
                  (setq spa:*grade* (spa:gradenorm (spa:aftercolon v)) got t))
              (if (setq v (cdr (assoc "TAPER" att)))
                  (setq spa:*taper* (spa:tapernorm (spa:aftercolon v)) got t))
              (if (null spa:*taper*)
                  (princ "\nNo readable TAPER tag on that block.")))
            (princ "\nThat is not a block reference."))))
  got)

;; Grade and taper for the hinge maths.  Whatever the block gave up front
;; stands; anything still missing is asked for now.  No grade at all
;; means Standard.  Returns (grade taper).
(defun spa:askdetails ( / v)
  ;; a form's grade/taper may still be waiting when this pass is
  ;; reached without going through c:SPA's own consume -- same rules,
  ;; same code, and a no-op when the store was already drained
  (spa:formdetails)
  (if (and (null spa:*grade*) (null spa:*taper*))
      (spa:readblock))                  ; not offered earlier -- offer now
  (if (null spa:*grade*) (setq spa:*grade* "STANDARD"))
  (if (spa:thermop) (setq spa:*taper* "1-3/8"))
  ;; getstring cannot take keywords, so Back is typed like a value here
  ;; -- B, BACK, U or UNDO alone, any case -- as the prompt says
  (while (null spa:*taper*)
    (setq v (getstring "\nTaper (3-2, 4-2, 4-3, 5-3, 5-4, 3-3, 1-3/8) [type B to go Back]: "))
    (if (spa:backstr v)
        (setq spa:*taper* 'CAL-BACK)
        (progn
          (setq spa:*taper* (spa:tapernorm v))
          (if (null spa:*taper*)
              (princ "\nNot a taper on the foam sheet -- again.")))))
  (if (eq spa:*taper* 'CAL-BACK)
      (progn (setq spa:*taper* nil) 'CAL-BACK)
      (list spa:*grade* spa:*taper*)))

;; The whole auto-hinge pass.  desc / x1 / x2 describe the COVER
;; outline; coverp nil means only the water's edge was drawn and the
;; hinges are being laid on that.  Draws the hinges and returns report
;; rows (also via spillaway rows gathered in spa:*hingerows*).
(defun spa:hingeflow (desc x1 x2 th coverp / forb gt grade taper row r opts
                         allowed best bestsc cand opt fw fl nmin res n xs
                         mc lenok pcok sc hw h nm vd allvel htys hty
                         k x ch maxch maxpc prev lbl)
  (setq spa:*hingerows* nil)
  (if (/= "Yes" (spa:askkwf 'autohinge "Auto-hinge the cover"
                            "Yes No" "Yes/No" "Yes" nil))
      nil
      (progn
        (if (not coverp)
            (spa:valnote "NO COVER OUTLINE - HINGES LAID ON THE WATER'S EDGE"))
        ;; 1 -- where hinges cannot go, then 2 -- grade + taper.  Back
        ;; at the taper re-opens the spillaways, its previous question.
        (setq gt 'CAL-BACK)
        (while (eq gt 'CAL-BACK)
          (setq forb (spa:askspill x1 x2)
                gt (spa:askdetails)))
        (setq grade (car gt) taper (cadr gt)
              ;; Thermo-Light is velcro throughout -- no fold hinge
              allvel (spa:thermop)
              row nil)
        (if allvel
            (spa:advise "THERMO-LIGHT: EVERY HINGE IS VELCRO - NO FOLD HINGE"))
        (foreach r spa:*foamtab*
          (if (and (not row) (= (car r) grade) (= (cadr r) taper))
              (setq row r)))
        (if (not row)                    ; e.g. an Economy taper only the
            (foreach r spa:*foamtab*     ; Standard sheet carries
              (if (and (not row) (= (car r) "STANDARD") (= (cadr r) taper))
                  (setq row r))))
        (if row
            (setq opts (caddr row) allowed (cadddr row))
            (progn
              (spa:valnote (strcat "GRADE/TAPER " grade " " taper
                                   " NOT ON THE FOAM SHEET - 48/96 ASSUMED"))
              (setq opts (list (cons 48.0 96.0)) allowed (list 2 3 4 5))))
        ;; 3 -- pick the foam option and the layout.
        ;; A grade/taper can carry MORE THAN ONE foam sheet -- Standard
        ;; 3-2 and 4-2 each come in a 48 x 144/96 and a 49-1/2 x 102 --
        ;; and one can work where the other will not: the wider sheet
        ;; needs fewer hinges, the longer one lets a hinge run further.
        ;; So every option is solved and scored on what it satisfies --
        ;; dodging the spillaways, fitting the foam length, an
        ;; acceptable piece count -- and only then on fewest pieces.
        (setq best nil bestsc -1)
        (foreach opt opts
          (setq fw (car opt)
                fl (cdr opt)
                nmin (max 2 (spa:ceilv (/ (- x2 x1) fw)))
                res (spa:hsolve x1 x2 fw forb nmin)
                mc (spa:hmaxchord desc (cadr res))
                lenok (or (null fl) (<= mc (+ fl 0.01)))
                pcok (if (spa:hallow (car res) allowed) t nil)
                sc (+ (if (caddr res) 4 0) (if lenok 2 0) (if pcok 1 0))
                cand (list (car res) (cadr res) fw fl (caddr res) lenok pcok mc))
          (if (or (null best)
                  (> sc bestsc)
                  (and (= sc bestsc) (< (car cand) (car best)))
                  ;; nothing to choose on either -> the longer sheet, so
                  ;; a hinge that overruns overruns by as little as it can
                  (and (= sc bestsc) (= (car cand) (car best))
                       (> (if fl fl 0.0)
                          (if (nth 3 best) (nth 3 best) 0.0))))
              (setq best cand bestsc sc)))
        (setq n (car best) xs (cadr best) fw (caddr best) fl (nth 3 best))
        (if (not (nth 4 best))
            (spa:valnote "SPILLAWAY ZONES COULD NOT ALL BE AVOIDED - CHECK HINGES"))
        (if (not (spa:hallow n allowed))
            (spa:valnote (strcat (itoa n) " PIECES NOT ACCEPTABLE FOR "
                                 (spa:gradeshort grade) " " taper)))
        ;; say which sheet was taken when the taper offers a choice
        (if (> (length opts) 1)
            (spa:advise (strcat "FOAM SHEET USED: " (rtos fw 2 2) " x "
                                (if fl (rtos fl 2 0) "N/A")
                                " (this taper has "
                                (itoa (length opts)) " sheets)")))
        ;; 4 -- draw them per the Hinge Arrangement Chart: FOLD hinges
        ;; (dashed, "Hinge") and Velcro (ByLayer, "Velcro Hinge") laid
        ;; out by spa:hingetypes -- pairs folding from both ends, so a
        ;; 5-piece cover reads Hinge / Velcro / Velcro / Hinge
        (setq htys (spa:hingetypes n allvel)
              k 0 maxch 0.0)
        (foreach x xs
          (setq ch (spa:chordat desc x)
                hty (nth k htys))
          (if ch
              (progn
                (setq maxch (max maxch (- (cadr ch) (car ch))))
                (if (= hty "H")
                    (spa:line (list x (car ch)) (list x (cadr ch))
                              "COVER" (spa:hdash))
                    (spa:line (list x (car ch)) (list x (cadr ch))
                              "COVER" nil))
                (spa:htext x (* 0.5 (+ (car ch) (cadr ch)))
                           (if (= hty "H") "Hinge" "Velcro Hinge"))
                (if (and fl (> (- (cadr ch) (car ch)) (+ fl 0.01)))
                    (spa:valnote (strcat "HINGE " (itoa (1+ k))
                                         " EXCEEDS THE FOAM LENGTH ("
                                         (rtos (- (cadr ch) (car ch)) 2 1)
                                         " > " (rtos fl 2 0) ")")))
                (if (spa:inforb x forb)
                    (spa:valnote (strcat "HINGE " (itoa (1+ k))
                                         " FALLS IN A SPILLAWAY ZONE")))))
          (setq k (1+ k)))
        (if (null fl)
            (spa:valnote "THERMOLIGHT: HINGE LENGTH N/A - VERIFY"))
        ;; 4b -- hardware called for by the longest hinge
        (setq hw nil)
        (foreach h spa:*hardtab*
          (if (and (not hw) (= (car h) grade)) (setq hw h)))
        (if hw
            (progn
              (setq k 0)
              (foreach nm (list "VELCRO HINGES" "DOUBLE C CHANNEL" "HOLD DOWN KIT")
                (setq vd (spa:hardverdict (nth (1+ k) hw) maxch))
                (if (car vd)
                    (spa:advise (strcat nm ": YES - " (cdr vd)))
                    (spa:advise (strcat nm ": no - " (cdr vd))))
                (setq k (1+ k)))))
        ;; 5 -- report rows: the pieces, their worst width, each hinge
        (setq maxpc 0.0 prev x1)
        (foreach x (append xs (list x2))
          (setq maxpc (max maxpc (- x prev)) prev x))
        (setq spa:*hingerows*
              (append spa:*hingerows*
                      (list (list (strcat "PIECES (" (spa:gradeshort grade)
                                          " " taper ")")
                                  nil (float n))
                            (list "FOAM WIDTH MAX" fw maxpc)
                            (list "FOAM LENGTH MAX" fl maxch))))
        (setq k 0)
        (foreach x xs
          (setq lbl (strcat "HINGE " (itoa (1+ k))
                            (if (= (nth k htys) "H") " (FOLD)" " (VELCRO)"))
                spa:*hingerows*
                (append spa:*hingerows* (list (list lbl nil (- x x1))))
                k (1+ k)))
        spa:*hingerows*)))

;;; -------------------- rectangle corner treatments --------------------
;;;
;;;  A corner may be Square, Rounded (radius) or Diag (chamfer).  Side
;;;  lengths are measured to the TRUE (sharp) corner; the treatment cuts
;;;  inward from there.  The size typed is:
;;;    Rounded -> the corner RADIUS
;;;    Diag    -> the CHAMFER FACE length (the cut itself)

;; The two points where a corner's treatment meets the straight sides
;; (toward the previous / next corner) plus, for Radius, the arc mid.
;; Returns (ePrev eNext arcMid|nil).  A 90 corner -> (P P nil).
(defun spa:cornerends (p pp pn ctype size / uprev unext dp ang sb bis cen)
  (setq uprev (spa:unit (cal:v- pp p))
        unext (spa:unit (cal:v- pn p))
        dp (cal:dot uprev unext)
        ang (atan (sqrt (max 0.0 (- 1.0 (* dp dp)))) dp))   ; interior angle
  (cond
    ((= ctype "Cut")
     (setq sb (/ size (* 2.0 (sin (/ ang 2.0)))))           ; face -> edge setback
     (list (cal:v+ p (cal:v* uprev sb))
           (cal:v+ p (cal:v* unext sb)) nil))
    ((= ctype "Radius")
     (setq sb (/ (* size (cos (/ ang 2.0))) (sin (/ ang 2.0)))  ; r/tan(ang/2)
           bis (spa:unit (cal:v+ uprev unext))
           cen (cal:v+ p (cal:v* bis (/ size (sin (/ ang 2.0))))))
     (list (cal:v+ p (cal:v* uprev sb))
           (cal:v+ p (cal:v* unext sb))
           (cal:v- cen (cal:v* bis size))))                 ; arc point nearest corner
    (t (list p p nil))))

;; Every corner's ends, in corner order.
(defun spa:allends (q corners)
  (mapcar '(lambda (i)
             (spa:cornerends (nth i q)
                             (nth (rem (+ i 3) 4) q)
                             (nth (rem (+ i 1) 4) q)
                             (car (nth i corners)) (cadr (nth i corners))))
          (list 0 1 2 3)))

;; A reference point at corner i of quad q:
;;   spec = 'true (the sharp corner) | 'prev | 'next (the treatment ends)
(defun spa:cornerpoint (q corners i spec / ce)
  (setq ce (spa:cornerends (nth i q)
                           (nth (rem (+ i 3) 4) q)
                           (nth (rem (+ i 1) 4) q)
                           (car (nth i corners)) (cadr (nth i corners))))
  (cond ((eq spec 'prev) (car ce))
        ((eq spec 'next) (cadr ce))
        (t (nth i q))))

;; Draw the rectangle perimeter with its corner treatments, as ONE
;; closed polyline.  A radius corner becomes an arc segment (its bulge
;; is tan of a quarter of the angle the arc sweeps, which for a square
;; corner is tan 22.5 = 0.4142); a diagonal becomes a straight segment
;; between its two ends; a 90 corner is a single vertex.
;;
;; Returns a per-corner list holding the polyline's entity name at each
;; RADIUS corner and nil elsewhere, so the corner callouts still have
;; something to hang a radius dimension on -- DIMRADIUS takes a polyline
;; arc segment picked at a point on it just as it takes a bare arc.
(defun spa:drawrect (q corners / ce i j tyi verts pl p pp pn uprev unext
                                 dp ang arcs)
  (setq ce (spa:allends q corners) verts nil)
  (foreach i (list 0 1 2 3)
    (setq tyi (car (nth i corners)))
    (cond
      ((member tyi '("Square" "NotGiven"))
       ;; a single sharp vertex, straight out to the next corner -- a
       ;; NotGiven corner is BUILT square and flagged by its ? mark
       (setq verts (cons (cons (nth i q) 0.0) verts)))
      ((= tyi "Cut")
       (setq verts (cons (cons (cadr (nth i ce)) 0.0)
                         (cons (cons (car (nth i ce)) 0.0) verts))))
      (t                                ; Radius
       (setq p  (nth i q)
             pp (nth (rem (+ i 3) 4) q)
             pn (nth (rem (+ i 1) 4) q)
             uprev (spa:unit (cal:v- pp p))
             unext (spa:unit (cal:v- pn p))
             dp (cal:dot uprev unext)
             ang (atan (sqrt (max 0.0 (- 1.0 (* dp dp)))) dp)
             ;; the fillet sweeps the corner's exterior angle, and the
             ;; walk is counter-clockwise, so the bulge is positive
             verts (cons (cons (cadr (nth i ce)) 0.0)
                         (cons (cons (car (nth i ce)) (spa:bulge (- pi ang)))
                               verts))))))
  (setq pl (spa:perpoly (reverse verts)) arcs nil)
  (foreach i (list 0 1 2 3)
    (setq arcs (cons (if (= (car (nth i corners)) "Radius") pl nil) arcs)))
  (reverse arcs))

;; How far the deepest corner treatment sets back along its walls -- an
;; inside dimension has to stand clear of that to land on a straight run.
(defun spa:maxsetback (corners / m c)
  (setq m 0.0)
  (foreach c corners
    (setq m (max m (spa:cornsb c))))
  m)

;; Do all four corners carry the same treatment?  Four identical corners
;; get ONE callout with a Typ. suffix, the way the order sheet shows it.
(defun spa:samecorners (corners / c c0 same)
  (setq c0 (car corners) same t)
  (foreach c corners
    (if (or (/= (car c) (car c0))
            (> (abs (- (cadr c) (cadr c0))) 0.0005))
        (setq same nil)))
  same)

;; The order sheet's 90-degree corner mark: a small circle on the corner
;; point with a leader out of it.  Assumes CLAYER is already DIMENSION.
(defun spa:dim90 (quad i cen doff txt / p outd r)
  (setq p (nth i quad)
        outd (spa:unit (cal:v- p cen))
        r (* 0.18 doff))
  (entmake (list '(0 . "CIRCLE")
                 (cons 8 "DIMENSION")
                 (cons 10 (spa:wp p))
                 (cons 40 r)))
  (command "_.LEADER" (spa:wp (cal:v+ p (cal:v* outd r)))
           (spa:wp (cal:v+ p (cal:v* outd (* 1.2 doff))))
           "" txt ""))

;; A NotGiven corner's mark: the circled corner with a ? leader, and a
;; "Not Given" note past the leader tip -- the sheet must SHOW the
;; treatment was never recorded, not silently claim a 90.  The note is
;; pulled back by its own width on a left-pointing corner, so it cannot
;; read back across its leader into the shape.  (pool:dimng is the
;; donor; STANDARDS section 2.)
(defun spa:dimng (quad i cen doff sfx / p outd h tp)
  (setq p (nth i quad)
        outd (spa:unit (cal:v- p cen)))
  (spa:dim90 quad i cen doff (strcat "?" sfx))
  (setq h (* 0.25 doff)
        tp (cal:v+ p (cal:v* outd (* 1.45 doff))))
  (if (< (car outd) 0.0)
      (setq tp (list (- (car tp) (* 9.0 0.6 h)) (cadr tp))))
  (spa:text tp h "Not Given" "DIMENSION"))

;; Corner callouts, laid out the way the order sheet does them: the note
;; sits OUTSIDE the corner, on the 45-degree line out of it.
;;   Radius    -> a radius dimension read from outside the arc  (R12")
;;   Diagonal  -> an aligned dimension across the cut face      (21")
;;   90        -> a circled corner point with a 90%%d leader
;;
;; Four identical corners are called out ONCE, at the bottom-right, with
;; a Typ. suffix -- that is the whole annotation an all-radius or
;; all-diagonal cover needs.  Mixed corners are called out one by one,
;; and the square ones among them share a single 90-degree mark (Typ.
;; when there is more than one).  A plain rectangle -- four 90 corners,
;; nothing cut -- gets no corner notes at all.
;;
;; None of these ever carry the Water's Edge / Cover Size note: they are
;; corners, not overalls.  Assumes CLAYER is already DIMENSION.
(defun spa:dimcorner1 (quad corners arcs cen doff i sfx / cc ce p pp pn ty
                                                          outd am fm)
  (setq p (nth i quad)
        pp (nth (rem (+ i 3) 4) quad)
        pn (nth (rem (+ i 1) 4) quad)
        cc (nth i corners)
        ty (car cc)
        ce (spa:cornerends p pp pn ty (cadr cc))
        outd (spa:unit (cal:v- p cen)))
  (cond
    ((= ty "Radius")
     (setq am (caddr ce))
     (spa:dimrad (nth i arcs) am outd doff sfx))
    ((= ty "Cut")
     (setq fm (cal:mid (car ce) (cadr ce)))
     (spa:dimalg (car ce) (cadr ce)
                 (cal:v+ fm (cal:v* outd (* 0.6 doff))) sfx))
    ((= ty "NotGiven")
     (spa:dimng quad i cen doff sfx))
    (t                                  ; Square
     (spa:dim90 quad i cen doff (strcat "90%%d" sfx))))
  (princ))

(defun spa:dimcorners (quad corners arcs cen doff / allsame sfx ilist i)
  ;; STANDARDS section 2: four identical corners get ONE callout with a
  ;; Typ. suffix at the reference corner -- all-Square included, which
  ;; used to get no note at all.  Mixed corners are called out one by
  ;; one, each Square with its own 90%%d mark and each NotGiven with
  ;; its own ? mark and Not Given note.
  (setq allsame (spa:samecorners corners)
        sfx (if allsame " Typ." "")
        ilist (if allsame (list 1) (list 0 1 2 3)))   ; 1 = bottom-right
  (foreach i ilist
    (spa:dimcorner1 quad corners arcs cen doff i sfx))
  (princ))

;; Re-draw the guide rectangle's corners with the chosen treatments so
;; the picture matches what will be built.  gq = the guide quad,
;; corners = per-corner (type size) with the sizes already clamped for
;; display.  Returns the updated pv.
(defun spa:pvcorners (pv gq corners / ce i k cc ent)
  (foreach k (list 'ab 'bc 'cd 'da)
    (spa:pvdel (cdr (assoc k pv))))
  (setq ce (spa:allends gq corners))
  ;; shortened straight sides (side i runs corner i -> corner i+1)
  (setq i 0)
  (foreach k (list 'ab 'bc 'cd 'da)
    (setq ent (spa:pvadd (spa:pvline (cadr (nth i ce))
                                     (car (nth (rem (+ i 1) 4) ce))))
          pv (subst (cons k (list ent)) (assoc k pv) pv)
          i (1+ i)))
  ;; the corner treatments themselves
  (setq i 0)
  (foreach cc corners
    (cond
      ((= (car cc) "Cut")
       (spa:pvadd (spa:pvline (car (nth i ce)) (cadr (nth i ce)))))
      ((= (car cc) "Radius")
       (spa:arc3p (car (nth i ce)) (caddr (nth i ce)) (cadr (nth i ce))
                  "SPA-NOTES" nil)
       (spa:pvadd (spa:setcol (entlast) spa:*pv-col*))))
    (setq i (1+ i)))
  pv)

;; The size question, worded the standard's way (STANDARDS section 2):
;; "Radius for <subject>" / "Cut face length for <subject>".
(defun spa:cornersizemsg (ty label)
  (strcat (if (= ty "Radius") "Radius for " "Cut face length for ") label))

;; Prompt one corner's treatment, named the way the order sheet's corner
;; legend names them: Radius / Diagonal / 90.  ("Square" is accepted as
;; a synonym for 90 and normalised away.)  dflty/dfltsz are the autofill
;; answer (corner A's) -- Enter accepts them.  maxsb caps the
;; treatment's setback along the walls at half the shorter adjacent
;; wall, so two treatments can never overlap and fold the perimeter;
;; too-large answers are re-asked.  Returns (type size) or CAL-BACK.
(defun spa:askcorner (label dflty dfltsz ents maxsb back / ty sz cols sb e
                                                            dsz out fk fty fsz)
  ;; A form can answer this corner: <stem>-ty carries the treatment,
  ;; <stem>-sz the radius or diagonal face.  Both are consumed NOW,
  ;; valid or not -- consume-once is what keeps Back from deadlocking,
  ;; and what lets a rejected size be retyped at the keyboard instead
  ;; of re-fed.  An answer the question would not accept falls through
  ;; to the prompt exactly as if the box had been left empty.
  (if (setq fk (spa:fckey label))
      (progn
        (if (spa:fhas (read (strcat fk "-ty")))
            (progn
              (setq fty (spa:ftake (read (strcat fk "-ty"))))
              ;; the palette's OLD wire words stay accepted (an
              ;; un-rebuilt DLL keeps working) and normalise exactly
              ;; like typed legacy input
              (setq fty (cond ((equal fty "90") "Square")
                              ((equal fty "Diagonal") "Cut")
                              ((equal fty "NG") "NotGiven")
                              (t fty)))
              (if (not (member fty '("Square" "Radius" "Cut" "NotGiven")))
                  (setq fty nil))))
        (if (spa:fhas (read (strcat fk "-sz")))
            (progn
              (setq fsz (spa:ftake (read (strcat fk "-sz"))))
              (if (not (and (numberp fsz) (> fsz 0.0)))
                  (setq fsz nil))))))
  (setq cols (mapcar 'spa:getcol ents))
  (foreach e ents (spa:setcol e spa:*hi-col*))
  (while (null out)
    (cal:osup)
    ;; the form's treatment stands in for the question ONCE -- a Back
    ;; from the size question re-asks at the keyboard.  The question is
    ;; the canonical Treatment of STANDARDS section 2; the pre-standard
    ;; words (90, ROUNDED, DIAG/DIAGONAL, NG) stay accepted typed in
    ;; full, hidden from the bracket, and are normalised HERE.
    (setq ty (if fty fty
                 (cal:askkw (strcat "How should " label " be treated?")
                            "Square Radius Cut NotGiven NG 90 ROUNDED DIAG DIAGONAL"
                            "Square/Radius/Cut/NotGiven" dflty back))
          fty nil)
    (cal:osdown)
    (setq ty (cond ((equal ty "NG") "NotGiven")
                   ((equal ty "90") "Square")
                   ((equal ty "ROUNDED") "Radius")
                   ((member ty '("DIAG" "DIAGONAL")) "Cut")
                   (t ty)))
    (cond
      ;; backed out of the type question -- out of the corner entirely
      ((eq ty 'CAL-BACK) (setq out 'CAL-BACK))
      ;; the two unsized answers: Square is a true 90, NotGiven is
      ;; DRAWN square and flagged -- nothing was measured, so no size
      ((member ty '("Square" "NotGiven")) (setq out (list ty 0.0)))
      (t
       ;; the autofill size only stands in when it came from the SAME
       ;; treatment -- a radius is not a cut face
       (setq dsz (if (or (null dfltsz) (<= dfltsz 0.0) (/= ty dflty))
                     nil dfltsz)
             ;; the form's size stands in the same way -- once; the
             ;; too-large loop below re-asks at the keyboard
             sz (if fsz fsz
                    (spa:askd (spa:cornersizemsg ty label) nil dsz t))
             fsz nil)
       ;; Back at the size re-asks the type, its previous question
       (if (not (eq sz 'CAL-BACK))
           (progn
             ;; Radius sets back r along each wall; a Diagonal face f
             ;; sets back f/sqrt(2) on a 90-degree corner
             (while (and maxsb
                         (not (eq sz 'CAL-BACK))
                         (> (setq sb (if (= ty "Radius") sz (* sz 0.70711)))
                            maxsb))
               (princ (strcat "\nToo large for this corner's walls -- max "
                              (rtos (if (= ty "Radius") maxsb
                                        (/ maxsb 0.70711)))
                              ".  Re-enter."))
               (setq sz (spa:askd (spa:cornersizemsg ty label)
                                  nil nil t)))
             (if (not (eq sz 'CAL-BACK)) (setq out (list ty sz))))))))
  (mapcar '(lambda (e c) (spa:setcol e c)) ents cols)
  out)

;;; -------------------- rectangle flow ---------------------------------

;; Gray nominal rectangle with its corner letters.
(defun spa:rectpreview ( / gq cen pr ent all pv)
  (setq gq (list (list 0.0 0.0) (list 240.0 0.0)
                 (list 240.0 200.0) (list 0.0 200.0))
        cen (list 120.0 100.0)
        all nil pv nil)
  (setq pv (list (cons 'ab (list (spa:pvline (nth 0 gq) (nth 1 gq))))
                 (cons 'bc (list (spa:pvline (nth 1 gq) (nth 2 gq))))
                 (cons 'cd (list (spa:pvline (nth 2 gq) (nth 3 gq))))
                 (cons 'da (list (spa:pvline (nth 3 gq) (nth 0 gq)))))
        all (apply 'append (mapcar 'cdr pv)))
  (foreach pr (list (list (nth 0 gq) "A") (list (nth 1 gq) "B")
                    (list (nth 2 gq) "C") (list (nth 3 gq) "D"))
    (spa:text (cal:v+ (car pr)
                      (cal:v* (spa:unit (cal:v- (car pr) cen)) 22.0))
              12.0 (cadr pr) "SPA-NOTES")
    (setq ent (spa:setcol (entlast) spa:*pv-col*)
          all (cons ent all)
          pv (cons (cons (spa:lblkey (cadr pr)) (list ent)) pv)))
  (setq spa:*pvents* all)
  pv)

;; Full guided flow for a rectangular spa.
(defun spa:rectflow ( / oldclay pv gq gsc w l corners anycut arcs quad
                        a b c d cen doff th allsame i j tmp lbls cc back
                        rows lbl mode1 meth ans g w2 l2 c2 org2 q2 cen2 arcs2
                        xlo xhi ylo yhi out1 sb1 sb2 ip1 ip2 hrows done)
  (setq oldclay (getvar "CLAYER")
        pv (spa:rectpreview))
  (command "_.ZOOM" "_Window"
           (spa:wp (list -110.0 -90.0)) (spa:wp (list 350.0 320.0)))
  (princ "\nA gray guide spa is shown -- the RED element is the dimension being asked for.")
  (princ "\nCorners: A bottom-left, B bottom-right, C top-right, D top-left.")
  (princ "\n(Enter at the length takes the width, i.e. a square spa)")
  (princ "\n(Back re-asks the previous question)")

  ;; -------- the two overalls (a moulded shell is a true rectangle)
  (defun rc:sides ( / ans)
    (setq ans (spa:askseqb
                (list (list 'w 'REQ "Overall WIDTH across (A-B)"
                            (append (cdr (assoc 'ab pv)) (cdr (assoc 'cd pv))
                                    (spa:lbl pv '(lA lB))))
                      ;; the width is offered back as the length, so a
                      ;; square spa is one measurement and Enter -- type
                      ;; a different value to decline it
                      (list 'l 'SUG "Overall LENGTH up (A-D)"
                            (append (cdr (assoc 'da pv)) (cdr (assoc 'bc pv))
                                    (spa:lbl pv '(lA lD)))
                            '(w)))
                nil))
    (setq w (spa:sq ans 'w)
          l (if (spa:sq ans 'l) (spa:sq ans 'l) w))   ; NA -> square
    nil)

  ;; -------- corner treatments; corner A autofills B, C and D
  (defun rc:corners ( / )
    (princ "\n(corner A's answer autofills B, C and D -- Enter accepts it,")
    (princ "\n or type a different treatment for that corner)")
    (setq lbls (list "A" "B" "C" "D")
          corners nil i 0 back nil)
    (while (and (< i 4) (not back))
      (setq cc (spa:askcorner
                 (strcat "Corner " (nth i lbls))
                 (if (> i 0) (car (car (reverse corners))) nil)
                 (if (> i 0) (cadr (car (reverse corners))) nil)
                 (spa:lbl pv (list (spa:lblkey (nth i lbls))))
                 (* 0.5 (min w l))
                 t))
      (if (eq cc 'CAL-BACK)
          (if (= i 0)
              (setq back t)             ; back out of the whole stage
              (setq i (1- i) corners (cdr corners)))
          (setq corners (cons cc corners) i (1+ i))))
    (if back
        'CAL-BACK
        (progn
          (setq corners (reverse corners) anycut nil)
          (foreach cc corners (if (spa:cutp cc) (setq anycut t)))
          ;; show the chosen treatments on the guide, scaled from the
          ;; real spa onto the 240 x 200 nominal and capped so a big
          ;; treatment cannot swallow the guide
          (setq gq (list (list 0.0 0.0) (list 240.0 0.0)
                         (list 240.0 200.0) (list 0.0 200.0))
                gsc (/ 240.0 (max w 1.0)))
          (if anycut
              (setq pv (spa:pvcorners
                         pv gq
                         (mapcar '(lambda (c)
                                    (list (car c) (min 50.0 (* (cadr c) gsc))))
                                 corners))))
          nil)))

  (spa:stages (list 'rc:sides 'rc:corners))
  (spa:pvkill)

  ;; -------------------------------------------------- orientation
  ;; The long overall always runs west to east, whichever order the two
  ;; were typed in.  Turning the cover a quarter turn clockwise carries
  ;; the corners round with it: the corner that was B lands bottom-left,
  ;; so the treatments and their letters rotate one step with the shape.
  (if (> l w)
      (setq tmp w
            w l
            l tmp
            corners (append (cdr corners) (list (car corners)))
            lbls (append (cdr lbls) (list (car lbls)))
            spa:*turned* t))
  (if spa:*turned*
      (princ "\nThe long overall runs across, so the cover is drawn a quarter turn over."))

  (setq quad (spa:quadat (list 0.0 0.0) w l)
        a (car quad) b (cadr quad) c (caddr quad) d (cadddr quad)
        cen (list (* 0.5 w) (* 0.5 l))
        doff (max 6.0 (/ (max w l) 12.0))
        th (max 1.0 (/ (max w l) 40.0))
        spa:*dashlt* (spa:ltload "DASHED")
        mode1 spa:*mode*)

  ;; ------------------------------------------- draw the first outline
  (setq arcs (spa:drawrect quad corners))

  ;; ------------------------------------------- and, if wanted, the other
  ;; Resolved BEFORE anything is dimensioned, because every dimension
  ;; line stands off the COVER outline -- the outer of the two.
  ;; Asked as one re-enterable unit: a Back anywhere inside either
  ;; branch re-opens the offer, so the method itself can be changed.
  (setq meth (spa:askother) done nil)
  (while (and meth (not done))
    (if (= meth "Offset")
        (progn
          (setq g (spa:askgap))
          (if (eq g 'CAL-BACK)
              (setq meth (spa:askother))
              (setq w2 (+ w (* 2.0 g))
                    l2 (+ l (* 2.0 g))
                    c2 (spa:offcorners corners g)
                    done t)))
        (progn
          (princ (strcat "\nThe two outlines share a centre; give the "
                         (spa:modeword (spa:othermode)) " as measured."))
          (setq ans (spa:askseqb
                      (list (list 'w2 'REQ (strcat (strcase (spa:modeword (spa:othermode)) t)
                                                   " overall ACROSS") nil)
                            (list 'l2 'SUG (strcat (strcase (spa:modeword (spa:othermode)) t)
                                                   " overall UP") nil '(w2)))
                      t))
          (if (eq ans 'CAL-BACK)
              (setq meth (spa:askother))
              (setq w2 (spa:sq ans 'w2)
                    l2 (if (spa:sq ans 'l2) (spa:sq ans 'l2) w2)
                    ;; the implied lap drives the corner sizes, which the
                    ;; user may then correct one at a time
                    g  (* 0.25 (+ (- w2 w) (- l2 l)))
                    c2 (spa:offcorners corners g)
                    c2 (spa:askothercorners c2 lbls (* 0.5 (min w2 l2)))
                    done t)))))
  (if (and meth done)
      (if (or (<= w2 0.0) (<= l2 0.0))
          (progn
            (spa:valnote "THE SECOND OUTLINE CAME OUT AT OR BELOW ZERO - SKIPPED")
            (setq meth nil))
          (setq org2 (spa:orgfor cen w2 l2)
                q2   (spa:quadat org2 w2 l2)
                cen2 cen)))

  ;; the cover is the larger, so its extents are the ones to stand off
  (setq xhi (if meth (max w (+ (car org2) w2)) w)
        ylo (if meth (min 0.0 (cadr org2)) 0.0)
        xlo (if meth (min 0.0 (car org2)) 0.0)
        yhi (if meth (max l (+ (cadr org2) l2)) l))

  ;; ------------------------------------------- draw the second outline
  (if meth
      (progn
        (spa:setmode (spa:othermode))
        (setq arcs2 (spa:drawrect q2 c2))
        (spa:setmode mode1)))

  ;; -------------------------------------------------- dimensions
  ;; Laid out the way the order sheet does it.  The COVER's overalls go
  ;; outside -- across 2 ft above it, up 3 ft to its left.  The WATER'S
  ;; EDGE's overalls, when both outlines are drawn, go a third of the way
  ;; INTO the water's edge.  When all four corners match, that plus one
  ;; Typ. corner callout is the whole drawing; when they do not, each
  ;; side a cut has shortened also gets its remaining FLAT dimensioned.
  (setq allsame (spa:samecorners corners)
        out1 (or (null meth) (= mode1 "Coversize"))
        sb1 (spa:maxsetback corners)
        ip1 (spa:insidepts 0.0 w 0.0 l sb1 sb1))
  (setvar "CLAYER" "DIMENSION")
  (spa:dimstylenow th)
  ;; the overalls -- the only dims that carry the Water's Edge / Cover
  ;; Size note
  (if out1
      (spa:dimoveralls t d c a d xlo yhi)
      (spa:dimoveralls nil (nth 0 ip1) (nth 1 ip1) (nth 2 ip1) (nth 3 ip1)
                       xlo yhi))
  ;; the flats
  (if (not allsame)
      (foreach i (list 0 1 2 3)
        (setq j (rem (+ i 1) 4))
        (if (or (spa:cutp (nth i corners))
                (spa:cutp (nth j corners)))
            (spa:dimalg (spa:cornerpoint quad corners i 'next)
                        (spa:cornerpoint quad corners j 'prev)
                        (spa:outoff (nth i quad) (nth j quad) cen spa:*flatoff*)
                        nil))))
  ;; corner callouts (no note -- these are corners, not overalls)
  (spa:dimcorners quad corners arcs cen doff)

  ;; the second outline, in ITS dimension style, plus one Typ. corner
  ;; callout at the top-left when its corners all match
  (if meth
      (progn
        (spa:setmode (spa:othermode))
        (spa:dimstylenow th)
        (setq sb2 (spa:maxsetback c2)
              ip2 (spa:insidepts (car org2) (+ (car org2) w2)
                                 (cadr org2) (+ (cadr org2) l2) sb2 sb2))
        (if out1
            (spa:dimoveralls nil (nth 0 ip2) (nth 1 ip2) (nth 2 ip2) (nth 3 ip2)
                             xlo yhi)
            (spa:dimoveralls t (nth 3 q2) (nth 2 q2) (nth 0 q2) (nth 3 q2)
                             xlo yhi))
        (if (spa:samecorners c2)
            (spa:dimcorner1 q2 c2 arcs2 cen2 doff 3 " Typ."))
        (spa:setmode mode1)
        ;; and how far the cover laps the water's edge, at the bottom
        (spa:dimstyle spa:*ds-cover* th 1.0)
        (spa:dimlap (* 0.5 (+ xlo xhi)) ylo (max 0.0 (cadr org2))))
      nil)
  (setvar "CLAYER" oldclay)

  ;; -------------------------------------------------- labels + report
  ;; the letters travel with their corners, so a turned cover still reads
  ;; back against the report table
  (setq i 0)
  (foreach lbl quad
    (spa:text (cal:v+ lbl (cal:v* (spa:unit (cal:v- lbl cen)) (* 1.6 th)))
              th (nth i lbls) "SPA-NOTES")
    (setq i (1+ i)))
  (spa:modenote xlo (- ylo (* 1.4 spa:*dimoff*)) th)
  (setq rows (list (list (strcat "OVERALL ACROSS (" (nth 0 lbls) "-" (nth 1 lbls) ")")
                         w w)
                   (list (strcat "OVERALL UP (" (nth 0 lbls) "-" (nth 3 lbls) ")")
                         l l)))
  (setq i 0)
  (foreach cc corners
    (setq rows (append rows
                       (list (list (strcat "CORNER " (nth i lbls) " "
                                           (strcase (car cc)))
                                   (if (spa:cutp cc) (cadr cc) nil)
                                   (cadr cc))))
          i (1+ i)))
  (if meth
      (progn
        (spa:setmode (spa:othermode))
        (setq rows (append rows (spa:otherrows w2 l2)))
        (setq i 0)
        (foreach cc c2
          (setq rows (append rows
                             (list (list (strcat (strcase (spa:modeword spa:*mode*))
                                                 " COR " (nth i lbls) " "
                                                 (strcase (car cc)))
                                         (if (spa:cutp cc) (cadr cc) nil)
                                         (cadr cc))))
                i (1+ i)))
        (spa:setmode mode1)))
  ;; -------------------------------------------------- hinges
  (setq hrows
    (cond ((= mode1 "Coversize")
           (spa:hingeflow (list "RECT" quad corners) 0.0 w th t))
          (meth
           (spa:hingeflow (list "RECT" q2 c2) (car org2) (+ (car org2) w2) th t))
          (t
           (spa:hingeflow (list "RECT" quad corners) 0.0 w th nil))))
  (if hrows (setq rows (append rows hrows)))
  (spa:report rows spa:*valnotes* (+ xhi spa:*dimoff*) yhi th "SPA-NOTES")
  (princ "\nSpa layout complete -- see the report table.")
  (princ))

;;; -------------------- octagon ----------------------------------------
;;;
;;;  Eight corners, counter-clockwise from the left end of the bottom
;;;  flat:
;;;                     F ---------- E
;;;                    /              \        B = overall across
;;;                   G                D       A = overall up
;;;                   |                |       T = the flats across
;;;                   H                C       V = the flats up
;;;                    \              /        S = cut along the side
;;;                     A ---------- B         S1 = cut up the end
;;;                                            S2 = the cut face itself
;;;
;;;  A and B are required; every cut letter may be NA, in which case the
;;;  shape falls back to a true square octagon (45-degree cuts, all eight
;;;  sides equal) sized off A and B.

(setq spa:*octnames* (list "A" "B" "C" "D" "E" "F" "G" "H"))

;; (i j kind) for each edge -- kind 'side is a flat, 'cut is a corner.
(setq spa:*octedges*
      (list '(0 1 side) '(1 2 cut) '(2 3 side) '(3 4 cut)
            '(4 5 side) '(5 6 cut) '(6 7 side) '(7 0 cut)))

;; Resolve the sheet letters against the overalls.
;;
;; The cut is normally measured as its FACE (S2) -- that is the tape run
;; a crew actually takes across the corner -- so a 45-degree face
;; resolves to equal legs, S = S1 = S2 / sqrt 2.  With even that
;; unmeasured the shape falls back to a true square octagon, where the
;; flats equal the cut faces:
;;   c = min(A,B) / (2 + sqrt 2)  ->  T = B - 2c,  V = A - 2c
;; Any letter that WAS measured wins and its partner is derived from it.
;; Returns (S T S1 V).
(defun spa:octov (aov bov sraw traw s1raw vraw s2raw / c s tv s1 v)
  (setq c (if s2raw
              (/ s2raw 1.41421356237)
              (/ (min aov bov) 3.41421356237)))
  (cond
    (sraw (setq s sraw tv (- bov (* 2.0 sraw))))
    (traw (setq s (/ (- bov traw) 2.0) tv traw))
    (t (setq s c tv (- bov (* 2.0 c)))))
  (cond
    (s1raw (setq s1 s1raw v (- aov (* 2.0 s1raw))))
    (vraw (setq s1 (/ (- aov vraw) 2.0) v vraw))
    ;; an unmeasured vertical cut matches the horizontal one (45 deg)
    (t (setq s1 s v (- aov (* 2.0 s)))))
  (list s tv s1 v))

;; The eight corner points for overalls a/b and cuts s (across) and
;; s1 (up).
(defun spa:octpts (bov aov s s1)
  (list (list s 0.0) (list (- bov s) 0.0)
        (list bov s1) (list bov (- aov s1))
        (list (- bov s) aov) (list s aov)
        (list 0.0 (- aov s1)) (list 0.0 s1)))

;; Gray nominal octagon (a regular one -- that is what the shape being
;; measured looks like) plus the overall-sheet ties.  Returns
;; (outline-pv . tie-pv).
(defun spa:octpreview ( / npts cen e p q ent all pv k pvo)
  (setq npts (spa:octpts 240.0 240.0 70.294 70.294)
        cen (spa:centroid npts)
        all nil pv nil)
  (foreach e spa:*octedges*
    (setq p (nth (car e) npts) q (nth (cadr e) npts)
          ent (spa:pvline p q)
          pv (cons (cons (list (car e) (cadr e)) (list ent)) pv)
          all (cons ent all)))
  (setq k 0)
  (foreach p npts
    (spa:text (spa:lbloff p cen npts 20.0) 12.0 (nth k spa:*octnames*) "SPA-NOTES")
    (setq ent (spa:setcol (entlast) spa:*pv-col*)
          all (cons ent all)
          pv (cons (cons (spa:lblkey (nth k spa:*octnames*)) (list ent)) pv)
          k (1+ k)))
  (setq spa:*pvents* all)
  ;; the field-sheet ties: B/T/S across the top, A/S1/V down the left,
  ;; S2 parallel to the bottom-right cut
  (setq pvo (list
    (spa:pvtie (list 0.0 300.0) (list 240.0 300.0) "B" 10.0)
    (spa:pvtie (list 70.294 278.0) (list 169.706 278.0) "T" 10.0)
    (spa:pvtie (list 0.0 278.0) (list 70.294 278.0) "S" 10.0)
    (spa:pvtie (list -85.0 0.0) (list -85.0 240.0) "A" 10.0)
    (spa:pvtie (list -42.0 169.706) (list -42.0 240.0) "S1" 10.0)
    (spa:pvtie (list -42.0 70.294) (list -42.0 169.706) "V" 10.0)
    (spa:pvtie (list 185.0 -15.0) (list 255.0 55.0) "S2" 10.0)))
  (cons pv pvo))

;; Full guided flow for an octagonal spa.
(defun spa:octflow ( / oldclay pvs pv pvo ans bov aov traw sraw s1raw vraw s2raw
                       ovres s tv s1 v pts cen doff th e p q k rows
                       tact vact s2act alleq tmp
                       mode1 meth g kk b2 a2 s2 s12 ovr org2 pts2 cen2
                       xlo xhi ylo yhi out1 ip1 ip2 hrows done)
  (setq oldclay (getvar "CLAYER")
        pvs (spa:octpreview)
        pv (car pvs) pvo (cdr pvs))
  (command "_.ZOOM" "_Window"
           (spa:wp (list -120.0 -70.0)) (spa:wp (list 340.0 340.0)))
  (princ "\nA gray guide spa is shown -- the RED tie is the dimension being asked for.")
  (princ "\nUsually A, B and the cut FACE S2 are all that is measured -- NA the rest.")
  (princ "\nEven S2 may be NA: A and B alone draw a true square octagon.")
  (princ "\n(after the first answer, Back re-asks the previous one)")

  (setq ans (spa:askseqb
              (list (list 'b 'REQ "B - overall size ACROSS" (cdr (assoc "B" pvo)))
                    (list 'a 'SUG "A - overall size UP" (cdr (assoc "A" pvo)) '(b))
                    (list 's2 'NAX "S2 - corner cut FACE (the tape across the cut)"
                          (cdr (assoc "S2" pvo)))
                    (list 'tt 'NAX "T - flat across (top & bottom)" (cdr (assoc "T" pvo)))
                    (list 'ss 'NAX "S - corner cut along the side" (cdr (assoc "S" pvo)))
                    (list 's1 'NAX "S1 - corner cut up the end" (cdr (assoc "S1" pvo)))
                    (list 'vv 'NAX "V - flat up (left & right)" (cdr (assoc "V" pvo))))
              nil)
        bov (spa:sq ans 'b)
        aov (if (spa:sq ans 'a) (spa:sq ans 'a) bov)   ; NA at A -> square
        traw (spa:sq ans 'tt) sraw (spa:sq ans 'ss)
        s1raw (spa:sq ans 's1) vraw (spa:sq ans 'vv)
        s2raw (spa:sq ans 's2)
        ovres (spa:octov aov bov sraw traw s1raw vraw s2raw)
        s (car ovres) tv (cadr ovres) s1 (caddr ovres) v (cadddr ovres))
  (spa:pvkill)

  ;; the sheet letters must close POSITIVE against the overalls; one
  ;; that does not fit is adjusted and the report says so
  (if (<= tv 1.0e-6)
      (progn
        (setq tv (min 6.0 (* 0.25 bov)) s (/ (- bov tv) 2.0))
        (spa:valnote "S + T + S DOES NOT FIT B - ADJUSTED")))
  (if (<= s 1.0e-6)
      (progn
        (setq s (min 6.0 (* 0.125 bov)) tv (- bov s s))
        (spa:valnote "T LONGER THAN B - ADJUSTED")))
  (if (<= v 1.0e-6)
      (progn
        (setq v (min 6.0 (* 0.25 aov)) s1 (/ (- aov v) 2.0))
        (spa:valnote "S1 + V + S1 DOES NOT FIT A - ADJUSTED")))
  (if (<= s1 1.0e-6)
      (progn
        (setq s1 (min 6.0 (* 0.125 aov)) v (- aov s1 s1))
        (spa:valnote "V LONGER THAN A - ADJUSTED")))

  ;; -------------------------------------------------- orientation
  ;; the long overall runs west to east; a quarter turn swaps the two
  ;; overalls and, with them, the flats and the cut legs
  (if (> aov bov)
      (setq tmp bov  bov  aov   aov   tmp
            tmp s    s    s1    s1    tmp
            tmp tv   tv   v     v     tmp
            tmp traw traw vraw  vraw  tmp
            tmp sraw sraw s1raw s1raw tmp
            spa:*turned* t))
  (if spa:*turned*
      (princ "\nThe long overall runs across, so the spa is drawn a quarter turn over."))

  (setq pts (spa:octpts bov aov s s1)
        cen (spa:centroid pts)
        doff (max 6.0 (/ (max bov aov) 12.0))
        th (max 1.0 (/ (max bov aov) 40.0))
        spa:*dashlt* (spa:ltload "DASHED")
        mode1 spa:*mode*)

  ;; ------------------------------------------- draw the first outline
  ;; one closed polyline, not eight loose lines
  (spa:perpoly (mapcar '(lambda (p) (cons p 0.0)) pts))

  ;; ------------------------------------------- and, if wanted, the other
  ;; An octagon offset by g keeps its shape: the overalls each grow by
  ;; 2g and the cut legs by g*(s + s1 - face)/the other leg.
  ;; one re-enterable unit: a Back inside either branch re-opens the offer
  (setq meth (spa:askother) done nil)
  (while (and meth (not done))
    (if (= meth "Offset")
        (progn
          (setq g (spa:askgap))
          (if (eq g 'CAL-BACK)
              (setq meth (spa:askother))
              (setq kk  (- (+ s s1) (distance (nth 1 pts) (nth 2 pts)))
                    b2  (+ bov (* 2.0 g))
                    a2  (+ aov (* 2.0 g))
                    s2  (+ s  (/ (* g kk) s1))
                    s12 (+ s1 (/ (* g kk) s))
                    done t)))
        (progn
          (princ (strcat "\nThe two outlines share a centre; give the "
                         (spa:modeword (spa:othermode)) " as measured."))
          (setq ans (spa:askseqb
                      (list (list 'b2 'REQ "Overall ACROSS" nil)
                            (list 'a2 'SUG "Overall UP" nil '(b2))
                            (list 'f2 'NAX "Corner cut FACE" nil))
                      t))
          (if (eq ans 'CAL-BACK)
              (setq meth (spa:askother))
              (setq b2 (spa:sq ans 'b2)
                    a2 (if (spa:sq ans 'a2) (spa:sq ans 'a2) b2)
                    ovr (spa:octov a2 b2 nil nil nil nil (spa:sq ans 'f2))
                    s2 (car ovr) s12 (caddr ovr)
                    done t)))))
  (if (and meth done)
      (if (or (<= b2 0.0) (<= a2 0.0) (<= s2 0.0) (<= s12 0.0)
              (<= (- b2 (* 2.0 s2)) 0.0) (<= (- a2 (* 2.0 s12)) 0.0))
          (progn
            (spa:valnote "THE SECOND OUTLINE WILL NOT CLOSE - SKIPPED")
            (setq meth nil))
          (setq org2 (spa:orgfor cen b2 a2)
                pts2 (mapcar '(lambda (p) (cal:v+ p org2))
                             (spa:octpts b2 a2 s2 s12))
                cen2 cen)))

  ;; the cover is the larger, so its extents are the ones to stand off
  (setq xlo (if meth (min 0.0 (car org2)) 0.0)
        xhi (if meth (max bov (+ (car org2) b2)) bov)
        ylo (if meth (min 0.0 (cadr org2)) 0.0)
        yhi (if meth (max aov (+ (cadr org2) a2)) aov))

  ;; ------------------------------------------- draw the second outline
  (if meth
      (progn
        (spa:setmode (spa:othermode))
        (spa:perpoly (mapcar '(lambda (p) (cons p 0.0)) pts2))
        (spa:setmode mode1)))

  ;; -------------------------------------------------- dimensions
  ;; The order sheet's octagon panel carries three things: the overall
  ;; across, the overall up, and ONE corner-cut callout, because all
  ;; eight sides are equal.  When the cut letters make the sides UNequal
  ;; the two flats are dimensioned as well, inboard of the overalls.
  (setq tact (distance (nth 0 pts) (nth 1 pts))
        vact (distance (nth 2 pts) (nth 3 pts))
        s2act (distance (nth 1 pts) (nth 2 pts))
        ;; "all sides equal" to within 1/8" -- a rounded-off cut face
        ;; like 39-3/8" must still read as the regular octagon it is
        alleq (and (< (abs (- tact vact)) 0.125)
                   (< (abs (- tact s2act)) 0.125))
        out1 (or (null meth) (= mode1 "Coversize"))
        ip1 (spa:insidepts 0.0 bov 0.0 aov s s1))
  (setvar "CLAYER" "DIMENSION")
  (spa:dimstylenow th)
  ;; the two overalls, hooked to real corners
  (if out1
      (spa:dimoveralls t (nth 7 pts) (nth 2 pts) (nth 0 pts) (nth 5 pts)
                       xlo yhi)
      (spa:dimoveralls nil (nth 0 ip1) (nth 1 ip1) (nth 2 ip1) (nth 3 ip1)
                       xlo yhi))
  ;; the flats, only when the eight sides are NOT simply all equal --
  ;; a true square octagon needs the overalls and the cut, nothing else
  (if (not alleq)
      (progn
        (spa:dimalg (nth 0 pts) (nth 1 pts)
                    (list (* 0.5 bov) (- 0.0 spa:*flatoff*)) nil)
        (spa:dimalg (nth 2 pts) (nth 3 pts)
                    (list (+ bov spa:*flatoff*) (* 0.5 aov)) nil)))
  ;; the corner cut itself -- one callout on the bottom-right cut, Typ.
  ;; because all four cuts of an octagon are the same
  (setq p (nth 1 pts) q (nth 2 pts))
  (spa:dimalg p q (spa:outoffp p q pts (* 0.8 doff)) " Typ.")

  ;; the second outline, in ITS dimension style, plus its cut face
  (if meth
      (progn
        (spa:setmode (spa:othermode))
        (spa:dimstylenow th)
        (setq ip2 (spa:insidepts (car org2) (+ (car org2) b2)
                                 (cadr org2) (+ (cadr org2) a2) s2 s12))
        (if out1
            (spa:dimoveralls nil (nth 0 ip2) (nth 1 ip2) (nth 2 ip2) (nth 3 ip2)
                             xlo yhi)
            (spa:dimoveralls t (nth 7 pts2) (nth 2 pts2) (nth 0 pts2) (nth 5 pts2)
                             xlo yhi))
        (setq p (nth 5 pts2) q (nth 6 pts2))
        (spa:dimalg p q (spa:outoffp p q pts2 (* 0.8 doff)) " Typ.")
        (spa:setmode mode1)
        ;; and how far the cover laps the water's edge, at the bottom
        (spa:dimstyle spa:*ds-cover* th 1.0)
        (spa:dimlap (* 0.5 (+ xlo xhi)) ylo (max 0.0 (cadr org2)))))
  (setvar "CLAYER" oldclay)

  ;; -------------------------------------------------- labels + report
  (setq k 0)
  (foreach p pts
    (spa:text (spa:lbloff p cen pts (* 1.8 th)) th (nth k spa:*octnames*) "SPA-NOTES")
    (setq k (1+ k)))
  (spa:modenote xlo (- ylo (* 1.4 spa:*dimoff*)) th)
  (setq rows (list (list "OVERALL ACROSS" bov bov)
                   (list "OVERALL UP" aov aov)
                   (list "T - FLAT ACROSS" traw tact)
                   (list "V - FLAT UP" vraw vact)
                   (list "S - CUT ALONG SIDE" sraw s)
                   (list "S1 - CUT UP END" s1raw s1)
                   (list "S2 - CUT FACE" s2raw s2act)))
  (if meth
      (progn
        (spa:setmode (spa:othermode))
        (setq rows (append rows
                           (spa:otherrows b2 a2)
                           (list (list (strcat (strcase (spa:modeword spa:*mode*))
                                               " CUT FACE")
                                       nil (distance (nth 1 pts2) (nth 2 pts2))))))
        (spa:setmode mode1)))
  ;; -------------------------------------------------- hinges
  (setq hrows
    (cond ((= mode1 "Coversize")
           (spa:hingeflow (list "OCT" pts) 0.0 bov th t))
          (meth
           (spa:hingeflow (list "OCT" pts2) (car org2) (+ (car org2) b2) th t))
          (t
           (spa:hingeflow (list "OCT" pts) 0.0 bov th nil))))
  (if hrows (setq rows (append rows hrows)))
  (spa:report rows spa:*valnotes* (+ xhi spa:*dimoff*) yhi th "SPA-NOTES")
  (princ "\nSpa layout complete -- see the report table.")
  (princ))

;;; -------------------- round ------------------------------------------
;;;
;;;  A round spa is a circle when the two overalls agree and an ellipse
;;;  when they do not -- B across, A up, both measured through the
;;;  middle.  There are no corners, so the perimeter is drawn exactly to
;;;  the overalls.

(defun spa:roundpreview ( / cen pv)
  (setq cen (list 120.0 120.0))
  (spa:body-round cen 240.0 240.0 "SPA-NOTES" nil)
  (spa:pvadd (spa:setcol (entlast) spa:*pv-col*))
  (setq pv (list
    (spa:pvtie (list 0.0 285.0) (list 240.0 285.0) "B" 10.0)
    (spa:pvtie (list -50.0 0.0) (list -50.0 240.0) "A" 10.0)))
  pv)

(defun spa:roundflow ( / oldclay pv ans bov aov cen doff th rows tmp
                         mode1 meth g b2 a2 cen2 xlo xhi ylo yhi
                         out1 bl br ab at hrows done)
  (setq oldclay (getvar "CLAYER")
        pv (spa:roundpreview))
  (command "_.ZOOM" "_Window"
           (spa:wp (list -130.0 -70.0)) (spa:wp (list 340.0 330.0)))
  ;; A round spa takes ONE measurement -- the diameter, through the
  ;; middle.  A spa that measured out of round is the exception, not the
  ;; rule, so it costs a keyword rather than a second prompt every time:
  ;; type O and the two axes are asked for instead.
  (princ "\nRound spa -- the diameter, measured through the middle.")
  (princ "\n(measured out of round?  type O for the two axes instead)")
  ;; A form can settle this up front.  A stored A means the two axes
  ;; were measured -- the Outofround branch -- and is only PEEKED at
  ;; here: the sequence below is what consumes it.  A stored numeric B
  ;; alone is the diameter itself, consumed now.  A (b . nil) is an NA:
  ;; consumed, and the diameter is prompted for as always.
  (setq bov (cond ((spa:fhas 'a) "Outofround")
                  ((and (spa:fhas 'b)
                        (numberp (setq bov (spa:ftake 'b)))
                        (> bov 0.0))
                   bov)
                  (t (spa:askd "Overall diameter" "Outofround" nil nil))))
  (if (= (type bov) 'STR)
      (progn
        (setq ans (spa:askseqb
                    (list (list 'b 'REQ "B - overall size ACROSS"
                                (cdr (assoc "B" pv)))
                          (list 'a 'SUG "A - overall size UP"
                                (cdr (assoc "A" pv)) '(b)))
                    nil)
              bov (spa:sq ans 'b)
              aov (if (spa:sq ans 'a) (spa:sq ans 'a) bov)))
      (setq aov bov))
  (spa:pvkill)
  ;; an out-of-round spa lies with its long overall west to east
  (if (> aov bov)
      (setq tmp bov bov aov aov tmp
            spa:*turned* t))
  (if spa:*turned*
      (princ "\nThe long overall runs across, so the spa is drawn a quarter turn over."))

  (setq cen (list (* 0.5 bov) (* 0.5 aov))
        doff (max 6.0 (/ (max bov aov) 12.0))
        th (max 1.0 (/ (max bov aov) 40.0))
        spa:*dashlt* (spa:ltload "DASHED")
        mode1 spa:*mode*)
  (spa:perround cen bov aov)
  (if (> (abs (- aov bov)) 1.0e-6)
      (princ "\nThe two overalls differ, so the spa is drawn as an ellipse.")
      (princ "\nA and B agree, so the spa is drawn as a true circle."))

  ;; ------------------------------------------- and, if wanted, the other
  ;; one re-enterable unit: a Back inside either branch re-opens the offer
  (setq meth (spa:askother) done nil)
  (while (and meth (not done))
    (if (= meth "Offset")
        (progn
          (setq g (spa:askgap))
          (if (eq g 'CAL-BACK)
              (setq meth (spa:askother))
              (setq b2 (+ bov (* 2.0 g))
                    a2 (+ aov (* 2.0 g))
                    done t)))
        (progn
          (princ (strcat "\nThe two outlines share a centre; give the "
                         (spa:modeword (spa:othermode)) " as measured."))
          (setq ans (spa:askseqb
                      (list (list 'b2 'REQ "Overall ACROSS" nil)
                            (list 'a2 'SUG "Overall UP" nil '(b2)))
                      t))
          (if (eq ans 'CAL-BACK)
              (setq meth (spa:askother))
              (setq b2 (spa:sq ans 'b2)
                    a2 (if (spa:sq ans 'a2) (spa:sq ans 'a2) b2)
                    done t)))))
  (if (and meth done)
      (if (or (<= b2 0.0) (<= a2 0.0))
          (progn
            (spa:valnote "THE SECOND OUTLINE CAME OUT AT OR BELOW ZERO - SKIPPED")
            (setq meth nil))
          (setq cen2 cen)))

  (setq xlo (if meth (min 0.0 (- (car cen) (* 0.5 b2))) 0.0)
        xhi (if meth (max bov (+ (car cen) (* 0.5 b2))) bov)
        ylo (if meth (min 0.0 (- (cadr cen) (* 0.5 a2))) 0.0)
        yhi (if meth (max aov (+ (cadr cen) (* 0.5 a2))) aov))

  (if meth
      (progn
        (spa:setmode (spa:othermode))
        (spa:perround cen2 b2 a2)
        (spa:setmode mode1)))

  ;; A true circle takes the single overall the order sheet's round panel
  ;; shows; only an out-of-round spa needs the second one.  A round spa's
  ;; overalls have to run through the centre, so the water's edge pair
  ;; sits on the centre lines rather than a third of the way in.
  (setq out1 (or (null meth) (= mode1 "Coversize")))
  (setvar "CLAYER" "DIMENSION")
  (spa:dimstylenow th)
  (if out1
      (progn
        (spa:dimov (list 0.0 (* 0.5 aov)) (list bov (* 0.5 aov))
                   (list (* 0.5 bov) (+ yhi spa:*topoff*)))
        (if (> (abs (- aov bov)) 1.0e-6)
            (spa:dimov (list (* 0.5 bov) 0.0) (list (* 0.5 bov) aov)
                       (list (- xlo spa:*dimoff*) (* 0.5 aov)))))
      (progn
        (spa:dimov (list 0.0 (* 0.5 aov)) (list bov (* 0.5 aov))
                   (list (* 0.5 bov) (* 0.5 aov)))
        (if (> (abs (- aov bov)) 1.0e-6)
            (spa:dimov (list (* 0.5 bov) 0.0) (list (* 0.5 bov) aov)
                       (list (* 0.5 bov) (* 0.5 aov))))))
  (if meth
      (progn
        (spa:setmode (spa:othermode))
        (spa:dimstylenow th)
        (setq bl (- (car cen) (* 0.5 b2)) br (+ (car cen) (* 0.5 b2))
              ab (- (cadr cen) (* 0.5 a2)) at (+ (cadr cen) (* 0.5 a2)))
        (if out1
            (progn
              (spa:dimov (list bl (cadr cen)) (list br (cadr cen))
                         (list (car cen) (cadr cen)))
              (if (> (abs (- a2 b2)) 1.0e-6)
                  (spa:dimov (list (car cen) ab) (list (car cen) at)
                             (list (car cen) (cadr cen)))))
            (progn
              (spa:dimov (list bl (cadr cen)) (list br (cadr cen))
                         (list (car cen) (+ yhi spa:*topoff*)))
              (if (> (abs (- a2 b2)) 1.0e-6)
                  (spa:dimov (list (car cen) ab) (list (car cen) at)
                             (list (- xlo spa:*dimoff*) (cadr cen))))))
        (spa:setmode mode1)
        ;; and how far the cover laps the water's edge, at the bottom
        (spa:dimstyle spa:*ds-cover* th 1.0)
        (spa:dimlap (car cen) ylo (max 0.0 ab))))
  (setvar "CLAYER" oldclay)

  (spa:modenote xlo (- ylo (* 1.4 spa:*dimoff*)) th)
  (setq rows (list (list "OVERALL ACROSS" bov bov)
                   (list "OVERALL UP" aov aov)))
  (if meth
      (progn
        (spa:setmode (spa:othermode))
        (setq rows (append rows (spa:otherrows b2 a2)))
        (spa:setmode mode1)))
  ;; -------------------------------------------------- hinges
  (setq hrows
    (cond ((= mode1 "Coversize")
           (spa:hingeflow (list "ROUND" cen bov aov) 0.0 bov th t))
          (meth
           (spa:hingeflow (list "ROUND" cen b2 a2)
                          (- (car cen) (* 0.5 b2)) (+ (car cen) (* 0.5 b2)) th t))
          (t
           (spa:hingeflow (list "ROUND" cen bov aov) 0.0 bov th nil))))
  (if hrows (setq rows (append rows hrows)))
  (spa:report rows spa:*valnotes* (+ xhi spa:*dimoff*) yhi th "SPA-NOTES")
  (princ "\nSpa layout complete -- see the report table.")
  (princ))

;;; -------------------- undo grouping ----------------------------------

;; Copes with drawings where undo is limited or off, and with an error
;; firing before the group was ever opened.
(defun spa:undobegin ()
  (if (= 1 (logand 1 (getvar "UNDOCTL")))
      (progn
        (command "_.UNDO" "_Begin")
        (setq spa:*undogrp* t))))

(defun spa:undoend ()
  (if spa:*undogrp* (command "_.UNDO" "_End"))
  (setq spa:*undogrp* nil))

;;; -------------------- sysvar save / restore --------------------------
;;; The snapshot of the user's settings lives in a GLOBAL and is taken
;;; only when no snapshot is already pending: if a previous run died
;;; before restoring, the stale snapshot still holds the user's TRUE
;;; settings.  Saving again at that point would capture the zeroed
;;; OSMODE and every later run would faithfully "restore" 0 -- the
;;; user's object snaps would look permanently wiped by the command.

(defun spa:sysvars ()
  (append '("OSMODE" "LUNITS" "CMDECHO" "CLAYER") spa:*dimvars*))

;;; -------------------- main command -----------------------------------

(defun c:SPA ( / *error* stype base)

  (defun *error* (msg)
    (if (and msg
             (not (wcmatch (strcase msg) "*BREAK*,*CANCEL*,*QUIT*,*EXIT*")))
        (princ (strcat "\nSPA error: " msg)))
    ;; user settings come back FIRST so nothing below can skip them
    (cal:sysrestore)
    (cal:dimstyrestore)
    ;; a stale form surviving a cancelled run would silently answer the
    ;; NEXT command-line SPA with last time's numbers -- cleared on
    ;; both exits, this one included
    (spa:fclear)
    (spa:pvkill)
    (spa:undoend)
    (if *pop-error-mode* (*pop-error-mode*))
    (princ))

  ;; AutoCAD 2012+ requires this so *error* may call (command);
  ;; harmless no-op guard on older releases where it doesn't exist
  (if *push-error-using-command* (*push-error-using-command*))

  (cal:syssave (spa:sysvars))
  (cal:dimstysave)
  (setq spa:*valnotes* nil
        spa:*turned* nil
        spa:*hingerows* nil
        spa:*advice* nil
        spa:*grade* nil
        spa:*taper* nil)
  (setvar "CMDECHO" 0)
  (spa:undobegin)
  ;; architectural units while prompting so every distance can be typed
  ;; as 6'10", 6'-10-1/2" or 6'10.5 as well as plain inches
  (setvar "LUNITS" 4)
  (princ "\nDistances may be typed as 6'10\", 6'-10-1/2\" or 82.5 (plain numbers = inches).")
  (princ "\nDimensions are written in standard inches and placed outside the shape.")

  ;; ------------------------------------------------ grade + taper first
  ;; The Spa Cover Details block is read UP FRONT because its grade can
  ;; settle the next question outright: a Thermo-Light cover's water's
  ;; edge and cover size are the same thing, so there is nothing to ask
  ;; and nothing to add later.  Skipping here just defers the block to
  ;; the hinge pass.
  (princ "\nThe Spa Cover Details block sets the grade and taper.")
  (spa:readblock)
  ;; the form's grade/taper land HERE, before the Thermo-Light branch,
  ;; so a form grade of THERMOLIGHT behaves exactly like the block's
  (spa:formdetails)
  (if (spa:thermop)
      (progn
        (spa:setmode "Coversize")
        (setq spa:*taper* "1-3/8")
        (princ "\nThermo-Light: the water's edge and the cover size are the same.")
        (spa:advise "THERMO-LIGHT: WATER'S EDGE = COVER SIZE, ONE OUTLINE"))
      (spa:setmode
        (spa:askkwf 'mode
                    "Is this drawing at the water's edge or the cover size"
                    "Watersedge Coversize" "Watersedge/Coversize" nil nil)))
  (princ (strcat "\n" spa:*modename* ": outline on layer " spa:*perlay*
                 (if spa:*perdash* " (dashed)" "")
                 "; overalls read <measurement> over \"" spa:*sfx* "\"."))

  ;; ------------------------------------------------ shape
  (setq stype (spa:fshape))

  ;; the base point is picked with the user's own snaps still live;
  ;; only afterwards do snaps drop for the command-fed drawing work
  (setq base (if (spa:fhas 'base)
                 (spa:ftake 'base)
                 (getpoint "\nInsertion base point <0,0>: "))
        spa:*base* (if base (list (car base) (cadr base)) (list 0.0 0.0)))
  (setvar "OSMODE" 0)

  ;; ------------------------------------------------ layers
  (spa:layer spa:*lay-water* 4)
  (spa:layer spa:*lay-cover* 6)
  (spa:layer "DIMENSION" 2)
  (spa:layer "SPA-NOTES" 3)
  (spa:layer "TEXT" 7)

  ;; dashed / dotted patterns up front so the guide draws them; the
  ;; patterns are defined in inches and scaled to cancel LTSCALE, so they
  ;; show the same in any drawing
  (setq spa:*dashlt* (spa:ltload "DASHED")
        spa:*dotlt*  (spa:ltload "DOT"))

  (cond
    ((= stype "OCtagon") (spa:octflow))
    ((= stype "ROUnd")   (spa:roundflow))
    (t                   (spa:rectflow)))

  ;; ------------------------------------------------ finish
  (command "_.ZOOM" "_Extents")
  (spa:undoend)
  (cal:sysrestore)
  (cal:dimstyrestore)
  (spa:fclear)
  (if *pop-error-mode* (*pop-error-mode*))
  (princ))


(defun c:SPAVER ()
  (princ (strcat "\nSPA " spa:*version*))
  (princ (strcat "\nTutorial: "
                 (if tut:*version* tut:*version* "not loaded")))
  (princ))

(princ (strcat "\nSPA " spa:*version*
               " loaded.  SPA to draw, SPAVER for the version"
               (if tut:*version* ", TUTORIALSPA to learn it" "")
               "."))
(princ)


;;; ======================================================================
;;; >>> TUTORIALSPA.lsp
;;; ======================================================================

;;; ====================================================================
;;;  TUTORIALSPA.LSP -- how SPA.LSP works, for someone meeting it new
;;;
;;;  Command:  TUTORIALSPA
;;;
;;; SHARED BUILD: requires CALOFIN-LIB.lsp (load via CALOFIN-LOADER.lsp).
;;; Generic helpers live there under cal: - see STANDARDS.md.
;;;
;;;    Checklist  every question it asks, every decision it makes for
;;;               you, and every check it runs -- written to the text
;;;               window, and optionally placed in the drawing as a
;;;               reference sheet you can plot.
;;;    Demo       draws a worked cover a step at a time, explaining each
;;;               step before it appears, so you see what SPA produces
;;;               and why.  Nothing is asked for: the measurements are
;;;               canned.
;;;    Both       the checklist, then the demo.
;;;
;;;  Requires SPA.LSP to be loaded first -- the demo drives the real
;;;  drawing functions (spa:drawrect, spa:dimov, the hinge solver ...),
;;;  so what it shows is what SPA actually does, not a mock-up.  Only
;;;  the ORDER of the steps is duplicated here; if the flow in SPA.LSP
;;;  changes, walk this file through with it.
;;;
;;;  This file ships twice under two names with IDENTICAL contents:
;;;      TUTORIALSPA.LSP                 the static name
;;;      TUTORIALSPA_MMDDYY_REV##.LSP    named for its revision
;;; ====================================================================

(setq tut:*version* "082726 REV07")

;;; -------------------- the worked example -----------------------------
;;;  140 x 110 cover, one diagonal corner, water's edge 3" inside it,
;;;  Standard 4-3.  Chosen because it exercises nearly everything:
;;;  mixed corners (so flats and a 90 Typ. mark appear), both outlines,
;;;  the overlap dimension, three pieces (so a fold hinge AND a velcro
;;;  hinge get drawn), and a hinge run long enough to call for a double
;;;  C channel.

(setq tut:*w*    140.0)
(setq tut:*l*    110.0)
(setq tut:*gap*    3.0)
(setq tut:*cut*   21.0)             ; the diagonal cut face at corner C
(setq tut:*fw*    48.0)             ; Standard 4-3 foam width
(setq tut:*fl*   144.0)             ; ... and its length

;;; -------------------- little helpers ---------------------------------

(defun tut:say (s) (princ (strcat "\n" s)) (princ))

(defun tut:head (s)
  (princ (strcat "\n\n=== " s " "))
  (princ (substr "=========================================================="
                 1 (max 3 (- 58 (strlen s)))))
  (princ))

(defun tut:pause ( / v)
  (setq v (getstring "\n      [Enter to carry on, X to stop] "))
  (if (or (= v "x") (= v "X")) 'TUT-STOP))

;; Zoom so the whole demo, dimensions and all, is on screen.
(defun tut:zoom ()
  (command "_.ZOOM" "_Window"
           (spa:wp (list -80.0 -80.0))
           (spa:wp (list (+ tut:*w* 200.0) (+ tut:*l* 70.0)))))

;; A step: explain, draw, show, wait.  tfn is a function of no arguments.
;;
;; AutoLISP is dynamically scoped, so a local of THIS function is visible
;; inside the callback -- a local named `l` here would shadow the demo's
;; cover length while the callback ran.  Hence the deliberately odd
;; names: nothing here may collide with a variable tut:demo uses.
(defun tut:step (ttitle tlines tfn / tln)
  (tut:head ttitle)
  (foreach tln tlines (tut:say (strcat "  " tln)))
  (apply tfn nil)
  (tut:zoom)
  (tut:pause))

;;; -------------------- the checklist ----------------------------------

(setq tut:*asks*
  (list
    "1.  The Spa Cover Details block -- picked FIRST, because its GRADE"
    "    decides what comes next.  Enter skips it; the hinge pass will"
    "    ask again.  GRADE and TAPER are read off the tags, and the"
    "    'Grade:' / 'Taper:' prefixes are stripped."
    "2.  Water's edge or cover size.  NOT asked on Thermo-Light -- the"
    "    two are the same thing there, so it draws the cover size."
    "3.  Shape: Rectangle, Octagon or Round."
    "4.  Insertion base point (Enter = 0,0).  Your own object snaps stay"
    "    live for this pick, and for every measurement prompt after it."
    "5.  The measurements, against a grey guide spa whose matching piece"
    "    turns RED while it is being asked for.  Back (B, or Undo/U)"
    "    re-asks the previous question, right across the input phase."
    "    A ROUND spa takes ONE measurement -- the diameter; type O at"
    "    it only if the spa measured out of round.  A RECTANGLE offers"
    "    the width back as the length, so Enter makes it square."
    "    Any measurement may be typed in MILLIMETRES with the unit on"
    "    the number -- 600mm, 1524 MM -- and is converted to inches."
    "6.  Rectangle corners, one at a time -- the Treatment question:"
    "    Square / Radius / Cut / NotGiven (the old words still work"
    "    typed in full: 90, ROUNDED, DIAG, NG)."
    "    Corner A's answer autofills B, C and D -- Enter accepts."
    "7.  Draw the other outline as well?  By Offset (give the lap) or by"
    "    Dims (give it as measured; the two are drawn concentric)."
    "    Skipped on Thermo-Light."
    "8.  Auto-hinge?  Then the spillaways, in a loop defaulting to No."))

(setq tut:*decides*
  (list
    "*   ORIENTATION.  The long overall always ends up running west to"
    "    east.  A taller-than-wide cover is turned a quarter turn, and"
    "    the corner treatments and their letters travel round with it,"
    "    so the corner you called B is still B in the report."
    "*   WHICH DIMS GO WHERE.  The cover's overalls go outside it -- 2 ft"
    "    above, 3 ft to the left.  When both outlines are drawn the"
    "    water's edge's go a third of the way INTO the water's edge."
    "    That follows from which outline it is, not which you drew first."
    "*   HOW MANY CORNER CALLOUTS.  Four identical corners get ONE, with"
    "    a Typ. suffix, at the bottom-right.  Mixed corners are called"
    "    out one by one, and the square ones share a single 90 mark."
    "    Four 90 corners get none at all."
    "*   WHICH FLATS TO DIMENSION.  Only the sides a cut corner actually"
    "    shortened, and only when the corners are not all identical."
    "*   WHICH FOAM SHEET.  A taper can carry more than one -- Standard"
    "    3-2 and 4-2 each come as 48 x 144/96 and as 49-1/2 x 102 -- and"
    "    one can work where the other will not.  Every sheet is solved"
    "    and scored before fewest pieces is even considered."
    "*   HOW MANY HINGES AND WHERE.  The fewest pieces that fit the foam"
    "    width, evenly spaced, nudged off the spillaway zones."
    "*   FOLD OR VELCRO, per the Hinge Arrangement Chart: the pieces"
    "    fold up in PAIRS from both ends -- a sewn fold hinge inside"
    "    each pair, velcro between bundles -- so 5 pieces read Hinge /"
    "    Velcro / Velcro / Hinge, and an odd count leaves one flat"
    "    piece at or beside the centre.  Thermo-Light: all velcro."))

(setq tut:*checks*
  (list
    "GEOMETRY"
    "  - a corner treatment too big for its own walls is re-asked, so"
    "    two treatments can never overlap and fold the perimeter"
    "  - the octagon's letters must close POSITIVE against the overalls"
    "    (S + T + S = B, S1 + V + S1 = A).  One that will not fit is"
    "    adjusted, its report row goes red, and a note says so"
    "  - a second outline that comes out at or below zero is skipped"
    "  - an octagon second outline that will not close is skipped"
    "  - an octagon whose eight sides come out equal within 1/8\" drops"
    "    its flat dimensions -- the overalls and the cut say it all"
    "  - a radius corner that came out flat gets no radius dimension"
    ""
    "HINGES"
    "  - a hinge longer than the foam length is still drawn, and the"
    "    report says by how much"
    "  - a piece count the taper does not allow is still drawn, flagged"
    "  - a hinge that ends up inside a spillaway zone is flagged"
    "  - spillaway zones that could not all be dodged are flagged"
    "  - a left/right wall spillaway cannot meet a north-south hinge, so"
    "    it is recorded but blocks nothing"
    "  - Thermo-Light has no published hinge length: a verify note"
    "  - a grade/taper not on the foam sheet falls back to 48 x 96"
    ""
    "HARDWARE (advisory, in cyan -- recommendations, not failures)"
    "  - velcro hinges, double C channel and hold down kit are each"
    "    recommended or not from the LONGEST hinge in the drawing:"
    "      Economy            all three upon request only"
    "      Standard & Deluxe  over 120 / over 108 / over 120"
    "      Ultra              over 108 / never    / over 96"
    "      Thermo-Light       always   / never    / never"
    ""
    "INPUT"
    "  - a block that is not named Spa Cover Details is read anyway,"
    "    with a warning; something that is not a block is refused"
    "  - a taper that is not on the foam sheet is re-asked"
    "  - every measurement prompt refuses zero and negative values"
    ""
    "THE DRAWING ITSELF"
    "  - your OSMODE, LUNITS, CMDECHO, CLAYER, the whole DIM set and the"
    "    current dimension style are put back on the way out -- including"
    "    after an Esc or an error mid-prompt"
    "  - the whole run is one UNDO group, so one U takes it all back"
    "  - a dimension style the drawing already defines is used exactly as"
    "    it stands; only a missing one is built"))

(setq tut:*draws*
  (list
    "COVER        the cover outline, solid -- ONE closed polyline, so"
    "             it picks in a click and encloses an area"
    "POOL         the water's edge outline, dashed -- likewise"
    "DIMENSION    every dimension, in standard inches (fractional to"
    "             1/8\" with the inch mark), always outside the shape"
    "TEXT         the Hinge / Velcro Hinge labels"
    "SPA-NOTES    corner letters, the mode note, the report table"
    ""
    "Freeze SPA-NOTES and what is left is the outline and its"
    "dimensions -- the drawing as the order sheet shows it."))

(defun tut:checklist ( / l)
  (tut:head "WHAT SPA ASKS YOU, IN ORDER")
  (foreach l tut:*asks* (tut:say l))
  (tut:head "WHAT SPA DECIDES FOR YOU")
  (foreach l tut:*decides* (tut:say l))
  (tut:head "WHAT SPA CHECKS")
  (foreach l tut:*checks* (tut:say l))
  (tut:head "WHAT SPA DRAWS, BY LAYER")
  (foreach l tut:*draws* (tut:say l))
  (princ "\n"))

;; The same checklist as a text sheet in the drawing, at a picked point.
(defun tut:sheet ( / p x y h l)
  (setq p (getpoint "\nPoint for the reference sheet <skip>: "))
  (if p
      (progn
        (spa:layer "SPA-NOTES" 3)
        (setq x (car p) y (cadr p) h 2.5)
        (spa:textc (list x y) (* 2.0 h)
                   (strcat "SPA " spa:*version* " -- REFERENCE") "SPA-NOTES" 7)
        (setq y (- y (* 4.0 h)))
        (foreach l (append (list "WHAT SPA ASKS YOU, IN ORDER") tut:*asks*
                           (list "" "WHAT SPA DECIDES FOR YOU") tut:*decides*
                           (list "" "WHAT SPA CHECKS") tut:*checks*
                           (list "" "WHAT SPA DRAWS, BY LAYER") tut:*draws*)
          (if (/= l "")
              (spa:text (list x y) h l "SPA-NOTES"))
          (setq y (- y (* 1.6 h))))
        (princ "\nReference sheet placed on SPA-NOTES."))))

;;; -------------------- the demo ---------------------------------------

(defun tut:demo ( / base w l cut gap corners quad cen doff th arcs
                    w2 l2 c2 org2 q2 ip2 sb2 desc n xs res nmin htys
                    k x ch rows stop)
  (setq base (getpoint "\nWhere shall the demo go <0,0>: ")
        spa:*base* (if base (list (car base) (cadr base)) (list 0.0 0.0)))
  (setvar "OSMODE" 0)

  ;; the same set-up the real command does
  (spa:layer "POOL" 4) (spa:layer "COVER" 6)
  (spa:layer "DIMENSION" 2) (spa:layer "SPA-NOTES" 3) (spa:layer "TEXT" 7)
  (setq spa:*dashlt* (spa:ltload "DASHED")
        spa:*dotlt*  (spa:ltload "DOT")
        spa:*valnotes* nil spa:*advice* nil spa:*turned* nil)
  (spa:setmode "Coversize")

  (setq w tut:*w* l tut:*l* cut tut:*cut* gap tut:*gap*
        corners (list (list "Square" 0.0) (list "Square" 0.0)
                      (list "Cut" cut) (list "Square" 0.0))
        quad (spa:quadat (list 0.0 0.0) w l)
        cen (list (* 0.5 w) (* 0.5 l))
        doff (max 6.0 (/ (max w l) 12.0))
        th (max 1.0 (/ (max w l) 40.0)))

  (tut:head "THE DEMO")
  (tut:say "  A 140 x 110 cover with one diagonal corner, a water's edge")
  (tut:say "  3\" inside it, and Standard 4-3 foam.  Nothing is asked for --")
  (tut:say "  the measurements are canned so you can watch the drawing")
  (tut:say "  build up.  Each step explains itself before it appears.")
  (if (eq (tut:pause) 'TUT-STOP)
      (setq stop t))

  (if (not stop)
      (setq stop
        (eq 'TUT-STOP
          (tut:step "STEP 1 -- THE COVER OUTLINE"
            (list "Corners A and B (bottom) and D (top-left) are Square."
                  "Corner C (top-right) is a Cut with a 21\" cut FACE."
                  ""
                  "The overalls are always measured to the TRUE, sharp"
                  "corner; the treatment then cuts inward from there.  So"
                  "the cover is 140 x 110 even though the cut takes a"
                  "bite out of the top-right.")
            '(lambda () (setq arcs (spa:drawrect quad corners)))))))

  (if (not stop)
      (setq stop
        (eq 'TUT-STOP
          (tut:step "STEP 2 -- THE OVERALLS"
            (list "Across the TOP, 2 ft above.  Up the LEFT, 3 ft to the"
                  "left.  Each reads the measurement with the note"
                  "stacked under it, across the dimension line:"
                  ""
                  "                    140\""
                  "              |--------------|"
                  "                 Cover Size"
                  ""
                  "Only the overalls carry that note.")
            '(lambda ()
               (setvar "CLAYER" "DIMENSION")
               (spa:dimstylenow th)
               (spa:dimov (nth 3 quad) (nth 2 quad)
                          (list (* 0.5 w) (+ l spa:*topoff*)))
               (spa:dimov (nth 0 quad) (nth 3 quad)
                          (list (- 0.0 spa:*dimoff*) (* 0.5 l))))))))

  (if (not stop)
      (setq stop
        (eq 'TUT-STOP
          (tut:step "STEP 3 -- THE FLATS"
            (list "The cut at corner C shortened the TOP and the RIGHT, so"
                  "each gets its remaining straight run dimensioned,"
                  "inboard of the overalls.  The bottom and left were not"
                  "shortened, so they get nothing."
                  ""
                  "Had all four corners matched, there would be no flats"
                  "at all -- the overalls and one Typ. callout would be"
                  "the whole drawing.")
            '(lambda ()
               (spa:dimalg (spa:cornerpoint quad corners 1 'next)
                           (spa:cornerpoint quad corners 2 'prev)
                           (spa:outoff (nth 1 quad) (nth 2 quad) cen
                                       spa:*flatoff*) nil)
               (spa:dimalg (spa:cornerpoint quad corners 2 'next)
                           (spa:cornerpoint quad corners 3 'prev)
                           (spa:outoff (nth 2 quad) (nth 3 quad) cen
                                       spa:*flatoff*) nil))))))

  (if (not stop)
      (setq stop
        (eq 'TUT-STOP
          (tut:step "STEP 4 -- THE CORNER CALLOUTS"
            (list "The cut face is dimensioned across itself, outside the"
                  "corner on its 45-degree line.  The three square corners"
                  "share ONE mark -- a circled corner point with a 90"
                  "leader, Typ. because there is more than one."
                  ""
                  "A radius corner would get R12\" instead, read from"
                  "outside the arc.  Corner callouts never carry the"
                  "Cover Size note -- they are corners, not overalls.")
            '(lambda () (spa:dimcorners quad corners arcs cen doff))))))

  (if (not stop)
      (setq stop
        (eq 'TUT-STOP
          (tut:step "STEP 5 -- THE WATER'S EDGE"
            (list "Offset 3\" INWARD, because the cover is always the"
                  "larger of the two.  This is a true parallel offset, so"
                  "the corner moves with it: the 21\" cut face shrinks by"
                  "3 x (2*root2 - 2) = 2.49\", to 18.51\"."
                  ""
                  "Dashed, on the POOL layer.  Its own overalls go a third"
                  "of the way INTO it, hooked to points on the dimension"
                  "line so the arrows land on the outline.")
            '(lambda ()
               (setq w2 (- w (* 2.0 gap))
                     l2 (- l (* 2.0 gap))
                     c2 (spa:offcorners corners (- gap))
                     org2 (spa:orgfor cen w2 l2)
                     q2 (spa:quadat org2 w2 l2)
                     sb2 (spa:maxsetback c2)
                     ip2 (spa:insidepts (car org2) (+ (car org2) w2)
                                        (cadr org2) (+ (cadr org2) l2)
                                        sb2 sb2))
               (spa:setmode "Watersedge")
               (spa:drawrect q2 c2)
               (setvar "CLAYER" "DIMENSION")
               (spa:dimstylenow th)
               (spa:dimoveralls nil (nth 0 ip2) (nth 1 ip2)
                                (nth 2 ip2) (nth 3 ip2) 0.0 l)
               (spa:setmode "Coversize"))))))

  (if (not stop)
      (setq stop
        (eq 'TUT-STOP
          (tut:step "STEP 6 -- THE OVERLAP"
            (list "How far the cover laps the water's edge, at the bottom."
                  "The lap itself is far too small to hold its text, so"
                  "the note is parked under the cover with a leader.")
            '(lambda ()
               (spa:dimstyle spa:*ds-cover* th 1.0)
               (spa:dimlap (* 0.5 w) 0.0 (cadr org2)))))))

  (if (not stop)
      (setq stop
        (eq 'TUT-STOP
          (tut:step "STEP 7 -- THE HINGES"
            (list "Standard 4-3 foam: 48\" wide, 144\" long, 2 to 4 pieces."
                  ""
                  "140\" / 48\" needs 3 pieces, so 2 hinges, evenly spaced."
                  "Fold vs velcro follows the Hinge Arrangement Chart:"
                  "pieces fold up in PAIRS from both ends, a dashed fold"
                  "Hinge inside each pair, Velcro Hinge between bundles."
                  "3 pieces = one pair + one flat piece: Hinge, Velcro."
                  "(5 pieces would read Hinge/Velcro/Velcro/Hinge.)"
                  ""
                  "Each hinge runs the full 110\", well inside the 144\""
                  "foam length.  Had a spillaway been declared, the even"
                  "stations would have been nudged off it.")
            '(lambda ()
               (setvar "CLAYER" "DIMENSION")
               (setq desc (list "RECT" quad corners)
                     nmin (max 2 (spa:ceilv (/ w tut:*fw*)))
                     res (spa:hsolve 0.0 w tut:*fw* nil nmin)
                     n (car res) xs (cadr res)
                     htys (spa:hingetypes n nil) k 0)
               (foreach x xs
                 (setq ch (spa:chordat desc x))
                 (if ch
                     (progn
                       (if (= (nth k htys) "H")
                           (spa:line (list x (car ch)) (list x (cadr ch))
                                     "COVER" (spa:hdash))
                           (spa:line (list x (car ch)) (list x (cadr ch))
                                     "COVER" nil))
                       (spa:htext x (* 0.5 (+ (car ch) (cadr ch)))
                                  (if (= (nth k htys) "H")
                                      "Hinge" "Velcro Hinge"))))
                 (setq k (1+ k))))))))

  (if (not stop)
      (tut:step "STEP 8 -- THE REPORT"
        (list "Target / actual / delta for everything that was measured,"
              "off to the right.  Problems print under it in RED --"
              "adjusted octagon letters, a hinge over the foam length, a"
              "piece count the taper does not allow."
              ""
              "Recommendations print in CYAN.  This 110\" hinge is over"
              "108\", so Standard & Deluxe calls for a double C channel."
              ""
              "The whole run is one UNDO group: a single U clears it.")
        '(lambda ()
           (spa:advise "DOUBLE C CHANNEL: YES - hinge 110.0 over 108")
           (spa:advise "VELCRO HINGES: no - hinge 110.0 not over 120")
           (spa:advise "HOLD DOWN KIT: no - hinge 110.0 not over 120")
           (spa:modenote 0.0 (- 0.0 (* 1.4 spa:*dimoff*)) th)
           (setq rows (list (list "OVERALL ACROSS (A-B)" w w)
                            (list "OVERALL UP (A-D)" l l)
                            (list "CORNER C DIAGONAL" cut cut)
                            (list "WATER'S EDGE ACROSS" w2 w2)
                            (list "WATER'S EDGE UP" l2 l2)
                            (list "PIECES (STD 4-3)" nil (float n))
                            (list "FOAM WIDTH MAX" tut:*fw* (/ w n))
                            (list "FOAM LENGTH MAX" tut:*fl* l)))
           (spa:report rows nil (+ w spa:*dimoff*) l th "SPA-NOTES"))))

  (tut:head "THAT IS THE WHOLE THING")
  (tut:say "  Type SPA to do it for real.  The grey guide will show you")
  (tut:say "  which measurement is being asked for, and Back at any")
  (tut:say "  prompt re-asks the previous one.")
  (princ "\n"))

;;; -------------------- the command ------------------------------------

(defun c:TUTORIALSPA ( / *error* what)

  (defun *error* (msg)
    (if (and msg
             (not (wcmatch (strcase msg) "*BREAK*,*CANCEL*,*QUIT*,*EXIT*")))
        (princ (strcat "\nTUTORIALSPA error: " msg)))
    (spa:sysrestore)
    (spa:undoend)
    (if *pop-error-mode* (*pop-error-mode*))
    (princ))

  (if (null spa:*version*)
      (progn
        (princ "\nLoad SPA.LSP first -- the tutorial drives its own drawing")
        (princ "\nfunctions, so it cannot run without it.")
        (princ))
      (progn
        (if *push-error-using-command* (*push-error-using-command*))
        (princ (strcat "\nSPA " spa:*version* " -- tutorial " tut:*version*))
        ;; the tutorial selector of STANDARDS section 3; the old
        ;; Checklist stays accepted typed in full, hidden
        (initget "Checks Demo Both CHECKLIST")
        (setq what (getkword "\nShow me [Checks/Demo/Both] <Both>: "))
        (if (= what "CHECKLIST") (setq what "Checks"))
        (if (null what) (setq what "Both"))
        (spa:syssave)
        (setvar "CMDECHO" 0)
        (spa:undobegin)
        (setvar "LUNITS" 4)
        (if (member what '("Checks" "Both"))
            (progn (tut:checklist) (tut:sheet)))
        (if (member what '("Demo" "Both"))
            (tut:demo))
        (spa:undoend)
        (spa:sysrestore)
        (if *pop-error-mode* (*pop-error-mode*))
        (princ))))

(princ (strcat "\nTUTORIALSPA " tut:*version*
               " loaded.  Type TUTORIALSPA to walk through SPA."))
(princ)


;;; ======================================================================
;;; >>> OASIS.lsp
;;; ======================================================================

;;; ======================================================================
;;; OASIS.lsp  --  continuous-tangent pool inside a given X/Y envelope
;;; ----------------------------------------------------------------------
;;; For AutoCAD 2018 and later (plain AutoLISP, no external libraries).
;;;
;;; Commands:  OASIS       draw a continuous-tangent pool
;;;            OASISVER    print the loaded version
;;; ======================================================================
;;;
;;; SHARED BUILD: requires CALOFIN-LIB.lsp (load via CALOFIN-LOADER.lsp).
;;; Generic helpers live there under cal: - see STANDARDS.md.
;;;
;;; The shape
;;; ---------
;;; An oasis pool is arcs and nothing else: no corners, and at most one
;;; straight run.  It is a ring of BULGES -- circles pinned to the
;;; envelope -- with a JOINER between each consecutive pair, and a joiner
;;; is either a smaller reverse arc curving back IN, or, when both bulges
;;; are tangent to the same bound, the straight run of that bound between
;;; them.  Every joint is smooth: the outline changes direction without
;;; ever changing tangent, which is why the whole thing can be given as a
;;; handful of radii and two overall dimensions.
;;;
;;; Four families come out of that, and the first question is which:
;;;
;;;   Center    three bulges -- left, right and one across the top,
;;;             centred -- joined by three reverse arcs.
;;;   TopRight  the same, with the third bulge tucked into the top-right
;;;             corner instead.
;;;   Cloud     two bulges, joined over the top by a reverse arc.
;;;   Kidney    three bulges and ONE reverse arc: the two side circles
;;;             sit INSIDE the big top circle, touching it from within,
;;;             and the outline hands straight over at each touch --
;;;             a SEAM, the one joint with nothing drawn between.
;;;
;;; The two families that come two ways get a second question of their
;;; own, asked straight after.  A cloud is one shape with two bottoms:
;;; Straight, the flat run of the Y-min bound between the two bulges, or
;;; Rounded, a reverse arc like any other joiner.  A kidney is one shape
;;; whose sides are either matched or not: on a TRUE kidney the top
;;; radius is given and the two equal sides are DERIVED from having to
;;; touch it; on an ASYMMETRIC one the two unequal sides are given and
;;; the top circle is derived -- tangent to the top bound and both
;;; sides, its centre landing wherever those three contacts put it.
;;; The pair of answers together names one of six rings.
;;;
;;;                        top bulge
;;;                      ___________                  ___________
;;;          top-left  ,'           `.  top-right   ,'           `.
;;;          tangent  /               \  tangent    /               \
;;;                  |                 |          |                 |
;;;      left bulge  |                 |  right   |         .        |
;;;                   \      ___      /                     \___,'
;;;                    `.__,'   `.__,'             `._____________,'
;;;                     bottom-center                straight bottom
;;;
;;; Nothing downstream of the solver knows which shape it is looking at.
;;; It reads the ring.
;;;
;;; Where the circles sit
;;; ---------------------
;;; The X and Y the user gives are ABSOLUTE bounds -- the pool touches
;;; all four of them and crosses none.  That pins the three bulges with
;;; no further input:
;;;
;;;   left bulge    the two OASIS shapes: the X-min and Y-min bounds
;;;                                                     -> centre (rL, rL)
;;;                 the two CLOUD shapes: the X-min, Y-min AND Y-max
;;;                 bounds all at once, which pins the radius itself at
;;;                 half the Y bound and takes it out of the questions
;;;                                                     -> centre (Y/2, Y/2)
;;;   right bulge   touches the X-max and Y-min bounds  -> centre (X-rR, rR)
;;;   top bulge     CENTER    touches the Y-max bound, centred across X
;;;                                                     -> centre (X/2, Y-rT)
;;;                 TOPRIGHT  touches the Y-max AND the X-max bound
;;;                                                     -> centre (X-rT, Y-rT)
;;;                 the cloud shapes have no third bulge.
;;;
;;; So on an oasis the box's bottom edge is held by the two side bulges
;;; (each dips to it), the left edge by the left bulge, the top edge by
;;; the top bulge -- and the right edge by the right bulge alone on a
;;; centre-bulge pool, or by the right bulge AND the corner bulge, with
;;; a reverse curve between them, on a top-right one.  On a cloud the
;;; left bulge alone holds three of the four bounds, and the right bulge
;;; the fourth.  On a centre-bulge
;;; pool the top bulge has one degree of freedom left and it is spent
;;; centring it: oasis:*topfrac* moves it along X if a job ever needs it
;;; off-centre.  The corner bulge has none -- two tangencies pin it.
;;;
;;; Each tangent radius is then the circle of that radius sitting
;;; externally tangent to both of its neighbouring bulges -- two such
;;; circles exist, one either side of the line joining the two bulge
;;; centres, and the one OUTSIDE the pool is the one wanted.  Listing
;;; the bulges counter-clockwise (left, right, top) makes that choice
;;; mechanical: a counter-clockwise ring keeps its inside on the left,
;;; so outside is always the right-hand solution.  The pool then reads
;;; counter-clockwise as
;;;
;;;   left -> bottom-center -> right -> top-right -> top -> top-left ->
;;;
;;; and every arc's two ends are the tangent points it shares with its
;;; neighbours: a bulge runs from the neighbour before it to the one
;;; after, a reverse tangent arc runs the other way round its own
;;; circle.  Nothing is trimmed and nothing is fitted -- the six arcs
;;; are computed closed and drawn closed.
;;;
;;; What it draws
;;; -------------
;;; Where it goes is picked first, and then the pool is drawn AS IT IS
;;; ANSWERED.  Before every question the preview is redrawn, with three
;;; things overlapping on purpose: the outline solid on the POOL layer,
;;; the circle each arc is cut from dashed on POOL-GUIDE behind it, and a
;;; label on every circle -- its radius once given, "?" until then.  The
;;; circle the question is about goes red, arc, circle and label
;;; together, so there is never a doubt which radius is wanted.  A radius
;;; not yet answered still needs a value for any of that to be drawable,
;;; so the preview fills the gaps with the proportions an oasis usually
;;; comes in -- a side bulge three quarters of the way across the short
;;; bound, the top bulge half way across the long one -- and marks every
;;; one it invented with its "?".  On a 40 x 20 that starts the run at
;;; 7'-6" side bulges and a 10'-0" top, against the 8'/9' and 11' of the
;;; drawing this tool was written from: near enough that the first
;;; question is already looking at a familiar shape.
;;;
;;; When the last answer is in, the preview is erased and the real thing
;;; goes down:
;;;
;;;   * the six arcs on the POOL layer;
;;;   * the overall X and Y and a radius on each of the six arcs -- eight
;;;     dimensions, on the DIMENSION layer, in the drawing's ordinary
;;;     dimension style.  This is not asked about; a pool is always
;;;     dimensioned;
;;;   * a CHECK DRAWING clear to the right, dimensioned the way a layout
;;;     is checked rather than the way it is built: every circle centre
;;;     tied back to the two envelope corners nearest it, and every pair
;;;     of neighbouring centres tied to each other, and every pair of
;;;     neighbouring BULGES tied across whatever sits between them.
;;;     Between them those pin every centre against the box and against
;;;     one another, so a transcription slip in any single radius shows
;;;     up as a dimension that does not agree with the order sheet.  The
;;;     ring ties have a second use: neighbouring circles are externally
;;;     tangent by construction, so each of those must read exactly the
;;;     two radii added together.  The bulge ties are the lobe-to-lobe
;;;     measurements a pool is actually read by, and the ring ties never
;;;     cross a reverse arc to give them.
;;;
;;; The check drawing's eighteen are drawn in the CROSS DIMENSIONS
;;; style, since that is what they are; the pool's own eight are left in
;;; the drawing's ordinary style, because the pool is a plan and reads
;;; like one.  A drawing that has not got one of those styles is told so
;;; once and those dims come out in whatever style is current -- an
;;; invented style would look right and measure wrong.  The envelope box
;;; is construction: dashed on the check drawing where the corners are
;;; being measured to, and not drawn at all on the pool itself.
;;;
;;; Which frame it is drawn in
;;; -------------------------
;;; The pool is laid out in the CURRENT UCS, so it follows the way the
;;; user is working and the dimensions read the X and Y that were typed.
;;; An ARC entity is the one thing that cannot follow: its centre is
;;; stored in WORLD coordinates and its angles are measured from the
;;; world X axis, so oasis:draw carries both across.  A UCS tilted out of
;;; the world plan is refused outright -- the arcs would each need an
;;; extrusion of their own, and a plan pool has no business in one.
;;;
;;; What it refuses
;;; ---------------
;;; Three things make the shape impossible rather than merely ugly, and
;;; each is caught at the question that causes it rather than after all
;;; eight answers are in:
;;;
;;;   * a bulge that does not fit the envelope.  A side bulge is tangent
;;;     to the bottom edge AND to its own side, so it is twice its
;;;     radius both ways: more than half the Y bound and it pushes out
;;;     through the top, more than half the X bound and it pushes out
;;;     through the far side.  The TOP RIGHT corner bulge is checked the
;;;     same way, for the same reason; the CENTER one is not, because it
;;;     is trimmed away long before it reaches anything;
;;;   * one bulge circle wholly inside another: no tangent radius of any
;;;     size can bridge them, because raising it grows both reaches
;;;     equally;
;;;   * a tangent radius too small to span the gap between its two
;;;     bulges -- the routine says the smallest one that will.
;;;
;;; Anything that is merely unusual is drawn and reported, not refused.
;;; Two things are measured on the finished outline and named if they are
;;; wrong: whether it stays inside the envelope, and whether it runs
;;; through itself -- radii wildly out of proportion can send one arc
;;; clean through another even though all six exist and close.  Both
;;; reports name the ARC at fault rather than guess at the radius behind
;;; it, and both are drawn anyway, so the problem is on the screen where
;;; it can be seen and one U takes it away.
;;; ======================================================================

(setq *oasis-version* "v8.0")   ; announced on load; release_lisp.py
                                ; reads this banner and stamps the
                                ; dated twin in releases/ from it

;;; -------------------- tunables ----------------------------------------

(setq oasis:*poollayer*  "POOL")       ; the six arcs
(setq oasis:*poolcolor*  4)
(setq oasis:*dimlayer*   "DIMENSION")  ; every dimension
(setq oasis:*dimcolor*   2)
(setq oasis:*guidelayer* "POOL-GUIDE") ; the dashed circles, box and labels
(setq oasis:*guidecolor* 8)
(setq oasis:*hicolor*    1)            ; red: the part being asked about

;; Where a Center pool's top bulge sits across the X bound, as a fraction
;; of it.  0.5 centres it, which is what every one on file wants; the
;; value is here so an off-centre one does not need the file edited.
(setq oasis:*topfrac* 0.5)

;; The pool bottom.  The offset the hopper question offers first, the
;; number of chords a guided slope line is drawn with, and how finely the
;; deepest point of the offset ring is looked for.
(setq oasis:*hopoff*   18.0)
(setq oasis:*hopchord* 24)
(setq oasis:*hopscan*  720)

;; Slack for "is this the same point / the same length" tests, drawing
;; units.  Measurements arrive in inches, so this is far below anything
;; a tape can tell apart.
(setq oasis:*fuzz* 1.0e-6)

;; Two styles, because the two drawings are read differently: the pool
;; itself is a plan and is dimensioned in the drawing's ordinary style,
;; while the check drawing beside it is nothing but tie measurements and
;; goes in the cross-dimension style, same as every other cross dim in
;; the repo.  A drawing that has not got one of them is told so once and
;; those dims come out in whatever style is current -- an invented style
;; would look right and measure wrong.
(setq oasis:*dimstyle*   "Standard")           ; the pool's own dims
(setq oasis:*crossstyle* "CROSS DIMENSIONS")   ; the check drawing's

;; The check drawing sits this far to the right of the pool, measured
;; from the pool's own right-hand bound, as a multiple of the dimension
;; stand-off.  Big enough to clear the radius dims on that side.
(setq oasis:*checkgap* 4.0)

;; The shape the preview starts from, before any radius has been given:
;; how far across the envelope a side bulge and the top bulge usually
;; reach, as fractions.  Three quarters of the short bound and half the
;; long one is what an oasis normally comes in, so the first question is
;; already looking at something familiar.
(setq oasis:*startside* 0.75)
(setq oasis:*starttop*  0.5)

;;; -------------------- the four shapes ----------------------------------
;;; Every one of them is a ring of BULGES -- circles pinned to the
;;; envelope -- with a JOINER between each consecutive pair.  A joiner is
;;; either a reverse arc of a radius the user gives, or, when both bulges
;;; are tangent to the same bound, the straight run of that bound between
;;; them.  Nothing downstream of the solver knows which shape it is
;;; looking at: it reads the ring.
;;;
;;; Three bulges -- left, right, top -- and three reverse arcs:
;;;
;;;   Center     the top bulge sits across the top, centred.
;;;   TopRight   it is tucked into the top-right corner instead, tangent
;;;              to the Y-max AND the X-max bound.
;;;
;;; Two bulges -- left and right -- with the top joined by a reverse arc
;;; and the bottom either way.  The left bulge is tangent to the X-min,
;;; Y-min AND Y-max bounds all at once, which pins it at half the Y bound
;;; and takes it out of the questions altogether:
;;;
;;;   StraightBottom  the bottom is the flat run of the Y-min bound
;;;                   between the two bulges.
;;;   RoundedBottom   the bottom is a reverse arc like any other joiner.

;; T for the two-bulge shapes.
(defun oasis:cloud-p (variant)
  (member variant '("StraightBottom" "RoundedBottom")))

;; T for the kidney shapes.
(defun oasis:kidney-p (variant)
  (member variant '("TrueKidney" "AsymKidney")))

;; T for the NXT cloud -- three lobes and four fillets, and the one
;; shape whose ring meets a bulge twice.
(defun oasis:nxt-p (variant)
  (= variant "NXTcloud"))

;; T when the run is a COMPLEX one.  Complex is not a shape: it is a
;; second question asked straight after the shape, and what it changes is
;; how much of the outline the user is allowed to say.  A simple run is
;; the shape as it has always been -- bulges pinned to the envelope,
;; reverse arcs between them.  A complex one adds two things a real
;; drawing sometimes has and the simple flow cannot express:
;;
;;   * any joiner may be answered LINE instead of a radius, and comes out
;;     as the straight run between the two bulges' tangent points --
;;     exactly the reverse arc with an infinite radius, so the outline
;;     stays tangent-continuous through it;
;;   * a Center pool's top bulge may be moved off centre by a signed
;;     offset, left negative.
;;
;; Neither changes the ring downstream: a straight joiner is the "LINE"
;; element the cloud's flat bottom already uses, and an offset hump is
;; the same bulge at a different X.
(defun oasis:complex-p (ans)
  (= (nth 11 ans) "Complex"))

;; The shape, resolved.  The first question offers four families --
;; Center, TopRight, Cloud and Kidney -- and the two families that come
;; two ways get a second question of their own, asked straight after: a
;; cloud is one shape with two bottoms, a kidney one shape whose sides
;; are either matched or not.  The pair of answers together names one of
;; the six rings.
(defun oasis:variant (ans)
  (cond ((= (nth 0 ans) "Cloud")
         (if (= (nth 10 ans) "Rounded") "RoundedBottom" "StraightBottom"))
        ((= (nth 0 ans) "Kidney")
         (if (= (nth 10 ans) "Asymmetric") "AsymKidney" "TrueKidney"))
        ((nth 0 ans))))

;; The left bulge's radius.  On a cloud shape three bounds pin it at once
;; -- left, bottom and top -- so it is half the Y bound and is never
;; asked for; on an oasis it is whatever was typed.
(defun oasis:leftrad (variant h rl)
  (if (oasis:cloud-p variant) (if h (* 0.5 h)) rl))

;; Where the third bulge sits, on the shapes that have one.  off is the
;; complex run's signed shift of a Center pool's hump along X -- negative
;; to the left, nil or zero for the centred one every simple run draws.
;; A corner bulge has no such freedom: two bounds already hold it.
(defun oasis:topcen (w h rt variant off)
  (if (= variant "TopRight")
      (list (- w rt) (- h rt))
      (list (+ (* w oasis:*topfrac*) (cond (off) (0.0))) (- h rt))))

;; Where a NXT cloud's three lobes sit.  All three are pinned by the
;; envelope alone, with nothing left to ask but their radii: the TOP-LEFT
;; one into the corner where the X-min and Y-max walls meet, the CENTRE
;; one on the Y-min wall halfway across, and the RIGHT one on the X-max
;; wall halfway up.
(defun oasis:nxtcen (w h r which)
  (cond ((= which 0) (list r (- h r)))
        ((= which 1) (list (* 0.5 w) r))
        (t           (list (- w r) (* 0.5 h)))))

;; What the ring's elements are called, in the order they run round the
;; pool: bulges at the even positions, joiners at the odd ones.  A seam
;; -- the direct handover where a kidney's side circle touches the top
;; circle from inside -- is a joiner with nothing to draw, so its name
;; never reaches the drawing.
(defun oasis:names (variant)
  (cond ((oasis:cloud-p variant)
         '("left" "bottom" "right" "top"))
        ((oasis:kidney-p variant)
         '("left" "bottom-center" "right" "right-seam" "top-center"
           "left-seam"))
        ;; eight, because the ring meets the centre lobe twice -- once
        ;; under it on the way out to the right, once over it on the way
        ;; back
        ((oasis:nxt-p variant)
         '("top-left" "left-bottom" "center-bottom" "right-bottom"
           "right" "right-top" "center-top" "left-top"))
        ((= variant "TopRight")
         '("left" "bottom-center" "right" "right-side" "top-right"
           "top-left"))
        (t
         '("left" "bottom-center" "right" "top-right" "top" "top-left"))))

;; What the question for one answer slot is called.  The wording follows
;; the shape, because "top-right" is the joiner on one and the bulge
;; itself on another.
(defun oasis:sprompt (variant slot)
  (cond
    ((oasis:cloud-p variant)
      (cond ((= slot 6) "Right bulge radius")
            ((= slot 7) "Top tangent radius")
            ((= slot 9) "Bottom radius")))
    ((oasis:nxt-p variant)
      (cond ((= slot 4)  "Top-left lobe radius")
            ((= slot 5)  "Center lobe radius")
            ((= slot 6)  "Right lobe radius")
            ((= slot 9)  "Left-bottom tangent radius")
            ((= slot 13) "Right-bottom tangent radius")
            ((= slot 8)  "Right-top tangent radius")
            ((= slot 7)  "Left-top tangent radius")))
    ((oasis:kidney-p variant)
      (cond ((= slot 4) "Left bulge radius")
            ((= slot 5) "Top-center radius")
            ((= slot 6) "Right bulge radius")
            ((= slot 9) "Bottom-center tangent radius")))
    (t
      (cond ((= slot 4) "Left bulge radius")
            ((= slot 5) (if (= variant "TopRight")
                            "Top-right bulge radius" "Top bulge radius"))
            ((= slot 6) "Right bulge radius")
            ((= slot 7) "Top-left tangent radius")
            ((= slot 8) (if (= variant "TopRight")
                            "Right-side tangent radius"
                            "Top-right tangent radius"))
            ((= slot 9) "Bottom-center tangent radius")
            ((= slot 12) "Top bulge off center, left negative")))))

;; Which answer slots this shape asks for, in the order it asks them.
;; The rest are either pinned by the envelope (a cloud's left bulge) or
;; are no part of the shape at all.
;;
;; The head is the same for every run: the shape, the sub-type on the two
;; families that have one, then simple-or-complex.  Complex adds one
;; question and only to the Center shape -- how far its hump is off
;; centre; the straight runs it also allows are not questions of their
;; own but answers to the joiner questions already being asked.
(defun oasis:steps (ans / fam out)
  (setq fam (nth 0 ans)
        out (cond ((= fam "Cloud")
                   (if (= (nth 10 ans) "Rounded") '(1 2 3 6 7 9)
                       '(1 2 3 6 7)))
                  ((= fam "Kidney")
                   (if (= (nth 10 ans) "Asymmetric") '(1 2 3 4 6 9)
                       '(1 2 3 5 9)))
                  ;; the three lobes, then the four fillets in the order
                  ;; the outline meets them
                  ((= fam "NXTcloud") '(1 2 3 4 5 6 9 13 8 7))
                  ((and (= fam "Center") (oasis:complex-p ans))
                   '(1 2 3 4 5 12 6 7 8 9))
                  (t '(1 2 3 4 5 6 7 8 9))))
  (append (if (member fam '("Cloud" "Kidney")) '(0 10 11) '(0 11)) out))

;; How the shape is named on the command line and in the report.
(defun oasis:vlabel (variant)
  (cond ((= variant "TopRight")       "top-right-bulge")
        ((= variant "StraightBottom") "straight-bottom cloud")
        ((= variant "RoundedBottom")  "rounded-bottom cloud")
        ((= variant "NXTcloud")       "NXT cloud")
        ((= variant "TrueKidney")     "true kidney")
        ((= variant "AsymKidney")     "asymmetric kidney")
        (t                            "center-bulge")))

;; T when the shape's third bulge has to fit the envelope the way a side
;; bulge does.  The corner one is tangent to two bounds, so it is twice
;; its radius both ways and can break out of either; the centred one is
;; trimmed away long before it reaches anything.
(defun oasis:topfits-p (variant) (= variant "TopRight"))

;;; -------------------- ask layer ---------------------------------------
;;; Copies of the CALOFIN-LIB helpers under this file's own prefix, so
;;; the standalone build loads alone (STANDARDS.md section 4).  The Back
;;; sentinel is the symbol OASIS-BACK.

;;; -------------------- snaps and the dimension style --------------------

;; Make the cross-dimension style current for the dims about to be drawn.
;; A missing style is NOT invented: the dims come out in whatever style is
;; current and the routine says so once, so a drawing started from the
;; wrong template is obvious instead of quietly producing wrong-looking
;; dims.  (The CDCREATE rule, CDCREATE.lsp:80.)
(defun oasis:dimstyle-on (name)
  (cond ((tblsearch "DIMSTYLE" name)
         (command "_.-DIMSTYLE" "_Restore" name)
         T)
        (t
         (princ (strcat "\nOASIS: this drawing has no \"" name
                        "\" dimension style -- those dims drawn in \""
                        (getvar "DIMSTYLE")
                        "\" instead.  Create the style (or start from the"
                        " standard template) and re-run."))
         nil)))

;;; -------------------- linetypes ----------------------------------------

;; Build a linetype from an explicit pattern (positive = dash length,
;; negative = gap), in drawing units.  Done with entmake rather than
;; loading acad.lin: a failed load falls back to CONTINUOUS silently,
;; which is how dashes vanish.  (From pool:ltmake, POOL.LSP:251.)
(defun oasis:ltmake (name descr pat / lst x)
  (if (not (tblsearch "LTYPE" name))
      (progn
        (setq lst (list '(0 . "LTYPE")
                        '(100 . "AcDbSymbolTableRecord")
                        '(100 . "AcDbLinetypeTableRecord")
                        (cons 2 name)
                        '(70 . 0)
                        (cons 3 descr)
                        '(72 . 65)
                        (cons 73 (length pat))
                        (cons 40 (apply '+ (mapcar 'abs pat)))))
        (foreach x pat
          (setq lst (append lst (list (cons 49 x) '(74 . 0)))))
        (entmake lst)))
  (if (tblsearch "LTYPE" name) name "CONTINUOUS"))

;; Per-entity linetype scale that cancels the drawing's LTSCALE, so a
;; pattern defined in drawing units always plots at that size however the
;; host drawing is set up.  (From pool:ltsc, POOL.LSP:271.)
(defun oasis:ltsc ( / s)
  (setq s (getvar "LTSCALE"))
  (if (or (null s) (<= s 0.0)) 1.0 (/ 1.0 s)))

;; The dash pattern the guide circles are drawn with, scaled to the pool
;; so it reads the same on a 10-foot spa and a 40-foot pool.
(defun oasis:dashlt (w h / d)
  (setq d (max 2.0 (/ (max w h) 40.0)))
  (oasis:ltmake "OASISDASH" "Oasis guide __ __ __ __" (list d (- 0.0 d))))

;;; -------------------- layers ------------------------------------------

;;; -------------------- geometry ----------------------------------------

;; Intersection of circle (c1 r1) with circle (c2 r2).  side 1.0 is the
;; point left of the c1->c2 direction, -1.0 the one right of it.  nil
;; when the two circles never meet.
(defun oasis:circint (c1 r1 c2 r2 side / d ux uy a h2 h bx by)
  (setq d (distance c1 c2))
  (if (> d oasis:*fuzz*)
      (progn
        (setq ux (/ (- (car c2) (car c1)) d)
              uy (/ (- (cadr c2) (cadr c1)) d)
              a  (/ (+ (* d d) (* r1 r1) (- (* r2 r2))) (* 2.0 d))
              h2 (- (* r1 r1) (* a a)))
        (if (> h2 0.0)
            (progn
              (setq h  (sqrt h2)
                    bx (+ (car c1) (* a ux))
                    by (+ (cadr c1) (* a uy)))
              (list (+ bx (* side h (- uy)))
                    (+ by (* side h ux))))))))

;; 2-D vector sum and scale.
(defun oasis:v+ (a b) (list (+ (car a) (car b)) (+ (cadr a) (cadr b))))
(defun oasis:v* (v s) (list (* (car v) s) (* (cadr v) s)))

;; The unit normal along which two circles share an external tangent
;; line, on the RIGHT of c1->c2 -- the outside of a counter-clockwise
;; ring.  Both tangent points lie along it from their own centre, so a
;; straight run between two bulges is entirely described by it.  When
;; both bulges are tangent to the same bound it comes out perpendicular
;; to that bound, which is what makes a flat bottom flat.  nil when one
;; circle contains the other.
(defun oasis:extnorm (c1 r1 c2 r2 / d ux uy k q)
  (setq d (distance c1 c2))
  (if (> d oasis:*fuzz*)
      (progn
        (setq ux (/ (- (car c2) (car c1)) d)
              uy (/ (- (cadr c2) (cadr c1)) d)
              k  (/ (- r1 r2) d)
              q  (- 1.0 (* k k)))
        (if (> q 0.0)
            (progn
              (setq q (sqrt q))
              ;; k along c1->c2, the rest along the right-hand perpendicular
              (list (+ (* k ux) (* q uy))
                    (- (* k uy) (* q ux))))))))

;; Centre of the circle of radius rf externally tangent to both (c1 r1)
;; and (c2 r2) and lying on the RIGHT of c1->c2.  The bulges are named
;; counter-clockwise round the pool, and a counter-clockwise ring keeps
;; the water on its left, so the right-hand solution is the one outside
;; the pool -- the one whose near side becomes the reverse curve.
(defun oasis:fillet (c1 r1 c2 r2 rf)
  (oasis:circint c1 (+ r1 rf) c2 (+ r2 rf) -1.0))

;; The joiner between two consecutive bulges, as
;;   (kind data angle-out angle-in)
;; where kind is nil for a reverse arc -- data its centre -- or "LINE"
;; for a straight run, data the outward normal along it.  angle-out is
;; where the first bulge hands over, angle-in where the second picks up.
;; nil when the two cannot be joined at all.
;;
;; rf says which: a number is the reverse arc's radius, "SEAM" the
;; internal tangency a kidney hands over at, and a straight run is either
;; asked for by name -- "LINE", what a complex run answers a joiner
;; question with -- or implied by the shape, which is how a cloud's flat
;; bottom arrives with nothing given at all.  Both reach the same place:
;; the straight run IS the reverse arc with an infinite radius, so
;; nothing downstream has to tell the two apart.
(defun oasis:joiner (c1 r1 c2 r2 rf / cf m a)
  (cond
    ;; a SEAM: one circle inside the other, touching -- the internal
    ;; tangency of a kidney's side against its top circle.  The touch
    ;; point lies along the line of centres, so BOTH arcs meet it at the
    ;; same angle -- from the bigger centre towards the smaller -- and
    ;; the outline hands straight over with nothing drawn between.
    ((and (= (type rf) 'STR) (= rf "SEAM"))
     (setq a (if (> r1 r2) (angle c1 c2) (angle c2 c1)))
     (list "SEAM" nil a a))
    ((or (null rf) (and (= (type rf) 'STR) (= rf "LINE")))
     (setq m (oasis:extnorm c1 r1 c2 r2))
     (if m (progn (setq a (atan (cadr m) (car m)))
                  (list "LINE" m a a))))
    (t
     (setq cf (oasis:fillet c1 r1 c2 r2 rf))
     (if cf (list nil cf (angle c1 cf) (angle c2 cf))))))

;; T when a joiner is a seam.
(defun oasis:seam-p (j)
  (and (= (type (nth 0 j)) 'STR) (= (nth 0 j) "SEAM")))

;; T when a ring element is a straight run rather than an arc.
(defun oasis:line-p (a)
  (and (= (type (nth 5 a)) 'STR) (= (nth 5 a) "LINE")))

;; The smallest tangent radius that can still reach from one bulge to
;; the other.  Zero when the two bulges already overlap, since then any
;; radius reaches.
(defun oasis:filmin (c1 r1 c2 r2)
  (max 0.0 (/ (- (distance c1 c2) r1 r2) 2.0)))

;; T when one bulge circle lies wholly inside the other (or the two are
;; concentric).  No tangent radius can bridge that: raising it grows
;; both circles' reach by the same amount, so they stay nested for ever.
(defun oasis:nested-p (c1 r1 c2 r2)
  (<= (distance c1 c2) (+ (abs (- r1 r2)) oasis:*fuzz*)))

;;; -------------------- kidney geometry ---------------------------------
;;; A kidney is three bulges and ONE reverse arc.  The two side circles
;;; sit inside the big top circle, touching it from within -- an internal
;;; tangency, where the outline hands straight over from one arc to the
;;; other with nothing drawn between.  The bottom is the ordinary
;;; external fillet.  What is given and what is derived depends on which
;;; kidney it is:
;;;
;;;   TrueKidney   the TOP-CENTER radius is given; the two sides come out
;;;                equal, derived from having to touch it.  The top
;;;                circle is tangent to the Y-max bound, centred.
;;;   AsymKidney   the two SIDE radii are given, unequal; the top circle
;;;                is derived -- tangent to the Y-max bound and touching
;;;                both sides from outside them, its centre landing
;;;                wherever those three contacts put it.

;; The smallest top-center radius a true kidney can take: the circle
;; through the two bottom corners tangent to the top bound -- where the
;; matching sides shrink to nothing.
(defun oasis:ktrue-min (w h)
  (+ (/ h 2.0) (/ (* w w) (* 8.0 h))))

;; The matching side radius a true kidney derives from its top circle,
;; or nil.  The discriminant is exactly 4(2R-w)(2R-h), so any R past
;; oasis:ktrue-min has one.
(defun oasis:ktrue-side (w h rt / b c disc r)
  (setq b    (+ w (* 2.0 h) (* -4.0 rt))
        c    (+ (/ (* w w) 4.0) (* (- h rt) (- h rt)) (- (* rt rt)))
        disc (- (* b b) (* 4.0 c)))
  (if (>= disc 0.0)
      (progn
        (setq r (/ (+ b (sqrt disc)) 2.0))
        (if (> r oasis:*fuzz*) r))))

;; The asymmetric kidney's top circle: tangent to the Y-max bound and
;; internally tangent to both given sides.  Eliminating its radius from
;; the two tangency equations leaves a quadratic in its centre's X; a
;; root is legal when the circle contains both sides and the point where
;; it touches the top bound lies ON the arc between the two seams --
;; that arc is the drawn top, so the touch must be on it.  Of the legal
;; roots the one nearest the middle wins.  Returns (cx R) or nil.
(defun oasis:kidney-top (w h rl rr
                         / sl sr a1 a2 b1 b2 qa qb qc d sd roots cx rt
                           ty al ar sw best bin cin)
  (setq sl (float rl)
        sr (- w rr)
        a1 (- h (* 2.0 rl))
        a2 (- h (* 2.0 rr))
        b1 (+ (* sl sl) (* (- h rl) (- h rl)) (- (* rl rl)))
        b2 (+ (* sr sr) (* (- h rr) (- h rr)) (- (* rr rr)))
        qa (- a2 a1)
        qb (* -2.0 (- (* sl a2) (* sr a1)))
        qc (- (* a2 b1) (* a1 b2))
        roots nil)
  (if (< (abs qa) oasis:*fuzz*)
      (if (> (abs qb) oasis:*fuzz*)
          (setq roots (list (/ (- qc) qb))))
      (progn
        (setq d (- (* qb qb) (* 4.0 qa qc)))
        (if (>= d 0.0)
            (setq sd    (sqrt d)
                  roots (list (/ (+ (- qb) sd) (* 2.0 qa))
                              (/ (- (- qb) sd) (* 2.0 qa)))))))
  (setq best nil)
  (foreach cx roots
    (setq rt (cond ((> (abs a1) oasis:*fuzz*)
                    (/ (+ (* cx cx) (* -2.0 sl cx) b1) (* 2.0 a1)))
                   ((> (abs a2) oasis:*fuzz*)
                    (/ (+ (* cx cx) (* -2.0 sr cx) b2) (* 2.0 a2)))))
    (if (and rt (> rt (+ (max rl rr) oasis:*fuzz*)))
        (progn
          (setq ty (- h rt)
                al (angle (list cx ty) (list sl rl))
                ar (angle (list cx ty) (list sr rr))
                sw (cal:angnorm (- al ar)))
          (if (<= (cal:angnorm (- (/ pi 2.0) ar)) sw)
              (progn
                (setq cin (and (<= sl cx) (<= cx sr)))
                (if (or (null best)
                        (and cin (not (nth 2 best)))
                        (and (eq cin (nth 2 best))
                             (< (abs (- cx (/ w 2.0))) (abs (- (car best) (/ w 2.0))))))
                    (setq best (list cx rt cin))))))))
  (if best (list (car best) (cadr best))))

;; The outline, in the counter-clockwise order it runs round the pool.
;; Each element comes back as
;;
;;     (name centre radius start end kind slot)
;;
;; with the angles in RADIANS ready for an ARC entity's group 50 / 51.
;; kind is T for a bulge, nil for a reverse arc, and "LINE" for a
;; straight run -- on which centre and radius hold the run's two ends
;; instead, and start holds the direction out of the pool.  slot is the
;; answer the radius came from, or nil where the envelope pinned it.
;;
;; Bulges land at the even positions and joiners at the odd ones, for
;; every shape: six elements for the three-bulge oasis shapes, four for
;; the two-bulge clouds.  nil when a joiner does not exist -- c:OASIS
;; checks for that before it ever gets here, so a nil return means an
;; input slipped past the checks, not a user mistake.
(defun oasis:solve (w h rl rt rr ftl ftr fbc fbr off variant
                    / nm bc br bs jr js kt n i j js2 jj ok jp jn jl jm out)
  (setq nm (oasis:names variant) ok T)
  (cond
    ((oasis:cloud-p variant)
     (setq rl (oasis:leftrad variant h rl)
           bc (list (list rl rl) (list (- w rr) rr))
           br (list rl rr)
           bs (list nil 6)
           jr (list (if (= variant "StraightBottom") nil fbc) ftl)
           js (list 9 7)))
    ((oasis:kidney-p variant)
     ;; the sides or the top come DERIVED, whichever the shape did not
     ;; ask for -- and when the derivation has no answer there is no
     ;; kidney to build
     (if (= variant "TrueKidney")
         (setq rl (oasis:ktrue-side w h rt)
               rr rl
               kt (if rl (list (* 0.5 w) rt)))
         (setq kt (oasis:kidney-top w h rl rr)))
     (if (and rl rr kt)
         (setq bc (list (list rl rl) (list (- w rr) rr)
                        (list (car kt) (- h (cadr kt))))
               br (list rl rr (cadr kt))
               bs (if (= variant "TrueKidney")
                      (list nil nil 5)
                      (list 4 6 nil))
               jr (list fbc "SEAM" "SEAM")
               js (list 9 nil nil))
         (setq ok nil br '())))
    ;; the NXT cloud: three lobes, and the ring meets the centre one
    ;; TWICE -- it is listed twice, so the solver walks under it out to
    ;; the right lobe and back over it, and cuts two arcs from the one
    ;; circle without knowing that is what it is doing
    ((oasis:nxt-p variant)
     (setq bc (list (oasis:nxtcen w h rl 0) (oasis:nxtcen w h rt 1)
                    (oasis:nxtcen w h rr 2) (oasis:nxtcen w h rt 1))
           br (list rl rt rr rt)
           bs (list 4 5 6 5)
           jr (list fbc fbr ftr ftl)
           js (list 9 13 8 7)))
    (t
     (setq bc (list (list rl rl) (list (- w rr) rr)
                    (oasis:topcen w h rt variant off))
           br (list rl rr rt)
           bs (list 4 6 5)
           jr (list fbc ftr ftl)
           js (list 9 8 7))))
  (setq n (length br) i 0 js2 nil)
  (while (< i n)
    (setq j  (rem (1+ i) n)
          jj (oasis:joiner (nth i bc) (nth i br) (nth j bc) (nth j br)
                           (nth i jr)))
    (if jj (setq js2 (cons jj js2)) (setq ok nil))
    (setq i (1+ i)))
  (setq js2 (reverse js2))
  (if ok
      (progn
        (setq i 0 out nil)
        (while (< i n)
          (setq j  (rem (1+ i) n)
                jp (nth (rem (+ i n -1) n) js2)   ; the joiner before it
                jn (nth i js2)                    ; and the one after
                ;; the bulge: from where the joiner before it hands over
                ;; to where the joiner after it picks up.  Those two can
                ;; be the SAME point -- two straight runs either side of
                ;; a bulge that shares a tangent line with both its
                ;; neighbours touch it in one place -- and then the bulge
                ;; is a point on the outline, not an arc of it.  Nothing
                ;; is drawn for it: an ARC whose two angles are equal is
                ;; a full circle to AutoCAD, which is not what a pinched
                ;; bulge means.
                out (if (> (cal:angnorm (- (nth 2 jn) (nth 3 jp)))
                           oasis:*fuzz*)
                        (cons (list (nth (* 2 i) nm) (nth i bc) (nth i br)
                                    (nth 3 jp) (nth 2 jn) T (nth i bs))
                              out)
                        out)
                ;; then that joiner.  A seam draws nothing -- the two
                ;; arcs hand straight over at the touch point.  A reverse
                ;; arc curves the other way round its own circle, so its
                ;; two ends swap over.
                out (cond
                      ((oasis:seam-p jn) out)
                      ((and (= (type (nth 0 jn)) 'STR)
                            (= (nth 0 jn) "LINE"))
                       (setq jl (oasis:v+ (nth i bc)
                                          (oasis:v* (nth 1 jn) (nth i br)))
                             jm (oasis:v+ (nth j bc)
                                          (oasis:v* (nth 1 jn) (nth j br))))
                       ;; two bulges already tangent to each other leave
                       ;; no run between them, only the point they touch
                       (if (> (distance jl jm) oasis:*fuzz*)
                           (cons (list (nth (1+ (* 2 i)) nm) jl jm
                                       ;; a run the user asked for keeps
                                       ;; its answer slot, so backing up
                                       ;; to it still picks it out in red;
                                       ;; the one a cloud's flat bottom
                                       ;; implies was never asked and has
                                       ;; none
                                       (nth 2 jn) nil "LINE"
                                       (if (nth i jr) (nth i js)))
                                 out)
                           out))
                      ((> (cal:angnorm (- (angle (nth 1 jn) (nth i bc))
                                            (angle (nth 1 jn) (nth j bc))))
                          oasis:*fuzz*)
                       (cons (list (nth (1+ (* 2 i)) nm) (nth 1 jn)
                                   (nth i jr)
                                   (angle (nth 1 jn) (nth j bc))
                                   (angle (nth 1 jn) (nth i bc))
                                   nil (nth i js))
                             out))
                      (t out))
                i   (1+ i)))
        (reverse out))))

;; Note an overrun of AMOUNT past SIDE by arc NM, keeping the worst one
;; seen for that side.  Anything within the fuzz is not an overrun.
(defun oasis:worst (lst side amount nm / p out hit)
  (if (<= amount oasis:*fuzz*)
      lst
      (progn
        (setq out nil hit nil)
        (foreach p lst
          (if (= (car p) side)
              (setq hit T
                    out (cons (if (> amount (cadr p)) (list side amount nm) p)
                              out))
              (setq out (cons p out))))
        (if hit (reverse out) (cons (list side amount nm) lst)))))

;; How far the outline reaches past each bound of the envelope, and which
;; arc takes it there.  Every arc end and the compass point of every
;; quadrant a sweep crosses is tested -- between them they hold every
;; extreme the outline has -- so the report can name the arc that is out
;; instead of guessing at the radius behind it.  Returns a list of
;; (side amount arc-name), only for bounds that are really broken.
(defun oasis:overruns (arcs w h / over a c r s sw k ang p nm)
  (setq over nil)
  (foreach a arcs
    (setq nm (nth 0 a)
          c  (nth 1 a)
          r  (nth 2 a)
          s  (nth 3 a)
          sw (if (oasis:line-p a) 0.0 (cal:angnorm (- (nth 4 a) s)))
          k  -2)
    (while (< k (if (oasis:line-p a) 0 4))
      (setq ang (cond ((= k -2) s)
                      ((= k -1) (nth 4 a))
                      (t (* k (/ pi 2.0)))))
      (if (or (minusp k) (<= (cal:angnorm (- ang s)) sw))
          (setq p    (if (oasis:line-p a)
                         (nth (if (= k -2) 1 2) a)   ; its two ends
                         (polar c ang r))
                over (oasis:worst over "the left"   (- 0.0 (car p)) nm)
                over (oasis:worst over "the bottom" (- 0.0 (cadr p)) nm)
                over (oasis:worst over "the right"  (- (car p) w) nm)
                over (oasis:worst over "the top"    (- (cadr p) h) nm)))
      (setq k (1+ k))))
  over)

;; T when the angle ANG falls inside ARC's counter-clockwise sweep.
(defun oasis:on-arc-p (a ang)
  (<= (cal:angnorm (- ang (nth 3 a)))
      (cal:angnorm (- (nth 4 a) (nth 3 a)))))

;; Where a straight run meets a circle: the up-to-two points of (c r)
;; that lie ON the segment p->q, as a list.  The segment is walked as
;; p + t(q - p) and only 0 <= t <= 1 counts, so a circle the run points
;; at but never reaches gives back nothing.
(defun oasis:seg-circ (p q c r / dx dy fx fy qa qb qc d sd out t1)
  (setq dx (- (car q) (car p))   dy (- (cadr q) (cadr p))
        fx (- (car p) (car c))   fy (- (cadr p) (cadr c))
        qa (+ (* dx dx) (* dy dy))
        qb (* 2.0 (+ (* fx dx) (* fy dy)))
        qc (- (+ (* fx fx) (* fy fy)) (* r r))
        out nil)
  (if (> qa oasis:*fuzz*)
      (progn
        (setq d (- (* qb qb) (* 4.0 qa qc)))
        (if (> d 0.0)
            (progn
              (setq sd (sqrt d))
              (foreach t1 (list (/ (+ (- qb) sd) (* 2.0 qa))
                                (/ (- (- qb) sd) (* 2.0 qa)))
                (if (and (>= t1 0.0) (<= t1 1.0))
                    (setq out (cons (list (+ (car p) (* t1 dx))
                                          (+ (cadr p) (* t1 dy)))
                                    out))))))))
  out)

;; Where two straight runs meet, or nil.  Parallel runs never do, and a
;; meeting past either segment's ends is not one.
(defun oasis:seg-seg (p q r s / ax ay bx by den t1 u)
  (setq ax  (- (car q) (car p))  ay (- (cadr q) (cadr p))
        bx  (- (car s) (car r))  by (- (cadr s) (cadr r))
        den (- (* ax by) (* ay bx)))
  (if (> (abs den) oasis:*fuzz*)
      (progn
        (setq t1 (/ (- (* (- (car r) (car p)) by)
                       (* (- (cadr r) (cadr p)) bx))
                    den)
              u  (/ (- (* (- (car r) (car p)) ay)
                       (* (- (cadr r) (cadr p)) ax))
                    den))
        (if (and (>= t1 0.0) (<= t1 1.0) (>= u 0.0) (<= u 1.0))
            (list (+ (car p) (* t1 ax)) (+ (cadr p) (* t1 ay)))))))

;; T when two ring elements meet somewhere other than the end they share.
;; Exact rather than sampled, whichever pair of kinds it is: two circles
;; meet in at most two points and a crossing is one of them inside BOTH
;; sweeps; a run meets a circle in at most two, and only the ones on the
;; segment and inside the arc's sweep count; two runs meet at most once.
;; A simple shape's only straight run lies along a bound with both its
;; bulges tangent to it, so nothing can reach it -- but a complex one's
;; runs slant across the pool, and those can be crossed like any arc.
(defun oasis:meet-p (a b / hit p)
  (setq hit nil)
  (cond
    ((and (oasis:line-p a) (oasis:line-p b))
     (setq hit (and (oasis:seg-seg (nth 1 a) (nth 2 a)
                                   (nth 1 b) (nth 2 b))
                    T)))
    ((oasis:line-p a)
     (foreach p (oasis:seg-circ (nth 1 a) (nth 2 a) (nth 1 b) (nth 2 b))
       (if (oasis:on-arc-p b (angle (nth 1 b) p)) (setq hit T))))
    ((oasis:line-p b)
     (foreach p (oasis:seg-circ (nth 1 b) (nth 2 b) (nth 1 a) (nth 2 a))
       (if (oasis:on-arc-p a (angle (nth 1 a) p)) (setq hit T))))
    (t
     (foreach p (list (oasis:circint (nth 1 a) (nth 2 a)
                                     (nth 1 b) (nth 2 b) 1.0)
                      (oasis:circint (nth 1 a) (nth 2 a)
                                     (nth 1 b) (nth 2 b) -1.0))
       (if (and p
                (oasis:on-arc-p a (angle (nth 1 a) p))
                (oasis:on-arc-p b (angle (nth 1 b) p)))
           (setq hit T)))))
  hit)

;; The pairs of ring elements that are arcs of the SAME circle running
;; over each other.  Only a shape whose ring meets a bulge twice can have
;; any: a NXT cloud's centre lobe gives two arcs of one circle, and if
;; the four fillets round it hand over in the wrong order one of those
;; arcs sweeps most of the way round and swallows the other, so the
;; outline covers part of that circle twice instead of once.
;; oasis:crossings cannot see it -- two identical circles never intersect
;; each other, they coincide -- so it is looked for on its own.
(defun oasis:overlaps (arcs / n i j a b out)
  (setq n (length arcs) i 0 out nil)
  (while (< i n)
    (setq j (1+ i))
    (while (< j n)
      (setq a (nth i arcs)
            b (nth j arcs))
      (if (and (not (oasis:line-p a))
               (not (oasis:line-p b))
               (< (distance (nth 1 a) (nth 1 b)) oasis:*fuzz*)
               (< (abs (- (nth 2 a) (nth 2 b))) oasis:*fuzz*)
               (or (< (cal:angnorm (- (nth 3 b) (nth 3 a)))
                      (- (oasis:esweep a) oasis:*fuzz*))
                   (< (cal:angnorm (- (nth 3 a) (nth 3 b)))
                      (- (oasis:esweep b) oasis:*fuzz*))))
          (setq out (cons (list (nth 0 a) (nth 0 b)) out)))
      (setq j (1+ j)))
    (setq i (1+ i)))
  (reverse out))

;; The pairs of ring elements that run through each other.  Neighbours
;; are tangent by construction and touch only at the end they share, so
;; they are skipped; anything else that meets is the outline crossing
;; itself.
(defun oasis:crossings (arcs / n i j a b pair out)
  (setq n (length arcs) i 0 out nil)
  (while (< i n)
    (setq j (1+ i))
    (while (< j n)
      (if (not (or (= j (1+ i)) (and (= i 0) (= j (1- n)))))
        (progn
          (setq a    (nth i arcs)
                b    (nth j arcs)
                pair (list (nth 0 a) (nth 0 b)))
          (if (and (not (member pair out)) (oasis:meet-p a b))
              (setq out (cons pair out)))))
      (setq j (1+ j)))
    (setq i (1+ i)))
  (reverse out))

;;; -------------------- the drawing frame --------------------------------
;;; The pool is laid out in the CURRENT UCS, so it lines up with the way
;;; the user is working, and the dimension commands -- which read their
;;; points in the UCS -- need no conversion at all.  An ARC entity is the
;;; awkward one: its centre is stored in WORLD coordinates and its start
;;; and end angles are measured from the WORLD X axis, so both have to be
;;; carried across on the way into entmake.  Mixing the two frames is how
;;; a pool ends up detached from its own dimensions.
;;;
;;; A UCS tilted out of the world plan cannot be carried this way -- each
;;; arc would need an extrusion of its own -- so c:OASIS refuses to run
;;; in one rather than draw something wrong.

;; T when the current UCS lies flat in the world plan, i.e. its Z axis is
;; parallel to the world Z.  Every plan-drafting UCS is.
(defun oasis:ucs-flat-p ( / z)
  (setq z (trans '(0.0 0.0 1.0) 1 0 T))
  (< (abs (- (abs (caddr z)) 1.0)) 1.0e-8))

;; How far the current UCS is turned from the world X axis.  Read off the
;; components rather than with (angle ...), which projects onto the UCS
;; plane and would answer zero however far the UCS is turned.
(defun oasis:ucsang ( / x)
  (setq x (trans '(1.0 0.0 0.0) 1 0 T))
  (atan (cadr x) (car x)))

;;; -------------------- drawing -----------------------------------------

;; A point in pool coordinates moved to where the pool is being drawn.
;; The result is a point in the current UCS, at the base point's own
;; elevation -- which is what the dimension commands want; oasis:draw
;; converts it for entmake.
(defun oasis:wp (p base)
  (list (+ (car p) (car base))
        (+ (cadr p) (cadr base))
        (caddr base)))

;; The six arcs, drawn in the order they run round the pool.  Returns
;; their entity names in that same order, so the radius dimensions can
;; hook onto them afterwards.
(defun oasis:draw (arcs base lay / out a rot)
  (setq out nil
        rot (oasis:ucsang))       ; UCS -> world, for the angles
  (foreach a arcs
    (if (oasis:line-p a)
        (entmake (list '(0 . "LINE")
                       (cons 8 lay)
                       (cons 10 (trans (oasis:wp (nth 1 a) base) 1 0))
                       (cons 11 (trans (oasis:wp (nth 2 a) base) 1 0))))
        (entmake (list '(0 . "ARC")
                       (cons 8 lay)
                       (cons 10 (trans (oasis:wp (nth 1 a) base) 1 0))
                       (cons 40 (nth 2 a))
                       (cons 50 (cal:angnorm (+ (nth 3 a) rot)))
                       (cons 51 (cal:angnorm (+ (nth 4 a) rot))))))
    (setq out (cons (entlast) out)))
  (reverse out))

;; How far off the pool the dimensions sit.  POOL's rule, so an oasis
;; drawn beside a rectangle is dimensioned at the same stand-off.
(defun oasis:dimoff (w h)
  (max 12.0 (/ (max w h) 18.0)))

;; The midpoint of an arc, and the direction out of the pool there.
;; On a bulge that is away from the centre; on a reverse arc it is
;; towards it, because a reverse arc's centre is itself outside the
;; pool.  Either way the radius dimension is dragged clear of the water.
;; Returns (midpoint . outward-angle).
(defun oasis:arcmid (a / c r s w m)
  (if (oasis:line-p a)
      ;; halfway along it, and straight out of the pool across it
      (cons (list (* 0.5 (+ (car (nth 1 a)) (car (nth 2 a))))
                  (* 0.5 (+ (cadr (nth 1 a)) (cadr (nth 2 a)))))
            (nth 3 a))
      (progn
        (setq c (nth 1 a)
              r (nth 2 a)
              s (nth 3 a)
              w (cal:angnorm (- (nth 4 a) s))
              m (polar c (cal:angnorm (+ s (/ w 2.0))) r))
        (cons m (if (nth 5 a) (angle c m) (angle m c))))))

;; The point at which the OUTLINE reaches furthest towards one bound --
;; over the arcs AS DRAWN, not the circles they are cut from, because a
;; circle can dip well past a bound where its own arc never goes.  Every
;; arc end and the compass point of every quadrant the sweep crosses is
;; tested, the same roster oasis:overruns walks, so the answer is exact.
;; which is 0 for X-min, 1 for X-max, 2 for Y-min and 3 for Y-max.
(defun oasis:extreme (arcs which / best bd a c r s sw k ang p v)
  (setq best nil bd nil)
  (foreach a arcs
    (setq c  (nth 1 a)
          r  (nth 2 a)
          s  (nth 3 a)
          sw (if (oasis:line-p a) 0.0 (cal:angnorm (- (nth 4 a) s)))
          k  -2)
    (while (< k (if (oasis:line-p a) 0 4))
      (setq ang (cond ((= k -2) s)
                      ((= k -1) (nth 4 a))
                      (t (* k (/ pi 2.0)))))
      (if (or (minusp k) (<= (cal:angnorm (- ang s)) sw))
          (progn
            (setq p (if (oasis:line-p a)
                        (nth (if (= k -2) 1 2) a)
                        (polar c ang r))
                  v (cond ((= which 0) (car p))
                          ((= which 1) (- 0.0 (car p)))
                          ((= which 2) (cadr p))
                          (t           (- 0.0 (cadr p)))))
            (if (or (null bd) (< v bd)) (setq bd v best p))))
      (setq k (1+ k))))
  best)

;; Overall X, overall Y, and a radius on each of the six arcs.  The two
;; overall dimensions are hooked to the points that actually touch the
;; envelope -- the left and right bulges' outermost points for X, the
;; top bulge's highest point and the left bulge's lowest for Y -- so
;; they measure the bounds the user was asked for, not a chord of them.
(defun oasis:dimension (arcs ents base w h lay / doff i a e md)
  (setvar "CLAYER" lay)
  (oasis:dimstyle-on oasis:*dimstyle*)
  ;; the overall two hook the points at which the OUTLINE actually
  ;; touches each bound, whichever arc holds it.  Which one that is is
  ;; the shape's business, not a fixed position in the ring: an oasis
  ;; hangs the left and the bottom on the same bulge, a NXT cloud hangs
  ;; the left and the top on its top-left lobe and the bottom on its
  ;; centre one.
  (setq doff (oasis:dimoff w h))
  (command "_.DIMLINEAR"
           (oasis:wp (oasis:extreme arcs 0) base)
           (oasis:wp (oasis:extreme arcs 1) base)
           "_H"
           (oasis:wp (list (* 0.5 w) (+ h doff)) base))
  (command "_.DIMLINEAR"
           (oasis:wp (oasis:extreme arcs 3) base)
           (oasis:wp (oasis:extreme arcs 2) base)
           "_V"
           (oasis:wp (list (- 0.0 doff) (* 0.5 h)) base))
  ;; walked by index so each arc keeps the entity oasis:draw made for it
  (setq i 0)
  (while (< i (length arcs))
    (setq a  (nth i arcs)
          e  (nth i ents)
          md (oasis:arcmid a)
          i  (1+ i))
    (cond
      ((null e))
      ;; a straight run has no radius to call out; its LENGTH is the
      ;; measurement that matters, so it gets an aligned dim instead
      ((oasis:line-p a)
       (command "_.DIMALIGNED"
                (oasis:wp (nth 1 a) base) (oasis:wp (nth 2 a) base)
                (oasis:wp (polar (car md) (cdr md) (* 0.9 doff)) base)))
      (t
       (command "_.DIMRADIUS"
                (list e (oasis:wp (car md) base))
                (oasis:wp (polar (car md) (cdr md) (* 0.9 doff)) base)))))
  (princ))

;;; -------------------- the check drawing --------------------------------
;;; A second copy of the pool, off to the right, dimensioned the way a
;;; layout is checked rather than the way it is built: every circle
;;; centre tied back to the two envelope corners nearest it, and every
;;; pair of neighbouring centres tied to each other.  Between them those
;;; two families pin all six centres against the box and against one
;;; another, so a transcription slip in any single radius shows up as a
;;; dimension that does not agree with the order sheet.
;;;
;;; The centre-to-centre ties have a second use: neighbouring circles are
;;; externally tangent by construction, so each of those dimensions must
;;; read exactly the sum of the two radii.  Anything else means the
;;; outline is not tangent-continuous.

;; The two envelope corners nearest point P, nearest first.
(defun oasis:near2 (p w h / corners c best rest d bd rd)
  (setq corners (list (list 0.0 0.0) (list w 0.0)
                      (list w h) (list 0.0 h))
        best nil rest nil bd nil rd nil)
  (foreach c corners
    (setq d (distance p c))
    (cond ((or (null bd) (< d bd)) (setq rest best rd bd best c bd d))
          ((or (null rd) (< d rd)) (setq rest c rd d))))
  (list best rest))

;; T when P is already in LST, to the fuzz.
(defun oasis:member-pt (p lst / hit q)
  (setq hit nil)
  (foreach q lst (if (< (distance p q) oasis:*fuzz*) (setq hit T)))
  hit)

;; Add a tie between two centres unless it is already there.  A pair of
;; bulges that happen to be ring neighbours as well would otherwise be
;; dimensioned twice, one dim on top of the other.
(defun oasis:addtie (ties p q / e hit)
  ;; a circle the ring meets twice -- a NXT cloud's centre lobe -- would
  ;; otherwise be tied to itself, which is a dimension of nothing
  (setq hit (< (distance p q) oasis:*fuzz*))
  (foreach e ties
    (if (or (and (equal (car e) p 1e-8) (equal (cadr e) q 1e-8))
            (and (equal (car e) q 1e-8) (equal (cadr e) p 1e-8)))
        (setq hit T)))
  (if hit ties (append ties (list (list p q)))))

;; One cross dimension between two drawn points, its dimension line
;; sitting on the line it measures -- the look POOL and CDCREATE give a
;; tie measurement.
(defun oasis:crossdim (p q base)
  (command "_.DIMALIGNED"
           (oasis:wp p base) (oasis:wp q base)
           (oasis:wp (list (* 0.5 (+ (car p) (car q)))
                           (* 0.5 (+ (cadr p) (cadr q))))
                     base)))

;; The whole check drawing, placed at CBASE.  Returns nothing; the caller
;; has already put the layers and the dim style in place.
(defun oasis:checkdraw (arcs cbase w h lt
                        / mark cens bul uniq ties a e i n near)
  (oasis:dimstyle-on oasis:*crossstyle*)
  (setvar "CLAYER" oasis:*guidelayer*)
  (oasis:pv-box w h cbase lt)
  (setq mark (max 1.0 (/ (max w h) 90.0)))
  ;; the outline itself, so the centres have something to belong to
  (oasis:draw arcs cbase oasis:*poollayer*)
  (setvar "CLAYER" oasis:*guidelayer*)
  ;; every circle centre in ring order, and the BULGE centres again on
  ;; their own.  A straight run has no centre, so it drops out of both
  ;; and the ring closes over it.  A circle the ring meets TWICE is in
  ;; the ring order twice -- which is right for the ring ties, and wrong
  ;; for the marks and the corner ties, so those walk a deduped copy.
  (setq cens nil bul nil uniq nil)
  (foreach a arcs
    (if (not (oasis:line-p a))
        (progn
          (setq cens (cons (nth 1 a) cens))
          (if (nth 5 a) (setq bul (cons (nth 1 a) bul))))))
  (setq cens (reverse cens)
        bul  (reverse bul)
        n    (length cens)
        i    0)
  (foreach a cens
    (if (not (oasis:member-pt a uniq)) (setq uniq (cons a uniq))))
  (setq uniq (reverse uniq))
  (foreach a uniq (oasis:pv-circle a mark cbase "CONTINUOUS" nil))
  (setvar "CLAYER" oasis:*dimlayer*)
  ;; every centre back to the two corners nearest it
  (foreach a uniq
    (setq near (oasis:near2 a w h))
    (oasis:crossdim a (car near) cbase)
    (oasis:crossdim a (cadr near) cbase))
  ;; then the ties between centres: each circle to the next one round the
  ;; ring, AND each bulge to the next bulge.  The ring ties check the
  ;; tangency -- neighbours are externally tangent, so each of those must
  ;; read the two radii added together -- and the bulge ties check the
  ;; lobes against each other, across whatever sits between them.
  (setq ties nil i 0)
  (while (< i n)
    (setq ties (oasis:addtie ties (nth i cens) (nth (rem (1+ i) n) cens))
          i    (1+ i)))
  (setq i 0)
  (while (< i (length bul))
    (setq ties (oasis:addtie ties (nth i bul)
                             (nth (rem (1+ i) (length bul)) bul))
          i    (1+ i)))
  (foreach e ties (oasis:crossdim (car e) (cadr e) cbase))
  (+ (* 2 (length uniq)) (length ties)))

;; Where the check drawing goes: clear to the right of the pool and of
;; the radius dimensions on that side.
(defun oasis:checkbase (base w h)
  (list (+ (car base) w (* oasis:*checkgap* (oasis:dimoff w h)))
        (cadr base)
        (caddr base)))

;;; -------------------- the live preview ---------------------------------
;;; Every question redraws the pool as it stands, so the answer being
;;; typed can be seen landing.  Three things overlap on purpose:
;;;
;;;   * the OUTLINE, solid, on the pool layer -- what will actually be
;;;     drawn;
;;;   * each circle it is cut from, DASHED, on the guide layer -- the
;;;     construction behind the outline, so the radius being asked for
;;;     has something to belong to;
;;;   * a label on every circle: its radius once given, "?" until then.
;;;
;;; The circle the question is about -- its dashed circle, its arc and
;;; its label -- is drawn red, so there is never a doubt about which
;;; radius is being asked for.
;;;
;;; A radius that has not been answered yet still needs a value for any
;;; of this to be drawable, so the preview fills the gaps in with
;;; provisional ones (oasis:fillin) and marks every one it invented with
;;; a "?".  If a provisional set happens not to solve, the outline is
;;; simply left out and the circles and box still show.

;; The answers so far, with the gaps filled in well enough to draw.
;;
;; The provisionals are not arbitrary: they are the proportions an oasis
;; usually comes in, so the shape on screen at the first question is
;; already close to the one being measured rather than something the
;; draftsman has to look past.  A side bulge spans about three quarters
;; of the short bound and the top bulge about half the long one --
;; oasis:*startside* and oasis:*starttop* are those two fractions, and
;; they are HALVED here because a bulge is twice its radius across.  On a
;; 40 x 20 that is 7'-6" side bulges and a 10'-0" top, against the 8'/9'
;; and 11' of the drawing this tool was written from.
;;
;; A tangent radius has no such rule of thumb -- what looks right depends
;; entirely on the three bulges -- so it takes a quarter of the short
;; bound, lifted clear of its own minimum when that is larger.
;;
;; A joiner ANSWERED as a straight run needs no provisional at all: the
;; string "LINE" is an answer like any other and goes straight through.
;; The hump's offset starts at nothing, which is the shape every simple
;; run draws, so a complex run's first preview looks like the familiar
;; one until the offset is typed.
;;
;; Hands back (w h rl rt rr ftl ftr fbc off), ready for oasis:solve.
(defun oasis:fillin (ans / var w h rl rt rr cl ct cr gl gr side off g big
                         ca cd cg)
  (setq var  (oasis:variant ans)
        w    (nth 2 ans)
        h    (nth 3 ans)
        off  (cond ((nth 12 ans)) (0.0)))
  (if (oasis:nxt-p var)
      ;; three lobes sized like any other bulge, four fillets read off
      ;; the smallest of them and lifted clear of their own minimums
      (progn
        (setq side (* 0.5 oasis:*startside* (min w h))
              rl   (cond ((nth 4 ans)) (side))
              rt   (cond ((nth 5 ans)) (side))
              rr   (cond ((nth 6 ans)) (side))
              g    (* 0.6 (min rl rt rr))
              ca   (oasis:nxtcen w h rl 0)
              cd   (oasis:nxtcen w h rt 1)
              cg   (oasis:nxtcen w h rr 2))
        (list w h rl rt rr
              (cond ((nth 7 ans))  ((max g (* 1.25 (oasis:filmin cd rt
                                                                 ca rl)))))
              (cond ((nth 8 ans))  ((max g (* 1.25 (oasis:filmin cg rr
                                                                 cd rt)))))
              (cond ((nth 9 ans))  ((max g (* 1.25 (oasis:filmin ca rl
                                                                 cd rt)))))
              (cond ((nth 13 ans)) ((max g (* 1.25 (oasis:filmin cd rt
                                                                 cg rr)))))
              0.0))
  (if (oasis:kidney-p var)
      ;; the kidney: what was not asked for is derived by the solver, so
      ;; only the asked slots need filling -- the true one's top circle
      ;; half again over its minimum, the asymmetric one's sides a
      ;; kidney-ish fraction of the short bound, and the bottom off the
      ;; sides the way every joiner is
      (progn
        (setq rt (if (= var "TrueKidney")
                     (cond ((nth 5 ans)) ((* 1.5 (oasis:ktrue-min w h)))))
              rl (if (= var "AsymKidney")
                     (cond ((nth 4 ans)) ((* 0.40 (min w h)))))
              rr (if (= var "AsymKidney")
                     (cond ((nth 6 ans)) ((* 0.45 (min w h)))))
              g  (if (= var "TrueKidney")
                     (cond ((oasis:ktrue-side w h rt)) (48.0))
                     (min rl rr))
              ;; the two circles the bottom joiner will actually span --
              ;; the matching pair derived on a true kidney, the two given
              ;; sides on an asymmetric one
              cl (if (= var "TrueKidney") (list g g) (list rl rl))
              gl (if (= var "TrueKidney") g rl)
              cr (if (= var "TrueKidney") (list (- w g) g) (list (- w rr) rr))
              gr (if (= var "TrueKidney") g rr))
        (list w h rl rt rr nil nil
              ;; and lifted clear of its own minimum, like every other
              ;; joiner provisional -- below it there is no fillet, and
              ;; the preview would have nothing to draw until the very
              ;; last question was answered
              (cond ((nth 9 ans))
                    ((max (* 0.6 g)
                          (* 1.25 (oasis:filmin cl gl cr gr)))))
              nil off))
      (progn
  (setq side (* 0.5 oasis:*startside* (min w h))
        rl   (cond ((oasis:leftrad var h (nth 4 ans))) (side))
        rr   (cond ((nth 6 ans)) (side))
        ;; the centred bulge is measured across the long bound, the
        ;; corner one across the short -- it has to fit both ways
        rt   (if (oasis:cloud-p var)
                 nil
                 (cond ((nth 5 ans))
                       ((* 0.5 oasis:*starttop*
                           (if (oasis:topfits-p var) (min w h) w)))))
        ;; a joiner is read against the bulges either side of it, not
        ;; against the envelope, so size it off them -- that keeps the
        ;; bulges the bigger circles, which is the point of the picture.
        ;; A cloud's bottom is the exception: it sweeps under the whole
        ;; pool, so it is read off the biggest bulge rather than the
        ;; smallest.
        g    (* 0.6 (min rl rr (cond (rt) (rl))))
        big  (* 1.2 (max rl rr (cond (rt) (rl))))
        cl   (list rl rl)
        ct   (if rt (oasis:topcen w h rt var off))
        cr   (list (- w rr) rr))
  (list w h rl rt rr
        (cond ((nth 7 ans))
              ((oasis:cloud-p var) (max g (* 1.25 (oasis:filmin cr rr cl rl))))
              ((max g (* 1.25 (oasis:filmin ct rt cl rl)))))
        (cond ((nth 8 ans))
              ((oasis:cloud-p var) nil)
              ((max g (* 1.25 (oasis:filmin cr rr ct rt)))))
        (cond ((nth 9 ans))
              ((oasis:cloud-p var) (max big (* 1.25 (oasis:filmin cl rl cr rr))))
              ((max g (* 1.25 (oasis:filmin cl rl cr rr)))))
        nil off)))))

;; Erase a preview.  Entities the user has since deleted are skipped, so
;; a stray U in the middle of the questions cannot break the next redraw.
(defun oasis:pv-clear (ents / e)
  (foreach e ents (if (and e (entget e)) (entdel e)))
  nil)

;; One dashed guide entity, red when it is the one being asked about.
(defun oasis:pv-circle (c r base lt hi / lst)
  (setq lst (list '(0 . "CIRCLE")
                  (cons 8 oasis:*guidelayer*)
                  (cons 10 (trans (oasis:wp c base) 1 0))
                  (cons 40 r)))
  (if hi (setq lst (append lst (list (cons 62 oasis:*hicolor*)))))
  (if (/= lt "CONTINUOUS")
      (setq lst (append lst (list (cons 6 lt) (cons 48 (oasis:ltsc))))))
  (entmake lst)
  (entlast))

(defun oasis:pv-line (p q base lt / lst)
  (setq lst (list '(0 . "LINE")
                  (cons 8 oasis:*guidelayer*)
                  (cons 10 (trans (oasis:wp p base) 1 0))
                  (cons 11 (trans (oasis:wp q base) 1 0))))
  (if (/= lt "CONTINUOUS")
      (setq lst (append lst (list (cons 6 lt) (cons 48 (oasis:ltsc))))))
  (entmake lst)
  (entlast))

(defun oasis:pv-text (pt hgt str base hi / lst)
  (setq lst (list '(0 . "TEXT")
                  (cons 8 oasis:*guidelayer*)
                  (cons 10 (trans (oasis:wp pt base) 1 0))
                  (cons 11 (trans (oasis:wp pt base) 1 0))
                  (cons 40 hgt)
                  (cons 72 1)                 ; centred on the point
                  (cons 1 str)))
  (if hi (setq lst (append lst (list (cons 62 oasis:*hicolor*)))))
  (entmake lst)
  (entlast))

;; The envelope box, dashed -- the bounds the pool is being fitted to.
(defun oasis:pv-box (w h base lt / out)
  (setq out (list (oasis:pv-line (list 0.0 0.0) (list w 0.0) base lt)
                  (oasis:pv-line (list w 0.0) (list w h) base lt)
                  (oasis:pv-line (list w h) (list 0.0 h) base lt)
                  (oasis:pv-line (list 0.0 h) (list 0.0 0.0) base lt)))
  out)

;; Redraw the preview for the question about answer slot K, and hand back
;; the entities it made, ready to be passed to the next call so they can
;; be cleared first.  Nothing is drawn until the shape, the base point
;; and both bounds are known -- before that there is no envelope to draw
;; anything inside.
(defun oasis:preview (old ans k
                      / var base w h full arcs lt out ring n i a md txt
                        hgt slot hi)
  (oasis:pv-clear old)
  (setq var  (oasis:variant ans)
        base (nth 1 ans)
        w    (nth 2 ans)
        h    (nth 3 ans)
        out  nil)
  (if (and var base w h)
      (progn
        (cal:osdown)
        (setq lt   (oasis:dashlt w h)
              hgt  (/ (max w h) 28.0)
              full (oasis:fillin ans)
              arcs (oasis:solve (nth 0 full) (nth 1 full) (nth 2 full)
                                (nth 3 full) (nth 4 full) (nth 5 full)
                                (nth 6 full) (nth 7 full) (nth 8 full)
                                (nth 9 full) var)
              out  (oasis:pv-box w h base lt))
        (if arcs
            (progn
              ;; the outline, solid, and behind it the circle each arc is
              ;; cut from, dashed; the one being asked about goes red
              (setq ring (oasis:draw arcs base oasis:*poollayer*)
                    out  (append out ring)
                    n    (length arcs)
                    i    0)
              (while (< i n)
                (setq a    (nth i arcs)
                      slot (nth 6 a)
                      hi   (and slot (= slot k))
                      md   (oasis:arcmid a))
                (if hi (oasis:recolor (nth i ring) oasis:*hicolor*))
                ;; a straight run has no circle behind it and no radius
                ;; to label -- the envelope box already shows its bound
                (if (not (oasis:line-p a))
                    (setq out (cons (oasis:pv-circle (nth 1 a) (nth 2 a)
                                                     base lt hi)
                                    out)
                          txt (if (and slot (nth slot ans))
                                  (rtos (nth slot ans))
                                  (if slot "?" (rtos (nth 2 a))))
                          out (cons (oasis:pv-text
                                      (polar (car md) (cdr md) (* 1.7 hgt))
                                      hgt txt base hi)
                                    out)))
                (setq i (1+ i)))))
        (cal:osup)))
  out)

;; Force an entity's colour, for the one arc a question is about.
(defun oasis:recolor (e col / ed)
  (if (and e (setq ed (entget e)))
      (entmod (if (assoc 62 ed)
                  (subst (cons 62 col) (assoc 62 ed) ed)
                  (append ed (list (cons 62 col)))))))

;;; -------------------- the questions -----------------------------------

;; lst with slot k replaced by v.  The answer list keeps its length, so
;; a Back and a re-answer overwrite in place instead of growing it.
(defun oasis:put (lst k v / i out e)
  (setq i 0 out nil)
  (foreach e lst
    (setq out (cons (if (= i k) v e) out)
          i   (1+ i)))
  (reverse out))

;; Where the pool goes.  Picked with the user's own object snaps still
;; live, and backed out of like any other question -- nothing has been
;; drawn at that point.  Enter takes the origin.  Returns a 3-D point
;; (the elevation is carried, so a UCS with one is honoured) or
;; OASIS-BACK.
(defun oasis:askbase (back / v)
  (if back (initget "Back Undo"))
  (setq v (getpoint (strcat "\nInsertion base point <0,0>"
                            (if back " [Back]" "") ": ")))
  (cond ((and (= (type v) 'STR) (member v '("Back" "Undo"))) 'CAL-BACK)
        ((null v) (list 0.0 0.0 0.0))
        (t (list (car v) (cadr v) (if (caddr v) (caddr v) 0.0)))))

;; A side bulge's radius, re-asked until it fits inside the Y bound.
;; A bulge is tangent to the bottom edge, so its top sits at twice its
;; radius: any more than half the Y bound and it breaks out of the top.
(defun oasis:ask-bulge (msg side w h / v)
  (setq v (cal:askdist 'REQ msg nil T))
  (while (and (not (eq v 'CAL-BACK))
              (or (> (* 2.0 v) (+ h oasis:*fuzz*))
                  (> (* 2.0 v) (+ w oasis:*fuzz*))))
    (if (> (* 2.0 v) (+ h oasis:*fuzz*))
        (princ (strcat "\nA " (rtos v) " " side " bulge stands "
                       (rtos (* 2.0 v)) " tall and breaks out through the"
                       " top of a " (rtos h) " envelope.  "
                       (rtos (/ h 2.0)) " or less."))
        (princ (strcat "\nA " (rtos v) " " side " bulge is "
                       (rtos (* 2.0 v)) " across and breaks out through the"
                       " far side of a " (rtos w) " envelope.  "
                       (rtos (/ w 2.0)) " or less.")))
    (setq v (cal:askdist 'REQ msg nil T)))
  v)

;; The top bulge's radius, re-asked while it swallows a side bulge (or
;; is swallowed by one).  Nesting cannot be cured with a tangent radius
;; later, so it has to be caught here.
(defun oasis:ask-top (msg w h rl variant off / v cl ct big)
  (setq cl (list rl rl)
        v  (cal:askdist 'REQ msg nil T))
  (while (and (not (eq v 'CAL-BACK))
              (progn
                (setq ct  (oasis:topcen w h v variant off)
                      big (and (oasis:topfits-p variant)
                               (> (* 2.0 v) (+ (min w h) oasis:*fuzz*))))
                (or big (oasis:nested-p ct v cl rl))))
    (if big
        ;; only the corner bulge can do this: it is tangent to two
        ;; bounds, so it is twice its radius both ways
        (princ (strcat "\nA " (rtos v) " corner bulge is " (rtos (* 2.0 v))
                       " both ways and breaks out of a " (rtos w) " x "
                       (rtos h) " envelope.  " (rtos (/ (min w h) 2.0))
                       " or less."))
        (princ (strcat "\nA " (rtos v) " top bulge and the left bulge lie one"
                       " inside the other, so no tangent radius can join them"
                       " -- raising one raises the other's reach by just as"
                       " much.  Try a top radius nearer the left bulge's "
                       (rtos rl) ".")))
    (setq v (cal:askdist 'REQ msg nil T)))
  v)

;; The Y bound.  It is asked the same way for every shape but one: a
;; TRUE kidney is the one the envelope's own proportions can rule out,
;; because its two matching sides are not given but derived.  Whatever
;; top radius they are derived from, they come out less than Y across
;; together and grow towards exactly that as the top circle grows -- so
;; they fit inside X only while Y is less than X, and on a Y that is not,
;; no top radius rescues the shape.  That is why it is caught here,
;; where the user can still change the number that caused it, rather
;; than at a radius question that would refuse every answer.
(defun oasis:ask-ybound (msg w var / v)
  (setq v (cal:askdist 'REQ msg nil T))
  (while (and (not (eq v 'CAL-BACK))
              (= var "TrueKidney")
              (> (+ v oasis:*fuzz*) w))
    (princ (strcat "\nA true kidney " (rtos v) " deep in a " (rtos w)
                   " envelope closes on itself -- its two matching"
                   " sides always meet"))
    (princ (strcat "\nbefore they reach the sides of the box.  Y has to"
                   " be less than X here; an asymmetric kidney takes any"
                   " envelope."))
    (setq v (cal:askdist 'REQ msg nil T)))
  v)

;; A true kidney's top-center radius, re-asked until a kidney can be
;; built on it.  Below a minimum the top circle cannot reach both sides
;; -- at the minimum it passes through the two bottom corners and the
;; matching sides shrink to nothing.  There is no maximum to check
;; against: the derived sides never span more than Y together, and
;; oasis:ask-ybound has already turned away any Y that is not less
;; than X.
(defun oasis:ask-ktop (msg w h / v r)
  (setq v (cal:askdist 'REQ msg nil T))
  (while (and (not (eq v 'CAL-BACK))
              (null (setq r (if (> v (+ (oasis:ktrue-min w h) oasis:*fuzz*))
                                (oasis:ktrue-side w h v)))))
    (princ (strcat "\nA " (rtos v) " top circle cannot reach both"
                   " sides of a " (rtos w) " x " (rtos h)
                   " envelope -- it has to be more than "
                   (rtos (oasis:ktrue-min w h)) "."))
    (setq v (cal:askdist 'REQ msg nil T)))
  v)

;; A joiner answer on a COMPLEX run: a radius as usual, or the keyword
;; Line for the straight run between the two bulges' tangent points.
;; Returns the number, the string "LINE", or OASIS-BACK.  Its own
;; getdist rather than cal:askdist because that one folds every
;; keyword but Back into nil, which is the answer a cloud's implied flat
;; bottom already means.
(defun oasis:askrun (msg / v)
  (initget 7 "Line Back Undo")
  (setq v (getdist (strcat "\n" msg " [Line/Back]: ")))
  (cond ((and (= (type v) 'STR) (member v '("Back" "Undo"))) 'CAL-BACK)
        ((= (type v) 'STR) "LINE")
        (t v)))

;; A signed distance, defaulting to none: zero and negative are both
;; ordinary answers here, where every other measurement in the file
;; refuses them.  Returns the number or OASIS-BACK.
(defun oasis:askoff (msg / v)
  (initget 0 "Back Undo")
  (setq v (getdist (strcat "\n" msg " [Back] <0>: ")))
  (cond ((and (= (type v) 'STR) (member v '("Back" "Undo"))) 'CAL-BACK)
        ((null v) 0.0)
        (t v)))

;; A tangent radius, re-asked until it is big enough to span its two
;; bulges.  Below the minimum the two circles it would have to touch
;; never meet, and there is no such arc at any position.  runs is T on a
;; complex pool, where Line is an answer too -- and the only thing that
;; can rule THAT out is one bulge lying inside the other, since a
;; straight run has no radius to be too small.
(defun oasis:ask-tangent (msg c1 r1 c2 r2 runs / v mn bad)
  (setq mn (oasis:filmin c1 r1 c2 r2)
        v  (if runs (oasis:askrun msg) (cal:askdist 'REQ msg nil T)))
  (while (and (not (eq v 'CAL-BACK))
              (setq bad
                    (if (= (type v) 'STR)
                        (if (null (oasis:extnorm c1 r1 c2 r2)) "nested")
                        (if (<= v (+ mn oasis:*fuzz*)) "short"))))
    (if (= bad "short")
        (princ (strcat "\n" (rtos v) " is too short to reach from one bulge"
                       " to the other -- it has to be more than "
                       (rtos mn) "."))
        (princ (strcat "\nOne of those two bulges lies inside the other,"
                       " so there is no straight run between them.")))
    (setq v (if runs (oasis:askrun msg) (cal:askdist 'REQ msg nil T))))
  v)

;; How far a complex Center pool's hump is off centre, re-asked while it
;; would put the hump somewhere there is no pool.  Two ways it can: past
;; either end of the envelope, where the "top" bulge is no longer over
;; the water at all, or so far across that it swallows the left bulge --
;; a nesting no tangent radius can bridge, exactly as oasis:ask-top
;; refuses on the centred one.  Reaching past a bound is NOT refused:
;; that is an ordinary trimmed hump, and oasis:report-extents names it.
(defun oasis:ask-offset (msg w h rl rt / v ct bad)
  (setq v (oasis:askoff msg))
  (while (and (not (eq v 'CAL-BACK))
              (progn
                (setq ct  (oasis:topcen w h rt "Center" v)
                      bad (cond ((or (< (car ct) 0.0) (> (car ct) w)) "out")
                                ((oasis:nested-p ct rt (list rl rl) rl)
                                 "nested")))
                bad))
    (if (= bad "out")
        (princ (strcat "\nThat puts the hump's centre at "
                       (rtos (car ct)) ", off the " (rtos w)
                       " envelope altogether -- it has to stay on it."))
        (princ (strcat "\nAt " (rtos v) " off centre the hump and the left"
                       " bulge lie one inside the other, so no tangent"
                       " radius can join them.")))
    (setq v (oasis:askoff msg)))
  v)

;; One question of the run.  k is the answer slot it fills, ans the
;; answers gathered so far -- the checks that need an earlier answer read
;; it from there, so backing up and changing one re-checks everything
;; after it.  Returns the answer, or OASIS-BACK.
;;
;;   0 which shape      3 Y bound         6 right bulge   8 joiner right
;;   1 base point       4 left bulge      7 joiner top    9 joiner bottom
;;   2 X bound          5 top bulge                      10 a cloud's bottom
;;
;; A shape asks only the slots oasis:steps lists for it.
(defun oasis:askstep (k ans / var v w h rl rt rr cl ct cr ca cd cg off
                          runs)
  (setq var  (oasis:variant ans)
        w    (nth 2 ans) h  (nth 3 ans)
        rl   (oasis:leftrad var h (nth 4 ans))
        rt   (nth 5 ans) rr (nth 6 ans)
        off  (nth 12 ans)
        ;; on a complex run every joiner question takes Line as well
        runs (oasis:complex-p ans))
  ;; a true kidney's sides are derived from its top circle, so by the
  ;; time the bottom joiner is asked for they are known without ever
  ;; having been asked about
  (if (and (= var "TrueKidney") w h rt)
      (setq rl (oasis:ktrue-side w h rt)
            rr rl))
  (setq cl  (if (and w h rl) (list rl rl))
        ct  (if (and w h rt (not (oasis:kidney-p var)))
                (oasis:topcen w h rt var off))
        cr  (if (and w h rr) (list (- w rr) rr))
        ;; a NXT cloud's three lobes sit nowhere near the other shapes'
        ;; left/right/top, so they get their own three
        ca  (if (and w h rl (oasis:nxt-p var)) (oasis:nxtcen w h rl 0))
        cd  (if (and w h rt (oasis:nxt-p var)) (oasis:nxtcen w h rt 1))
        cg  (if (and w h rr (oasis:nxt-p var)) (oasis:nxtcen w h rr 2)))
  (cond
    ;; CLoud takes two capitals because Center already has the C.  The
    ;; keyword comes back spelled that way, so it is normalized here and
    ;; nothing downstream ever sees it.
    ((= k 0)
     (setq v (cal:askkw "Which shape is it?"
                          "Center TopRight CLoud Kidney NXTcloud"
                          "Center/TopRight/CLoud/Kidney/NXTcloud"
                          "Center" nil))
     (if (= v "CLoud") "Cloud" v))
    ((= k 10)
     (if (= (nth 0 ans) "Kidney")
         (cal:askkw "Kidney type?" "True Asymmetric"
                      "True/Asymmetric" "True" T)
         (cal:askkw "Cloud bottom?" "Straight Rounded"
                      "Straight/Rounded" "Straight" T)))
    ;; simple is the shape as it has always been; complex opens the two
    ;; things a drawing sometimes has and the plain flow cannot say --
    ;; a straight run in place of any joiner, and a hump off centre
    ((= k 11)
     (cal:askkw "Simple or complex?" "Simple Complex"
                  "Simple/Complex" "Simple" T))
    ((= k 1) (oasis:askbase T))
    ((= k 2) (cal:askdist 'REQ "X - overall left-to-right bounds" nil T))
    ((= k 3) (oasis:ask-ybound "Y - overall front-to-back bounds" w var))
    ((= k 4) (oasis:ask-bulge (oasis:sprompt var 4)
                              (if (oasis:nxt-p var) "top-left" "left") w h))
    ((= k 5) (cond ((oasis:nxt-p var)
                    (oasis:ask-bulge (oasis:sprompt var 5) "center" w h))
                   ((oasis:kidney-p var)
                    (oasis:ask-ktop (oasis:sprompt var 5) w h))
                   ((oasis:ask-top (oasis:sprompt var 5) w h rl var off))))
    ((= k 6) (oasis:ask-bulge (oasis:sprompt var 6) "right" w h))
    ;; on a cloud the top joiner runs straight from the right bulge back
    ;; to the left one; on an oasis it stops at the third bulge first;
    ;; on a NXT cloud every joiner runs between two of the three lobes
    ((= k 7) (cond ((oasis:nxt-p var)
                    (oasis:ask-tangent (oasis:sprompt var 7) cd rt ca rl
                                       runs))
                   ((oasis:cloud-p var)
                    (oasis:ask-tangent (oasis:sprompt var 7) cr rr cl rl
                                       runs))
                   ((oasis:ask-tangent (oasis:sprompt var 7) ct rt cl rl
                                       runs))))
    ((= k 8) (if (oasis:nxt-p var)
                 (oasis:ask-tangent (oasis:sprompt var 8) cg rr cd rt runs)
                 (oasis:ask-tangent (oasis:sprompt var 8) cr rr ct rt runs)))
    ((= k 9) (if (oasis:nxt-p var)
                 (oasis:ask-tangent (oasis:sprompt var 9) ca rl cd rt runs)
                 (oasis:ask-tangent (oasis:sprompt var 9) cl rl cr rr runs)))
    ((= k 12) (oasis:ask-offset (oasis:sprompt var 12) w h rl rt))
    ((= k 13) (oasis:ask-tangent (oasis:sprompt var 13) cd rt cg rr runs))))

;; The lobe a NXT cloud's right one lies inside, or swallows, or nil.
;; Its three are pinned by the envelope, so two of them can end up nested
;; with no tangent radius able to bridge them, exactly as on the oasis
;; shapes -- and the right lobe is the last of the three asked, so it is
;; where the pair shows up.  The other pair, the centre lobe inside the
;; top-left one, needs the top-left lobe at exactly half of a square
;; envelope, and there it swallows the right lobe as well, so this catches
;; that too.
(defun oasis:nxt-nests (w h rl rt rr / ca cd cg)
  (setq ca (oasis:nxtcen w h rl 0)
        cd (oasis:nxtcen w h rt 1)
        cg (oasis:nxtcen w h rr 2))
  (cond ((oasis:nested-p cg rr ca rl) "top-left")
        ((oasis:nested-p cg rr cd rt) "center")))

;; The right bulge is the last of the three, so it is the one that has
;; to be checked against BOTH of the others before the tangent radii are
;; asked for.  Returns the name of the bulge it nests with, or nil.
(defun oasis:right-nests (w h rl rt rr off variant / cl ct cr)
  (setq rl (oasis:leftrad variant h rl)
        cl (list rl rl)
        cr (list (- w rr) rr))
  (cond ((oasis:nested-p cr rr cl rl) "left")
        ((oasis:cloud-p variant) nil)
        ((progn (setq ct (oasis:topcen w h rt variant off))
                (oasis:nested-p cr rr ct rt))
         "top")))

;;; -------------------- walking the outline ------------------------------
;;; The bottom of the pool is laid out ON the perimeter, so everything
;;; below needs to be able to say where a point is along it.  The ring is
;;; a closed curve, so one number does it: the arc length S from the
;;; start of element 0, running the way the outline runs.
;;;
;;; That direction is not the same as an arc's own: a BULGE is walked
;;; counter-clockwise from its start angle to its end, a REVERSE arc the
;;; other way (its centre is outside the pool, so the outline goes round
;;; it clockwise), and a straight run from its first end to its second.
;;; Every element also knows which way is INTO the water, which is what
;;; an offset is measured along -- towards the centre on a bulge, away
;;; from it on a reverse arc, and across a run.

;; The angle one element sweeps, 0 for a straight run.
(defun oasis:esweep (a)
  (if (oasis:line-p a) 0.0 (cal:angnorm (- (nth 4 a) (nth 3 a)))))

;; How long one element is along the walk.
(defun oasis:elen (a)
  (if (oasis:line-p a)
      (distance (nth 1 a) (nth 2 a))
      (* (nth 2 a) (oasis:esweep a))))

;; The whole way round.
(defun oasis:ringlen (arcs / s a)
  (setq s 0.0)
  (foreach a arcs (setq s (+ s (oasis:elen a))))
  s)

;; Where element A is at fraction U of its own walk, as
;; (point . inward-angle) -- inward being the way an offset is measured.
(defun oasis:eat (a u / th)
  (if (oasis:line-p a)
      (cons (oasis:v+ (nth 1 a)
                      (oasis:v* (mapcar '- (nth 2 a) (nth 1 a)) u))
            (cal:angnorm (+ (nth 3 a) pi)))
      (progn
        ;; a bulge runs with the angle, a reverse arc against it
        (setq th (if (nth 5 a)
                     (+ (nth 3 a) (* u (oasis:esweep a)))
                     (- (nth 4 a) (* u (oasis:esweep a)))))
        (cons (polar (nth 1 a) th (nth 2 a))
              ;; the centre is inside the pool on a bulge and outside it
              ;; on a reverse arc, so the two point opposite ways
              (cal:angnorm (if (nth 5 a) (+ th pi) th))))))

;; The point at arc length S round the ring, as
;; (point inward-angle element-index fraction).  S wraps.
(defun oasis:ringat (arcs s / tot i n a l u pu out)
  (setq tot (oasis:ringlen arcs)
        n   (length arcs)
        i   0)
  (while (< s 0.0) (setq s (+ s tot)))
  (while (>= s tot) (setq s (- s tot)))
  (while (and (< i n) (null out))
    (setq a (nth i arcs)
          l (oasis:elen a))
    (if (or (<= s l) (= i (1- n)))
        (setq u   (if (> l oasis:*fuzz*) (/ s l) 0.0)
              pu  (oasis:eat a u)
              out (list (car pu) (cdr pu) i u))
        (setq s (- s l)))
    (setq i (1+ i)))
  out)

;; A list of numbers in ascending order, without duplicates closer
;; together than the fuzz -- a crossing that lands exactly on a joint is
;; found by both elements that meet there, and it is one crossing.
(defun oasis:sortasc (lst / out v p taken)
  (setq out nil taken nil)
  (while
    (progn
      (setq p nil)
      (foreach v lst
        (if (and (or (null taken) (> v (+ taken oasis:*fuzz*)))
                 (or (null p) (< v p)))
            (setq p v)))
      p)
    (setq out   (cons p out)
          taken p))
  (reverse out))

;; The arc length at which each element STARTS -- and so, one per
;; element, the arc length of every change of tangency round the ring.
(defun oasis:joints (arcs / s out a)
  (setq s 0.0 out nil)
  (foreach a arcs
    (setq out (cons s out)
          s   (+ s (oasis:elen a))))
  (reverse out))

;; The arc length of the point on the ring nearest P.
(defun oasis:ringnear (arcs p / s best bd i n a l u q d dx dy dd)
  (setq s 0.0 best 0.0 bd nil i 0 n (length arcs))
  (while (< i n)
    (setq a (nth i arcs)
          l (oasis:elen a))
    (if (oasis:line-p a)
        (setq dx (- (car (nth 2 a)) (car (nth 1 a)))
              dy (- (cadr (nth 2 a)) (cadr (nth 1 a)))
              dd (+ (* dx dx) (* dy dy))
              u  (if (> dd oasis:*fuzz*)
                     (/ (+ (* (- (car p) (car (nth 1 a))) dx)
                           (* (- (cadr p) (cadr (nth 1 a))) dy))
                        dd)
                     0.0))
        (setq u (if (> (oasis:esweep a) oasis:*fuzz*)
                    (/ (cal:angnorm
                         (if (nth 5 a)
                             (- (angle (nth 1 a) p) (nth 3 a))
                             (- (nth 4 a) (angle (nth 1 a) p))))
                       (oasis:esweep a))
                    0.0)))
    (setq u (max 0.0 (min 1.0 u))
          q (car (oasis:eat a u))
          d (distance p q))
    (if (or (null bd) (< d bd)) (setq bd d best (+ s (* u l))))
    (setq s (+ s l)
          i (1+ i)))
  best)

;; Every arc length at which the ring crosses the straight line through Q
;; with unit normal NRM, in ascending order.  Exact: a run is linear in
;; its own parameter, and an arc meets a line where its angle is one of
;; two the normal names -- no walking and no sampling.
(defun oasis:ringcut (arcs q nrm / s out i n a l d0 dx dy den u ph c th)
  (setq s 0.0 out nil i 0 n (length arcs))
  (while (< i n)
    (setq a  (nth i arcs)
          l  (oasis:elen a)
          d0 (+ (* (- (car (nth 1 a)) (car q)) (car nrm))
                (* (- (cadr (nth 1 a)) (cadr q)) (cadr nrm))))
    (if (oasis:line-p a)
        (progn
          (setq dx  (- (car (nth 2 a)) (car (nth 1 a)))
                dy  (- (cadr (nth 2 a)) (cadr (nth 1 a)))
                den (+ (* dx (car nrm)) (* dy (cadr nrm))))
          (if (> (abs den) oasis:*fuzz*)
              (progn
                (setq u (/ (- d0) den))
                (if (and (>= u 0.0) (<= u 1.0))
                    (setq out (cons (+ s (* u l)) out))))))
        (progn
          (setq c (/ (- d0) (nth 2 a)))
          (if (<= (abs c) 1.0)
              (progn
                (setq ph (atan (cadr nrm) (car nrm)))
                (foreach th (list (+ ph (atan (sqrt (max 0.0 (- 1.0 (* c c))))
                                              c))
                                  (- ph (atan (sqrt (max 0.0 (- 1.0 (* c c))))
                                              c)))
                  (setq u (if (> (oasis:esweep a) oasis:*fuzz*)
                              (/ (cal:angnorm
                                   (if (nth 5 a)
                                       (- th (nth 3 a))
                                       (- (nth 4 a) th)))
                                 (oasis:esweep a))))
                  (if (and u (<= u 1.0))
                      (setq out (cons (+ s (* u l)) out))))))))
    (setq s (+ s l)
          i (1+ i)))
  (oasis:sortasc out))

;;; -------------------- the pool bottom ----------------------------------
;;; The floor, laid out on the perimeter the questions have just built --
;;; ABHD's bottom flow, with ABHD's one input replaced.  There it is a
;;; survey: points are picked on the pool edge and everything is measured
;;; from the nearest one.  Here the perimeter is not surveyed but KNOWN,
;;; exactly, so a point on it can be said three ways:
;;;
;;;   Tangency  every change of tangency round the outline is numbered
;;;             and drawn on screen while the question is up -- the
;;;             joints between the arcs, which are the places a pool
;;;             is naturally broken at.  Name a number.
;;;   Nearest   pick anywhere; the pick is dropped onto the outline at
;;;             the nearest point of it, exactly.
;;;   Offset    say how far in from one of the four bounds, and the
;;;             break is where that line crosses the pool -- one answer
;;;             for both ends of the break, which is how a deep end is
;;;             usually called out ("the hopper starts 12 feet in").
;;;
;;; What is drawn is ABHD's: a SHALLOW BREAK across the pool where the
;;; flat shallow floor starts to fall, a DEEP BREAK where it levels out,
;;; the HOPPER beyond it -- the flat deep floor, the perimeter offset
;;; inward -- and a SLOPE LINE up each side from the hopper's corner to
;;; the shallow break.  The deep break goes down as three collinear
;;; pieces, dashed stubs from each wall in to the hopper's corners with a
;;; solid run between them, and carries the classic K/L/M string of
;;; chained dimensions a stand-off clear of it on the shallow side.
;;;
;;; One thing is not ABHD's.  ABHD asks three offsets -- one at each end
;;; of the deep break and one at the back -- and blends them along the
;;; wall, because a surveyed shape is irregular and the tape says
;;; different things in different places.  An oasis is a designed shape,
;;; so its hopper is ONE offset, and that buys exactness: offsetting a
;;; tangent-continuous ring inward by a constant is again a
;;; tangent-continuous ring, with the same centres, the same angles, and
;;; every bulge shrunk and every reverse arc grown by the offset.  The
;;; hopper is that ring cut off at the deep break, so it is arcs and
;;; runs, not a polyline of facets, and its corners are exactly where it
;;; meets the break.  The K/L/M string then reads what the offset really
;;; produced at the break rather than the number that was typed.

;; One ring element pushed inward by OFF.  A bulge curves away from the
;; water, so it shrinks; a reverse arc curves into it, so it grows; a
;; straight run simply moves across.  The result meets its neighbours at
;; the same normals it did, which is why the offset ring is still
;; tangent-continuous.
(defun oasis:offel (a off)
  (if (oasis:line-p a)
      (list (nth 0 a)
            (polar (nth 1 a) (+ (nth 3 a) pi) off)
            (polar (nth 2 a) (+ (nth 3 a) pi) off)
            (nth 3 a) nil "LINE" nil)
      (list (nth 0 a) (nth 1 a)
            (if (nth 5 a) (- (nth 2 a) off) (+ (nth 2 a) off))
            (nth 3 a) (nth 4 a) (nth 5 a) nil)))

;; The first bulge an offset of OFF would swallow, or nil.  Past its own
;; radius a bulge has no offset left to give and the hopper cannot be
;; built at all -- there is no arc on the other side of it.
(defun oasis:offbad (arcs off / bad a)
  (setq bad nil)
  (foreach a arcs
    (if (and (null bad) (not (oasis:line-p a)) (nth 5 a)
             (<= (- (nth 2 a) off) oasis:*fuzz*))
        (setq bad (nth 0 a))))
  bad)

;; The whole ring pushed inward by OFF, or nil when a bulge would go.
(defun oasis:offring (arcs off / out a)
  (if (oasis:offbad arcs off)
      nil
      (progn
        (setq out nil)
        (foreach a arcs (setq out (cons (oasis:offel a off) out)))
        (reverse out))))

;; One ring element cut down to the stretch between fractions U0 and U1
;; of its own walk.  An arc keeps its centre and its radius; only the two
;; angles move, and which end each fraction lands on depends on which way
;; the walk runs -- with the angle on a bulge, against it on a reverse.
(defun oasis:trimel (a u0 u1 / sw)
  (if (oasis:line-p a)
      (list (nth 0 a) (car (oasis:eat a u0)) (car (oasis:eat a u1))
            (nth 3 a) nil "LINE" nil)
      (progn
        (setq sw (oasis:esweep a))
        (if (nth 5 a)
            (list (nth 0 a) (nth 1 a) (nth 2 a)
                  (cal:angnorm (+ (nth 3 a) (* u0 sw)))
                  (cal:angnorm (+ (nth 3 a) (* u1 sw)))
                  (nth 5 a) nil)
            (list (nth 0 a) (nth 1 a) (nth 2 a)
                  (cal:angnorm (- (nth 4 a) (* u1 sw)))
                  (cal:angnorm (- (nth 4 a) (* u0 sw)))
                  (nth 5 a) nil)))))

;; How far it is round the ring from SA forward to SB.
(defun oasis:spanlen (arcs sa sb / tot d)
  (setq tot (oasis:ringlen arcs)
        d   (- sb sa))
  (while (< d 0.0) (setq d (+ d tot)))
  (while (>= d tot) (setq d (- d tot)))
  d)

;; The stretch of the ring from SA forward to SB, as ring elements with
;; the first and last trimmed -- an OPEN chain, drawable by oasis:draw
;; like any other.
(defun oasis:subring (arcs sa sb / n at k u0 want l avail u1 out guard)
  (setq n     (length arcs)
        at    (oasis:ringat arcs sa)
        k     (nth 2 at)
        u0    (nth 3 at)
        want  (oasis:spanlen arcs sa sb)
        out   nil
        guard 0)
  (while (and (> want oasis:*fuzz*) (< guard (* 4 n)))
    (setq l     (oasis:elen (nth k arcs))
          avail (* l (- 1.0 u0)))
    (if (<= want (+ avail oasis:*fuzz*))
        (setq u1   (if (> l oasis:*fuzz*) (min 1.0 (+ u0 (/ want l))) 1.0)
              out  (cons (oasis:trimel (nth k arcs) u0 u1) out)
              want 0.0)
        (setq out  (if (> avail oasis:*fuzz*)
                       (cons (oasis:trimel (nth k arcs) u0 1.0) out)
                       out)
              want (- want avail)
              k    (if (= k (1- n)) 0 (1+ k))
              u0   0.0))
    (setq guard (1+ guard)))
  (reverse out))

;; The stretch from SA to SB as a run of N+1 points, each pushed in by an
;; offset easing from O0 to O1 over the walk.  Where the offset varies
;; there is no exact curve to draw -- a slope line running out to nothing
;; at the shallow break is the case -- so it goes down as a polyline.
(defun oasis:chordrun (arcs sa sb o0 o1 n / len i out at f)
  (setq len (oasis:spanlen arcs sa sb)
        i   0
        out nil)
  (while (<= i n)
    (setq f   (/ (float i) (float n))
          at  (oasis:ringat arcs (+ sa (* len f)))
          out (cons (polar (car at) (cadr at) (+ o0 (* (- o1 o0) f))) out)
          i   (1+ i)))
  (reverse out))

;; How far the ring reaches beyond the break line through MID along U,
;; over the LEN of walk starting at SA, and where.  Returns
;; (arc-length . reach).
(defun oasis:reach (arcs sa len mid u n / i s at d best bd)
  (setq i  0
        bd nil)
  (while (<= i n)
    (setq s  (+ sa (* len (/ (float i) (float n))))
          at (oasis:ringat arcs s)
          d  (+ (* (- (car (car at)) (car mid)) (car u))
                (* (- (cadr (car at)) (cadr mid)) (cadr u))))
    (if (or (null bd) (> d bd)) (setq bd d best s))
    (setq i (1+ i)))
  (cons best bd))

;; The unit vector square to the deep break, pointing AWAY from the
;; shallow break -- the direction the hopper lies in.
(defun oasis:deepdir (p1 p2 q / u)
  (setq u (list (- (cadr p2) (cadr p1)) (- (car p1) (car p2))))
  (setq u (oasis:v* u (/ 1.0 (max oasis:*fuzz* (distance '(0.0 0.0) u)))))
  (if (> (+ (* (- (car q) (car p1)) (car u))
            (* (- (cadr q) (cadr p1)) (cadr u)))
         0.0)
      (oasis:v* u -1.0)
      u))

;; Where the hopper starts and stops on the OFFSET ring: the two places
;; it crosses the deep break line either side of its deepest point.
;; Returns (from to deepest), or nil when the offset ring never reaches
;; the break -- an offset so big the deep end has closed up.
(defun oasis:hopcut (offall q nrm mid u / cuts tot far ca cb c)
  (setq cuts (oasis:ringcut offall q nrm)
        tot  (oasis:ringlen offall))
  (if (< (length cuts) 2)
      nil
      (progn
        (setq far (car (oasis:reach offall 0.0 tot mid u oasis:*hopscan*))
              ca  nil
              cb  nil)
        (foreach c cuts
          (if (and (<= c far) (or (null ca) (> c ca))) (setq ca c))
          (if (and (>= c far) (or (null cb) (< c cb))) (setq cb c)))
        ;; the deepest point can sit past the last crossing, in which
        ;; case the hopper wraps the start of the ring
        (if (null ca) (setq ca (last cuts)))
        (if (null cb) (setq cb (car cuts)))
        (if (< (oasis:spanlen offall ca cb) oasis:*fuzz*)
            nil
            (list ca cb far)))))

;;; -------------------- the bottom, asked ---------------------------------

;; Every change of tangency, numbered on screen, so one can be named.
;; Scaffolding: the marks go when the flow does, like the preview.
(defun oasis:tangmarks (arcs w h base lt / out js i n at hgt mk)
  (setq js  (oasis:joints arcs)
        n   (length js)
        i   0
        hgt (/ (max w h) 34.0)
        mk  (/ (max w h) 150.0)
        out nil)
  (while (< i n)
    (setq at  (oasis:ringat arcs (nth i js))
          out (cons (oasis:pv-circle (car at) mk base "CONTINUOUS" T) out)
          ;; the number sits OUTSIDE the water, clear of the outline
          out (cons (oasis:pv-text (polar (car at)
                                          (+ (cadr at) pi)
                                          (* 1.6 hgt))
                                   hgt (itoa (1+ i)) base T)
                    out)
          i   (1+ i)))
  out)

;; A tangency change, by number.  Returns its arc length, or OASIS-BACK.
(defun oasis:asktang (msg arcs / js n v)
  (setq js (oasis:joints arcs)
        n  (length js)
        v  nil)
  (while (null v)
    (initget 7 "Back Undo")
    (setq v (getint (strcat "\n" msg " -- tangency change 1-" (itoa n)
                            " [Back]: ")))
    (cond ((and (= (type v) 'STR) (member v '("Back" "Undo")))
           (setq v 'CAL-BACK))
          ((and (= (type v) 'INT) (<= v n)))
          (t (princ (strcat "\nThere are " (itoa n) " changes of tangency"
                            " round this pool; that is not one of them."))
             (setq v nil))))
  (if (eq v 'CAL-BACK) v (nth (1- v) js)))

;; A point picked anywhere, dropped onto the outline at the nearest point
;; of it.  Returns its arc length, or OASIS-BACK.
(defun oasis:asknear (msg arcs base / v)
  (initget 1 "Back Undo")
  (setq v (getpoint (strcat "\n" msg " [Back]: ")))
  (if (and (= (type v) 'STR) (member v '("Back" "Undo")))
      'CAL-BACK
      (oasis:ringnear arcs (list (- (car v) (car base))
                                 (- (cadr v) (cadr base))))))

;; A line parallel to one bound of the envelope, a given distance in from
;; it.  Returns (point normal), or OASIS-BACK.
(defun oasis:askbound (msg w h / side d)
  ;; BOttom takes two capitals because Back already has the B
  (setq side (cal:askkw (strcat msg " -- in from which bound?")
                          "Left Right BOttom Top"
                          "Left/Right/BOttom/Top" "BOttom" T))
  (if (eq side 'CAL-BACK)
      side
      (progn
        (setq d (cal:askdist 'REQ (strcat "How far in from the "
                                            (strcase side T) " bound")
                               nil T))
        (if (eq d 'CAL-BACK)
            d
            (cond ((= side "Left")    (list (list d 0.0) '(1.0 0.0)))
                  ((= side "Right")   (list (list (- w d) 0.0) '(1.0 0.0)))
                  ((= side "BOttom")  (list (list 0.0 d) '(0.0 1.0)))
                  (t                  (list (list 0.0 (- h d))
                                            '(0.0 1.0))))))))

;; One break, both ends, said whichever of the three ways suits.  Returns
;; (s1 s2) as arc lengths round the outline, or OASIS-BACK.
(defun oasis:askbreak (what arcs w h base / how ln cuts a b)
  (setq a nil)
  (while (null a)
    (setq how (cal:askkw (strcat what " break, located how?")
                           "Offset Tangency Nearest"
                           "Offset/Tangency/Nearest" "Offset" T))
    (cond
      ((eq how 'CAL-BACK) (setq a how))
      ;; one answer gives both ends: the break is the chord that line cuts
      ((= how "Offset")
       (setq ln (oasis:askbound (strcat "The " (strcase what T) " break")
                                w h))
       (cond
         ((eq ln 'CAL-BACK) (setq a ln))
         (t (setq cuts (oasis:ringcut arcs (car ln) (cadr ln)))
            ;; a pool whose edge dips can be crossed more than twice by
            ;; one line -- the break is the full width of it, so the two
            ;; outermost crossings are the ones wanted, and the rest are
            ;; the dip the break runs over
            (cond
              ((< (length cuts) 2)
               (princ (strcat "\nThat line does not cross the pool at all,"
                              " so it does not name a break.")))
              (t (if (> (length cuts) 2)
                     (princ (strcat "\n(that line crosses the outline "
                                    (itoa (length cuts)) " times -- the"
                                    " break is taken right across, from the"
                                    " first to the last)")))
                 (setq a (list (car cuts) (last cuts))))))))
      ((= how "Tangency")
       (setq a (oasis:asktang (strcat "The " (strcase what T)
                                      " break, first end") arcs))
       (if (not (eq a 'CAL-BACK))
           (progn
             (setq b (oasis:asktang (strcat "The " (strcase what T)
                                            " break, second end") arcs))
             (if (eq b 'CAL-BACK)
                 (setq a nil)
                 (setq a (list a b))))))
      (t
       (setq a (oasis:asknear (strcat "The " (strcase what T)
                                      " break, first end") arcs base))
       (if (not (eq a 'CAL-BACK))
           (progn
             (setq b (oasis:asknear (strcat "The " (strcase what T)
                                            " break, second end")
                                    arcs base))
             (if (eq b 'CAL-BACK)
                 (setq a nil)
                 (setq a (list a b)))))))
    ;; two ends in the same place are not a break
    (if (and a (listp a)
             (< (distance (car (oasis:ringat arcs (car a)))
                          (car (oasis:ringat arcs (cadr a))))
                oasis:*fuzz*))
        (progn
          (princ "\nBoth ends of that break land on the same point.")
          (setq a nil))))
  a)

;;; -------------------- the bottom, built and drawn -----------------------

;; Everything the bottom is made of, worked out from the two breaks and
;; the one offset.  Returns
;;
;;   (hopper cs ce pda pdb qsa qsb ssa sda ssb sdb backw backh)
;;
;; where the hopper is a chain of ring elements, cs and ce its two
;; corners on the deep break line, pda / pdb the deep break's own two
;; ends -- pda first in the hopper's own walk -- qsa / qsb the shallow
;; break ends paired with them, ssa / sda / ssb / sdb their arc lengths,
;; and backw / backh the wall and hopper points at the back, which is
;; where the offset is worth dimensioning.  A string instead of a list is
;; the reason it cannot be built.
(defun oasis:bottom (arcs sh1 sh2 sd1 sd2 off
                     / p1 p2 q1 q2 pmid qmid u bad offall cut hop
                       ca cb cs ce da db pda pdb ssa ssb qsa qsb bp backh
                       backw r12 r21)
  (setq p1   (car (oasis:ringat arcs sd1))
        p2   (car (oasis:ringat arcs sd2))
        q1   (car (oasis:ringat arcs sh1))
        q2   (car (oasis:ringat arcs sh2))
        pmid (list (* 0.5 (+ (car p1) (car p2)))
                   (* 0.5 (+ (cadr p1) (cadr p2))))
        qmid (list (* 0.5 (+ (car q1) (car q2)))
                   (* 0.5 (+ (cadr q1) (cadr q2))))
        ;; u is square to the deep break and points away from the
        ;; shallow one, so it is also that break line's own normal --
        ;; which is what a cut of the ring is asked for by
        u    (oasis:deepdir p1 p2 qmid))
  ;; which way round the ring is the deep end?  the stretch that reaches
  ;; furthest away from the shallow break
  (setq r12 (cdr (oasis:reach arcs sd1 (oasis:spanlen arcs sd1 sd2)
                              pmid u oasis:*hopscan*))
        r21 (cdr (oasis:reach arcs sd2 (oasis:spanlen arcs sd2 sd1)
                              pmid u oasis:*hopscan*)))
  (if (>= r12 r21)
      (setq da sd1 db sd2 pda p1 pdb p2)
      (setq da sd2 db sd1 pda p2 pdb p1))
  ;; the shallow end on each side is the one nearest that deep end
  ;; walking AWAY from the hopper -- backwards, since the hopper runs
  ;; forwards from da
  (if (<= (oasis:spanlen arcs sh1 da) (oasis:spanlen arcs sh2 da))
      (setq ssa sh1 qsa q1 ssb sh2 qsb q2)
      (setq ssa sh2 qsa q2 ssb sh1 qsb q1))
  (cond
    ;; a shallow break on the far side of the deep one is the two of them
    ;; the wrong way round: the slope lines would have to run through the
    ;; hopper to reach it
    ((or (> (+ (* (- (car q1) (car pmid)) (car u))
               (* (- (cadr q1) (cadr pmid)) (cadr u)))
            (- oasis:*fuzz*))
         (> (+ (* (- (car q2) (car pmid)) (car u))
               (* (- (cadr q2) (cadr pmid)) (cadr u)))
            (- oasis:*fuzz*)))
     "the shallow break reaches past the deep one -- the two look swapped")
    ((setq bad (oasis:offbad arcs off))
     (strcat "the " bad " bulge is not " (rtos off) " wide, so there is"
             " no hopper wall to draw inside it"))
    ((null (setq offall (oasis:offring arcs off)))
     "that offset leaves no pool inside it")
    ((oasis:crossings offall)
     "at that offset the hopper wall runs through itself")
    ((null (setq cut (oasis:hopcut offall pda u pmid u)))
     "the offset closes the deep end before it reaches the break")
    (t
     (setq ca  (car cut)
           cb  (cadr cut)
           hop (oasis:subring offall ca cb)
           cs  (car (oasis:ringat offall ca))
           ce  (car (oasis:ringat offall cb)))
     ;; the corner at the start of the hopper's walk belongs to the wall
     ;; end that walk starts from: the offset ring runs the same way
     ;; round as the wall and stays the offset inside it, so the crossing
     ;; before the deepest point is the one off pda and the crossing
     ;; after it the one off pdb
     ;; the back: the deepest point of the hopper, and the wall it is
     ;; measured off
     (setq bp    (car (oasis:reach offall ca (oasis:spanlen offall ca cb)
                                   pmid u oasis:*hopscan*))
           backh (car (oasis:ringat offall bp))
           backw (car (oasis:ringat arcs (oasis:ringnear arcs backh))))
     (list hop cs ce pda pdb qsa qsb ssa da ssb db backw backh))))

;; A LINE on one layer, optionally with a linetype of its own.
(defun oasis:mkline (p q base lay lt / lst)
  (setq lst (list '(0 . "LINE")
                  (cons 8 lay)
                  (cons 10 (trans (oasis:wp p base) 1 0))
                  (cons 11 (trans (oasis:wp q base) 1 0))))
  (if (and lt (/= lt "CONTINUOUS"))
      (setq lst (append lst (list (cons 6 lt) (cons 48 (oasis:ltsc))))))
  (entmake lst)
  (entlast))

;; An open polyline through PTS.
(defun oasis:mkpl (pts base lay / lst p)
  (setq lst (list '(0 . "LWPOLYLINE")
                  '(100 . "AcDbEntity")
                  (cons 8 lay)
                  '(100 . "AcDbPolyline")
                  (cons 90 (length pts))
                  '(70 . 0)))
  (foreach p pts
    (setq lst (append lst (list (cons 10 (trans (oasis:wp p base) 1 0))))))
  (entmake lst)
  (entlast))

;; One slope line, from a hopper corner up to the shallow break point on
;; its own side.  Straight is a clean run; guided follows the pool's own
;; wall with its offset easing from the hopper's at the deep break to
;; nothing at the shallow one, so it lands on the shallow break having
;; followed the curve in.  Either way it departs from the corner itself.
(defun oasis:slope (arcs ss sd off corner shal guided base lay / pts)
  (if (not guided)
      (oasis:mkline corner shal base lay nil)
      (progn
        (setq pts (oasis:chordrun arcs ss sd 0.0 off oasis:*hopchord*))
        ;; the walk ends at the deep break; the line has to end on the
        ;; corner, which sits on the break line itself
        (setq pts (reverse (cons corner (cdr (reverse pts))))
              pts (cons shal (cdr pts)))
        (oasis:mkpl pts base lay))))

;; Draw the whole bottom and dimension it.  Returns the entities made.
(defun oasis:drawbottom (bot arcs base w h lt ga gb off
                         / hop cs ce pda pdb qsa qsb ssa da ssb db backw
                           backh out doff sh p)
  (setq hop  (nth 0 bot)  cs   (nth 1 bot)  ce   (nth 2 bot)
        pda  (nth 3 bot)  pdb  (nth 4 bot)  qsa  (nth 5 bot)
        qsb  (nth 6 bot)  ssa  (nth 7 bot)  da   (nth 8 bot)
        ssb  (nth 9 bot)  db   (nth 10 bot) backw (nth 11 bot)
        backh (nth 12 bot)
        doff (oasis:dimoff w h)
        out  nil)
  (setvar "CLAYER" oasis:*poollayer*)
  ;; the shallow break, straight across
  (setq out (cons (oasis:mkline qsa qsb base oasis:*poollayer* nil) out))
  ;; the deep break in three collinear pieces: a dashed stub from each
  ;; wall in to its hopper corner, a solid run across the hopper between
  (setq out (cons (oasis:mkline pda cs base oasis:*poollayer* lt) out)
        out (cons (oasis:mkline cs ce base oasis:*poollayer* nil) out)
        out (cons (oasis:mkline ce pdb base oasis:*poollayer* lt) out))
  ;; the hopper itself -- arcs and runs, not facets
  (setq out (append (oasis:draw hop base oasis:*poollayer*) out))
  ;; a slope line up each side
  (setq out (cons (oasis:slope arcs ssa da off cs qsa ga base
                               oasis:*poollayer*)
                  out)
        out (cons (oasis:slope arcs ssb db off ce qsb gb base
                               oasis:*poollayer*)
                  out))
  ;; the K/L/M string: wall to hopper, hopper across, hopper to wall,
  ;; all chained on one line a stand-off clear of the deep break on the
  ;; SHALLOW side, so it reads from the shallow end rather than from
  ;; over the deep end it measures
  (setvar "CLAYER" oasis:*dimlayer*)
  (oasis:dimstyle-on oasis:*dimstyle*)
  (setq sh (oasis:v* (oasis:deepdir pda pdb
                                    (list (* 0.5 (+ (car qsa) (car qsb)))
                                          (* 0.5 (+ (cadr qsa) (cadr qsb)))))
                     -1.0))
  (foreach p (list (list pda cs) (list cs ce) (list ce pdb))
    (command "_.DIMALIGNED"
             (oasis:wp (car p) base) (oasis:wp (cadr p) base)
             (oasis:wp (polar (list (* 0.5 (+ (car (car p)) (car (cadr p))))
                                    (* 0.5 (+ (cadr (car p))
                                              (cadr (cadr p)))))
                              (atan (cadr sh) (car sh))
                              doff)
                       base)))
  ;; and the offset itself, where it is squarest to the wall
  (oasis:crossdim backw backh base)
  out)

;; The hopper offset, re-asked until a hopper can be built on it.  What
;; rules one out is never the number on its own -- it is the number
;; against this pool -- so the check is the build itself.  Returns
;; (offset bottom), or OASIS-BACK.
(defun oasis:askhopoff (arcs sh sd / off bot try)
  (setq bot nil)
  (while (null bot)
    (initget 6 "Back Undo")
    (setq off (getdist (strcat "\nHopper offset in from the wall [Back] <"
                               (rtos oasis:*hopoff*) ">: ")))
    (cond
      ((and (= (type off) 'STR) (member off '("Back" "Undo")))
       (setq bot 'CAL-BACK))
      (t
       (if (null off) (setq off oasis:*hopoff*))
       (setq try (oasis:bottom arcs (car sh) (cadr sh) (car sd) (cadr sd)
                               off))
       (if (= (type try) 'STR)
           (princ (strcat "\nAt " (rtos off) " " try "."))
           (setq oasis:*hopoff* off
                 bot            (list off try))))))
  bot)

;; How one slope line runs.  The side is named by the arc its end of the
;; deep break lands on, so there is never a doubt which of the two is
;; being asked about.  Returns T for guided, nil for straight, or
;; OASIS-BACK.
(defun oasis:askslope (arcs bot which / da nm v)
  (setq da (if (= which 0) (nth 8 bot) (nth 10 bot))
        nm (nth 0 (nth (nth 2 (oasis:ringat arcs da)) arcs))
        v  (cal:askkw (strcat "Slope line on the " nm " side")
                        "Straight Guided" "Straight/Guided" "Straight" T))
  (if (eq v 'CAL-BACK) v (= v "Guided")))

;; The whole bottom flow, with Back between its steps the way the pool's
;; own questions have it.  Back out of the first step and nothing is
;; added at all.  Returns the lines to report, so they land after the
;; pool's own, or nil when nothing was added.
(defun oasis:askbottom (arcs w h base lt / marks ans pos k v off bot done)
  (setq marks (oasis:tangmarks arcs w h base lt)
        ans   (list nil nil nil nil nil)
        pos   0)
  (while (and pos (< pos 5))
    (setq k pos
          v (cond ((= k 0) (oasis:askbreak "Shallow" arcs w h base))
                  ((= k 1) (oasis:askbreak "Deep" arcs w h base))
                  ((= k 2) (oasis:askhopoff arcs (nth 0 ans) (nth 1 ans)))
                  (t       (oasis:askslope arcs (cadr (nth 2 ans))
                                           (- k 3)))))
    (if (eq v 'CAL-BACK)
        (if (> pos 0)
            (progn (princ "\nStepping back one step.")
                   (setq pos (1- pos)))
            (progn (princ "\nNo bottom added.")
                   (setq pos nil)))
        (setq ans (oasis:put ans k v)
              pos (1+ pos))))
  (setq marks (oasis:pv-clear marks))
  (if (null pos)
      nil
      (progn
        (setq off  (car (nth 2 ans))
              bot  (cadr (nth 2 ans))
              done (oasis:drawbottom bot arcs base w h lt
                                     (nth 3 ans) (nth 4 ans) off))
        (list
          (strcat "\nBottom on layer " oasis:*poollayer*
                  ": the shallow break, the three-piece deep break"
                  " (dashed stubs,")
          (strcat "\n  solid middle), the hopper " (rtos off)
                  " in from the wall, and the slope lines ("
                  (if (nth 3 ans) "guided" "straight") " / "
                  (if (nth 4 ans) "guided" "straight") ").")
          (strcat "\n  K/L/M at the deep break: "
                  (rtos (distance (nth 3 bot) (nth 1 bot))) " / "
                  (rtos (distance (nth 1 bot) (nth 2 bot))) " / "
                  (rtos (distance (nth 2 bot) (nth 4 bot))) ".")))))

;;; -------------------- reporting ---------------------------------------

;; s padded out to w characters, so the report's rows line up.
(defun oasis:pad (s w)
  (while (< (strlen s) w) (setq s (strcat s " ")))
  s)

;; The bulges the ring left out.  A bulge whose two joiners hand over at
;; the same point is a point on the outline rather than an arc of it, and
;; oasis:solve drops it -- so the radius the user gave for it is not in
;; the drawing anywhere, which is worth saying out loud.  Bulges sit at
;; the even positions of the name list.
(defun oasis:pinched (arcs variant / have nm out i)
  (setq have (mapcar 'car arcs)
        nm   (oasis:names variant)
        out  nil
        i    0)
  (while (< i (length nm))
    (if (and (= 0 (rem i 2)) (not (member (nth i nm) have)))
        (setq out (cons (nth i nm) out)))
    (setq i (+ i 1)))
  (reverse out))


;; Say when the outline runs through itself.  Nothing that gets this far
;; was impossible to build -- every arc exists and the six of them close
;; -- but radii wildly out of proportion with each other can send one arc
;; clean through another, and that is not a pool.  It is drawn anyway and
;; named, so it is obvious on the screen and one U takes it away.
(defun oasis:report-crossings (arcs / bad p)
  (setq bad (oasis:crossings arcs))
  (if bad
      (progn
        (princ "\nOASIS: the outline runs through itself --")
        (foreach p bad
          (princ (strcat "\n         the " (car p) " arc crosses the "
                         (cadr p) " arc")))
        (princ "\n       That is not a pool.  One U takes it away; try a")
        (princ "\n       smaller radius on either of the arcs named.")))
  (setq bad (oasis:overlaps arcs))
  (if bad
      (progn
        (princ "\nOASIS: the outline runs over the same circle twice --")
        (foreach p bad
          (princ (strcat "\n         the " (car p) " arc laps the "
                         (cadr p) " arc")))
        (princ "\n       The lobe they are both cut from is handed over in")
        (princ "\n       the wrong order.  One U takes it away; the tangent")
        (princ "\n       radii round that lobe are what decide it."))
  )
  (princ))

;; Say how the finished outline compares with the envelope it was asked
;; to fill.  Everything impossible was refused at the question that
;; caused it, so anything left here is legal but worth knowing about -- a
;; top bulge wide enough to swing out past a side before its tangent arcs
;; catch it, most often.  The arc that is out is named, because the
;; radius behind an overrun is not always the one you would guess.
(defun oasis:report-extents (arcs w h / over p)
  (setq over (oasis:overruns arcs w h))
  (if over
      (progn
        (princ "\nOASIS: the outline does NOT stay inside the envelope --")
        (foreach p over
          (princ (strcat "\n         the " (caddr p) " arc goes "
                         (rtos (cadr p)) " past " (car p))))
        (princ "\n       Drawn as asked; try a smaller radius on the arc")
        (princ "\n       named, and on the bulge either side of it."))
  )
  (princ))

;;; -------------------- the command -------------------------------------


(defun c:OASIS ( / *error* undo-open guard ans pos k steps v var base w h
                   rl rt rr ftl ftr fbc fbr off cbase arcs ents nests prev
                   lt a nchk gotbot)
  (defun *error* (msg)
    ;; user settings come back FIRST so nothing below can skip them
    (cal:dimstyrestore)
    (cal:sysrestore)
    ;; an Esc part-way through a dimension leaves that command pending,
    ;; and the UNDO below would be swallowed as an answer to it
    (setq guard 0)
    (while (and (> (getvar "CMDACTIVE") 0) (< guard 10))
      (command)
      (setq guard (1+ guard)))
    ;; the preview is scaffolding, not a result -- it goes whether the run
    ;; finished or the user pressed Esc part-way through the questions
    (oasis:pv-clear prev)
    (if undo-open (command "_.UNDO" "_End"))
    (if (and msg (not (wcmatch (strcase msg)
                               "*BREAK*,*CANCEL*,*QUIT*,*EXIT*")))
      (princ (strcat "\nOASIS error: " msg)))
    (princ))

  (cal:syssave '("OSMODE" "CMDECHO" "CLAYER"))
  (cal:dimstysave)

  (cond
    ;; -- a plan pool has nothing sensible to draw in a UCS that is not
    ;;    flat in the world plan, and half of what it draws (the arcs)
    ;;    could not follow it there anyway
    ((not (oasis:ucs-flat-p))
     (princ (strcat "\nOASIS: the current UCS is tilted out of the world"
                    " plan, so a flat plan pool"))
     (princ (strcat "\n       cannot be laid out in it.  Set the UCS back"
                    " to World (or to any"))
     (princ "\n       plan UCS) and run OASIS again.")
     (cal:sysrestore))
    (t

     (setvar "CMDECHO" 0)
     (command "_.UNDO" "_Begin")
     (setq undo-open T)
     (cal:ensure-layer oasis:*poollayer* oasis:*poolcolor*)
     (cal:ensure-layer oasis:*guidelayer* oasis:*guidecolor*)
     (cal:ensure-layer oasis:*dimlayer* oasis:*dimcolor*)

     ;; -- which shape, where it goes, and then the eight measurements,
     ;;    with Back between them all.  Every check reads the answers
     ;;    already given, so backing up to change one re-checks
     ;;    everything that follows it -- and the preview is redrawn
     ;;    before each question, with the circle being asked about
     ;;    picked out in red.
     ;;    Which slots get asked, and in what order, is the shape's own
     ;;    business -- so the step list is re-read every time round,
     ;;    and changing the shape at the first question changes every
     ;;    question after it.
     (setq ans '(nil nil nil nil nil nil nil nil nil nil nil nil nil nil)
           pos 0)
     (while (progn (setq steps (oasis:steps ans))
                   (< pos (length steps)))
       (setq k    (nth pos steps)
             prev (oasis:preview prev ans k)
             v    (oasis:askstep k ans))
       (if (eq v 'CAL-BACK)
           (if (> pos 0)
               (progn (princ "\nStepping back one step.")
                      (setq pos (1- pos)))
               (princ "\nAlready at the first step."))
           (progn
             (setq ans (oasis:put ans k v)
                   pos (1+ pos))
             ;; the right bulge is the last one asked for on every shape,
             ;; so it is where anything the sides do TOGETHER finally
             ;; shows up: a nesting on the oasis shapes, an unreachable
             ;; top circle on the asymmetric kidney
             (if (= k 6)
                 (cond
                   ((oasis:nxt-p (oasis:variant ans))
                    (setq nests (oasis:nxt-nests (nth 2 ans) (nth 3 ans)
                                                 (nth 4 ans) (nth 5 ans)
                                                 (nth 6 ans)))
                    (if nests
                        (progn
                          (princ (strcat "\nThat right lobe and the " nests
                                         " lobe lie one inside the other, so"
                                         " no tangent radius can join them."
                                         "  Asking again."))
                          (setq pos (1- pos)))))
                   ((= (oasis:variant ans) "AsymKidney")
                    (if (not (oasis:kidney-top (nth 2 ans) (nth 3 ans)
                                               (nth 4 ans) (nth 6 ans)))
                        (progn
                          (princ (strcat "\nNo circle can be tangent to the"
                                         " top of the envelope and touch"
                                         " both those sides from outside"
                                         " them.  Sides more alike (or"
                                         " larger) usually fix it.  Asking"
                                         " again."))
                          (setq pos (1- pos)))))
                   ((not (oasis:kidney-p (oasis:variant ans)))
                    (setq nests (oasis:right-nests (nth 2 ans) (nth 3 ans)
                                                   (nth 4 ans) (nth 5 ans)
                                                   (nth 6 ans) (nth 12 ans)
                                                   (oasis:variant ans)))
                    (if nests
                        (progn
                          (princ (strcat "\nThat right bulge and the " nests
                                         " bulge lie one inside the other, so no"
                                         " tangent radius can join them.  Asking"
                                         " again."))
                          (setq pos (1- pos))))))))))

     (setq prev (oasis:pv-clear prev)
           var  (oasis:variant ans) base (nth 1 ans)
           w    (nth 2 ans) h    (nth 3 ans)
           rl   (oasis:leftrad var (nth 3 ans) (nth 4 ans))
           rt   (nth 5 ans) rr (nth 6 ans)
           ftl  (nth 7 ans) ftr  (nth 8 ans) fbc (nth 9 ans)
           fbr  (nth 13 ans) off (nth 12 ans)
           arcs (oasis:solve w h rl rt rr ftl ftr fbc fbr off var))

     (if (not arcs)
         (progn
           (princ (strcat "\nOASIS: those radii do not make a closed outline"
                          " -- nothing drawn."))
           (command "_.UNDO" "_End")
           (setq undo-open nil)
           (cal:sysrestore))
         (progn
           (cal:osdown)
           (setq lt    (oasis:dashlt w h)
                 cbase (oasis:checkbase base w h))
           (setvar "CLAYER" oasis:*poollayer*)
           (setq ents (oasis:draw arcs base oasis:*poollayer*))
           (oasis:dimension arcs ents base w h oasis:*dimlayer*)
           (setq nchk (oasis:checkdraw arcs cbase w h lt))

           (princ (strcat "\nOASIS " *oasis-version* ": " (rtos w) " x "
                          (rtos h) " " (oasis:vlabel var)
                          (if (oasis:complex-p ans) " complex" "")
                          " oasis on layer " oasis:*poollayer* "."))
           (if (and off (/= off 0.0))
               (princ (strcat "\n  hump " (rtos (abs off)) " off centre to the "
                              (if (< off 0.0) "left" "right") ".")))
           (foreach a arcs
             (princ (strcat "\n  " (oasis:pad (nth 0 a) 14)
                            (if (oasis:line-p a)
                                (strcat "straight run, "
                                        (rtos (distance (nth 1 a) (nth 2 a))))
                                (strcat (cond ((not (nth 5 a)) "reverse R")
                                              ((oasis:nxt-p var) "lobe   R")
                                              ("bulge  R"))
                                        (rtos (nth 2 a))))
                            (cond ((nth 6 a) "")
                                  ((oasis:kidney-p var)
                                   "   (derived from the tangency)")
                                  (t "   (pinned by the envelope)")))))
           (princ (strcat "\n  " (itoa (+ 2 (length arcs)))
                          " dimensions on the pool in the " oasis:*dimstyle*
                          " style, and " (itoa nchk) " on the"))
           (princ (strcat "\n  check drawing beside it in " oasis:*crossstyle*
                          " -- all on layer " oasis:*dimlayer* "."))
           (foreach a (oasis:pinched arcs var)
             (princ (strcat "\nOASIS: the " a " bulge is pinched out -- the"
                            " two joiners either side of it"))
             (princ (strcat "\n       touch it at the same point, so it is a"
                            " point on the outline and"))
             (princ "\n       nothing is drawn for it."))
           (oasis:report-extents arcs w h)
           (oasis:report-crossings arcs)

           ;; and then, if it is wanted, the floor -- laid out on the
           ;; outline that has just been built, so every point of it can
           ;; be said exactly instead of picked at.  Still inside the
           ;; undo group: one U takes the pool and its bottom together.
           (cal:osup)
           (if (= "Yes" (cal:askkw
                          "Add the bottom of the pool (breaks and hopper)?"
                          "Yes No" "Yes/No" "No" nil))
               (setq gotbot (oasis:askbottom arcs w h base lt)))
           (cal:osdown)
           (cal:dimstyrestore)

           (command "_.UNDO" "_End")
           (setq undo-open nil)
           (cal:sysrestore)
           (foreach a gotbot (princ a))))))
  (princ))

(defun c:OASISVER ()
  (princ (strcat "\nOASIS " *oasis-version*))
  (princ))

(princ (strcat "\nOASIS " *oasis-version*
               " loaded.  Type OASIS to draw a continuous-tangent pool."))
(princ)


;;; ======================================================================
;;; >>> abcdef.lsp
;;; ======================================================================

;;; ==========================================================================
;;; abcdef.lsp  --  Locate measured points inside a rectangle and plot them
;;; --------------------------------------------------------------------------
;;; For AutoCAD 2018 and later (plain AutoLISP, no external libraries).
;;;
;;; Commands:  ABCDEF      read the sheet, place every point, report the fit
;;;            ABCDEFVER   print the loaded version
;;;
;;; SHARED BUILD: requires CALOFIN-LIB.lsp (load via CALOFIN-LOADER.lsp).
;;; Generic helpers live there under cal: - see STANDARDS.md.
;;;
;;; Points A B C D sit on the corners of a rectangle:
;;;
;;;        A --------- B         A = top-left      B = top-right
;;;        |           |         C = bottom-left   D = bottom-right
;;;        |           |
;;;        C --------- D         (C sits DIRECTLY BELOW A and D directly
;;;                               below B - the same "Z" reading order as
;;;                               the field sheet, NOT clockwise A-B-C-D)
;;;
;;; The command asks for the two rectangle dimensions A-B (width) and A-C
;;; (height), reads a spreadsheet with the columns
;;;
;;;     POINT NAME | DIST FROM A | DIST FROM B | DIST FROM C | DIST FROM D
;;;
;;; and works out where each named point has to be.  The corners are built
;;; square to the world axes and every one of the four angles is measured
;;; back off the drawn coordinates before anything is plotted, so the frame
;;; the points land in is a true 90-degree rectangle or the run stops.
;;;
;;; HOW MANY TAPES IT TAKES.  Two distances fix a point up to a mirror,
;;; three fix it outright, and the fourth is the cross-check.  A sheet
;;; rarely gives four clean ones, so the leniency is built in:
;;;
;;;   * a row with only TWO distances still plots - the two circles are
;;;     crossed exactly and the root that falls inside the rectangle is
;;;     taken (the mirror root is on the far side of a rectangle side)
;;;   * a row with THREE is least-squares fitted, sharing the leftover
;;;     error across all three
;;;   * a row with FOUR is fitted on all four; if that fit is poor and
;;;     leaving ONE tape out settles the other three, that tape is dropped
;;;     and the report names it
;;;
;;; What it will NOT do is drop a tape it cannot prove is the bad one.
;;; Three tapes that disagree give no evidence about which of them is
;;; wrong - every pair of them fits perfectly - so a poor 3-tape row keeps
;;; all three and is flagged instead of being quietly made to look exact.
;;;
;;; PLACEMENT METHOD, asked per run:
;;;   Auto      the rules above - all tapes, minus a provably bad one
;;;   Furthest  only the two supplied corners furthest apart (widest base)
;;;   Mean      every 2- and 3-tape subset solved, and the answers averaged
;;;   Least     least-squares over every supplied tape, nothing dropped
;;;
;;; CONFIDENCE.  Every point is reported with the number of tapes that
;;; actually placed it, which corners they were, any tape dropped, and a
;;; 0-99 confidence built from four measured things: redundancy, the
;;; leftover fit error, how far the answer moves when any one tape is taken
;;; away, and the angle the tapes cross at.  Nothing in it is a guess.
;;;
;;; INSIDE THE FRAME.  A surveyed pool point belongs inside the rectangle it
;;; was measured from.  A solution that lands outside is pulled back onto
;;; the frame, and the distance it had to be pulled is reported - a small
;;; snap is rounding, a large one means a tape or a dimension is wrong.
;;;
;;; WHAT IT DRAWS.  Each point is an "ab_pt" block on layer POINTS carrying
;;; its sheet label in the number attribute - the same thing a Leica import
;;; produces - so ABHD, CABHD, ABFIND, BPCALLOUT and LHD read this import
;;; with no conversion.  The run ends by offering ABHD the whole set, which
;;; is how a sheet of tape measurements becomes a pool perimeter.
;;;
;;; Distances are entered / stored as architectural feet-inches, e.g.
;;;     12'-3 1/2"      3 1/2"      0'-6"      5'-0 3/4"
;;;
;;; Should a sheet label its bottom corners the other way round (C =
;;; bottom-right, D = bottom-left), the import notices - the distances only
;;; fit the rectangle one way - swaps C and D to match, and says so.
;;;
;;; All geometry is created in inches (1 drawing unit = 1 inch).
;;; ==========================================================================

(vl-load-com)

;; Version banner, shown on load and in every run's output.  When plotted
;; points look wrong, FIRST check the drawing/command line shows the version
;; you think you loaded - two separate field failures turned out to be a
;; stale or hand-edited copy of this file still loaded in AutoCAD.
(setq *abcdef-version* "v5.2")

;;; --------------------------------------------------------------------------
;;;  Tunables
;;; --------------------------------------------------------------------------

;; Quarter-inch field data that was read and typed correctly fits a
;; rectangle well under a tenth of an inch.  These two numbers are where
;; "fits" stops and "check this" starts, in inches of RMS leftover error.
(setq abcdef:*fit-ok*  0.20)   ; at or under this, the tapes agree
(setq abcdef:*fit-bad* 0.50)   ; over this, the point is flagged CHECK

;; How far outside the rectangle a solved point may land and still be
;; treated as rounding to be snapped back, rather than a bad reading.
(setq abcdef:*edge-tol* 1.0)

(setq abcdef:*fuzz* 1e-9)      ; below this, two lengths are the same length

;;; --------------------------------------------------------------------------
;;;  String helpers
;;; --------------------------------------------------------------------------

;; Replace every occurrence of the single char OLD with NEW in S.
(defun abcdef:replace (s old new / out i c)
  (setq out "" i 1)
  (repeat (strlen s)
    (setq c (substr s i 1))
    (setq out (strcat out (if (= c old) new c)))
    (setq i (1+ i)))
  out)

;; Remove every occurrence of the single char CH from S.
(defun abcdef:strip (s ch)
  (abcdef:replace s ch ""))

;; Split S on spaces, returning a list of non-empty tokens.
(defun abcdef:tokens (s / out tok i c)
  (setq out '() tok "" i 1)
  (repeat (strlen s)
    (setq c (substr s i 1))
    (if (= c " ")
      (progn (if (/= tok "") (setq out (cons tok out))) (setq tok ""))
      (setq tok (strcat tok c)))
    (setq i (1+ i)))
  (if (/= tok "") (setq out (cons tok out)))
  (reverse out))

;;; --------------------------------------------------------------------------
;;;  Dirty-data cleanup helpers (OCR / hand-transcription noise)
;;;
;;;  Field measurements often come back mangled by scanning or re-typing:
;;;    20'_114"      really 20'-1/4"    ( _->-,  114 is 1/4 with / read as 1 )
;;;    1 1'-IO 1/2"  really 11'-10 1/2" ( stray space, I->1, O->0 )
;;;    39'- 8 314"   really 39'-8 3/4"  ( 314 is 3/4 with / read as 1 )
;;;    34'-4 1 /4"   really 34'-4 1/4"  ( fraction split by a stray space )
;;;  These helpers repair that noise deterministically before parsing, and
;;;  flag abcdef:*dirty* so the import can report what it changed.
;;; --------------------------------------------------------------------------

(setq abcdef:*dirty* nil)   ; set T whenever a value needed cleaning
(setq abcdef:*fixes* nil)   ; running list of cleanup / warning messages

;; True if S is one or more chars and every char is a digit 0-9.
(defun abcdef:alldigits (s / ok i a)
  (if (= (strlen s) 0)
    nil
    (progn
      (setq ok T i 1)
      (repeat (strlen s)
        (setq a (ascii (substr s i 1)))
        (if (or (< a 48) (> a 57)) (setq ok nil))
        (setq i (1+ i)))
      ok)))

;; Return the 1-character string for Unicode code point N, but ONLY when this
;; AutoCAD's (chr)/(ascii) round-trip cleanly to that exact point.  On builds
;; where (chr) wraps code points > 255 modulo 256 (some pre-2019 releases),
;; e.g. (chr 8242) -> "2", the round-trip fails and we return nil rather than
;; corrupt real digits.  Everything is caught so it can never raise on load/run.
(defun abcdef:safechr (n / r a)
  (setq r (vl-catch-all-apply 'chr (list n)))
  (if (or (vl-catch-all-error-p r) (/= (type r) 'STR) (/= (strlen r) 1))
    nil
    (progn
      (setq a (vl-catch-all-apply 'ascii (list r)))
      (if (and (not (vl-catch-all-error-p a)) (= a n)) r nil))))

;; True if S contains only characters a feet-inch value may legitimately hold
;; (digits, space, and  "  '  -  .  / ).  Anything else after scrubbing means a
;; genuinely corrupt cell we should flag rather than silently mis-read.
(defun abcdef:parseable-p (s / ok i a)
  (setq ok T i 1)
  (repeat (strlen s)
    (setq a (ascii (substr s i 1)))
    (if (not (or (and (>= a 48) (<= a 57))   ; 0-9
                 (= a 32) (= a 34) (= a 39)   ; space  "  '
                 (= a 45) (= a 46) (= a 47))) ; -  .  /
      (setq ok nil))
    (setq i (1+ i)))
  ok)

;; Character-level scrub of a raw cell: letter / underscore / dash look-alikes
;; and the "smart quote" glyphs Excel/Word insert.  No non-ASCII bytes are
;; embedded in this source (some AutoCAD builds refuse to load such files);
;; single-byte look-alikes use (chr), higher code points go through
;; abcdef:safechr so a build that can't represent them simply skips that pair:
;;   U+2019 ' / U+2032 prime -> '     U+201D " / U+2033 dbl prime -> "
;;   U+2013 en / U+2014 em dash and CP1252 bytes 150/151 -> -
;; These are high-confidence fixes and are NOT flagged as "needs verifying";
;; only the riskier repairs (fraction rebuild, apostrophe-as-1, split feet)
;; set abcdef:*dirty*.
(defun abcdef:scrub (raw / s q)
  (setq s raw)
  (setq s (abcdef:replace s "_" "-"))    ; underscore read for a dash
  (setq s (abcdef:replace s "O" "0"))    ; letter O -> zero
  (setq s (abcdef:replace s "o" "0"))
  (setq s (abcdef:replace s "I" "1"))    ; letter I / l / bar -> one
  (setq s (abcdef:replace s "l" "1"))
  (setq s (abcdef:replace s "|" "1"))
  (setq s (abcdef:replace s (chr 150) "-"))   ; CP1252 en dash byte
  (setq s (abcdef:replace s (chr 151) "-"))   ; CP1252 em dash byte
  (if (setq q (abcdef:safechr 8217)) (setq s (abcdef:replace s q "'")))
  (if (setq q (abcdef:safechr 8242)) (setq s (abcdef:replace s q "'")))
  (if (setq q (abcdef:safechr 8221)) (setq s (abcdef:replace s q "\"")))
  (if (setq q (abcdef:safechr 8243)) (setq s (abcdef:replace s q "\"")))
  (if (setq q (abcdef:safechr 8211)) (setq s (abcdef:replace s q "-")))
  (if (setq q (abcdef:safechr 8212)) (setq s (abcdef:replace s q "-")))
  s)

;; TOK is an all-digit run with no slash.  A fraction like 3/4 whose slash was
;; scanned as a 1 becomes 314; because that substitution keeps the length, a
;; valid inch fraction (den in 2..32, 0<num<den) has exactly one reconstruction.
;; Return "num/den" if one is found (scanning candidate slash positions left to
;; right), else nil.
(defun abcdef:defrac (tok / len k num den ni di best)
  (setq len (strlen tok) k 1 best nil)
  (while (and (<= k len) (null best))
    (if (= (substr tok k 1) "1")
      (progn
        (setq num (substr tok 1 (1- k))
              den (substr tok (1+ k)))
        (if (and (> (strlen num) 0) (> (strlen den) 0)
                 (abcdef:alldigits num) (abcdef:alldigits den))
          (progn
            (setq ni (atoi num) di (atoi den))
            (if (and (member di '(2 4 8 16 32)) (> ni 0) (< ni di))
              (setq best (strcat num "/" den)))))))
    (setq k (1+ k)))
  best)

;; A fraction OCR-split across tokens: "1 /4", "1/ 4" or "1 / 4" tokenises as
;; ("1" "/4"), ("1/" "4") or ("1" "/" "4"), and the broken "/x" piece would
;; otherwise contribute 0 (losing the fraction).  Re-join a token that starts
;; or ends with "/" with its neighbour so the value parses as a real fraction.
(defun abcdef:mergefrac (toks / out tok changed)
  (setq out '() changed nil)
  (while toks
    (setq tok (car toks) toks (cdr toks))
    (cond
      ;; "1/" + "4" -> re-queue "1/4" (also eats the middle of "1 / 4")
      ((and toks (= (substr tok (strlen tok) 1) "/"))
       (setq toks (cons (strcat tok (car toks)) (cdr toks)))
       (setq changed T))
      ;; "1" + "/4" -> "1/4"
      ((and out (> (strlen tok) 1) (= (substr tok 1 1) "/"))
       (setq out (cons (strcat (car out) tok) (cdr out)))
       (setq changed T))
      (T (setq out (cons tok out)))))
  (if changed (setq abcdef:*dirty* T))
  (reverse out))

;;; --------------------------------------------------------------------------
;;;  Feet-inch parser  ->  inches (real).  Returns nil for an empty OR corrupt
;;;  cell.  MAXD, when supplied, is the largest geometrically-possible distance
;;;  (the rectangle's diagonal); it lets the parser recover a foot mark that was
;;;  scanned as a digit and reject impossible values.
;;;
;;;  Accepts, e.g.:  12'-3 1/2"   3 1/2"   0'-6"   5'-0 3/4"   1/2"   18
;;;  and repairs the dirty forms field data comes back in:
;;;    28-7"         missing foot mark    -> 28'-7"   (dash separates ft/in)
;;;    101-10"       foot mark read as 1  -> 10'-10"  (needs MAXD to detect)
;;;    20'-7 114"    "/" read as 1        -> 20'-7 1/4"
;;;    34'-4 1 /4"   fraction split       -> 34'-4 1/4"
;;;    1 1'-IO 1/2"  split feet / O,I     -> 11'-10 1/2"
;;;  Only the non-obvious repairs set abcdef:*dirty* (for the change report).
;;; --------------------------------------------------------------------------

(defun abcdef:ftin->in (raw maxd / s neg feet ftstr rest inch p dp tok
                                    num den slash df val)
  (setq s (abcdef:scrub (cal:trim raw)))
  (cond
    ((= s "") nil)                              ; blank cell
    ((not (abcdef:parseable-p s))               ; corrupt char left over
     (setq abcdef:*dirty* T) nil)
    (T
      (setq neg nil)
      (if (= (substr s 1 1) "-") (setq neg T s (cal:trim (substr s 2))))
      ;; --- split feet from inches ----------------------------------------
      (setq p (vl-string-search "'" s))
      (cond
        (p                                      ; explicit foot mark
          (setq ftstr (cal:trim (substr s 1 p)))
          (if (vl-string-search " " ftstr) (setq abcdef:*dirty* T))
          (setq feet (atof (abcdef:strip ftstr " ")))
          (setq rest (cal:trim (substr s (+ p 2)))))
        ((setq dp (vl-string-search "-" s))     ; no ' but a dash: it is the
          (setq ftstr (abcdef:strip (cal:trim (substr s 1 dp)) " "))
          (if (vl-string-search " " (cal:trim (substr s 1 dp)))
            (setq abcdef:*dirty* T))            ; feet/inch separator
          (setq feet (atof ftstr))
          (setq rest (cal:trim (substr s (+ dp 2)))))
        (T (setq feet 0.0 ftstr "" rest s)))    ; inches only
      ;; --- clean the inch remainder --------------------------------------
      (if (= (substr rest 1 1) "-") (setq rest (cal:trim (substr rest 2))))
      (setq rest (abcdef:strip rest "\""))   ; drop inch marks
      (setq rest (abcdef:strip rest "'"))    ; and a trailing ' misused as one
      (setq rest (abcdef:replace rest "-" " "))
      (setq rest (cal:trim rest))
      ;; --- inches: sum whole-number and fraction tokens ------------------
      (setq inch 0.0)
      (foreach tok (abcdef:mergefrac (abcdef:tokens rest))
        ;; a slash-less all-digit run of 3+ digits is very likely a fraction
        ;; whose "/" was scanned as a "1" (114 -> 1/4); reconstruct it.
        (if (and (not (vl-string-search "/" tok))
                 (>= (strlen tok) 3)
                 (abcdef:alldigits tok)
                 (setq df (abcdef:defrac tok)))
          (setq tok df abcdef:*dirty* T))
        (setq slash (vl-string-search "/" tok))
        (if slash
          (progn
            (setq num (atof (substr tok 1 slash)))
            (setq den (atof (substr tok (+ slash 2))))
            (if (/= den 0.0) (setq inch (+ inch (/ num den)))))
          (setq inch (+ inch (atof tok)))))
      (setq val (+ (* feet 12.0) inch))
      ;; --- foot mark scanned as a "1" ------------------------------------
      ;; e.g. 10'-10" -> "101-10": with no real ' and a value past the
      ;; diagonal, a trailing 1 on the feet was the apostrophe; drop it.
      (if (and maxd (null p) (> val (* maxd 1.05))
               (> (strlen ftstr) 1)
               (= (substr ftstr (strlen ftstr) 1) "1"))
        (progn
          (setq feet (atof (substr ftstr 1 (1- (strlen ftstr))))
                val  (+ (* feet 12.0) inch)
                abcdef:*dirty* T)))
      (if neg (setq val (- val)))
      ;; --- final sanity: non-positive or still impossible -> unreadable --
      (if (or (<= val 0.0) (and maxd (> val (* maxd 1.1))))
        (progn (setq abcdef:*dirty* T) nil)
        val))))

;;; --------------------------------------------------------------------------
;;;  Format inches back to a feet-inch string (for the correction log), to the
;;;  nearest 1/32", reduced.  e.g. 476.75 -> 39'-8 3/4"
;;; --------------------------------------------------------------------------

(defun abcdef:in->ftin (v / neg feet whole frac n den ft s)
  (setq neg (< v 0.0) v (abs v))
  (setq n (fix (+ (* v 32.0) 0.5)))      ; total 1/32" units, rounded
  (setq feet (fix (/ n 384)))            ; 384 = 32*12
  (setq n (- n (* feet 384)))
  (setq whole (fix (/ n 32)))
  (setq n (- n (* whole 32)))            ; leftover 1/32 units, 0..31
  (setq den 32)
  (while (and (> n 0) (= (rem n 2) 0)) (setq n (/ n 2) den (/ den 2)))
  (setq s (strcat (itoa feet) "'-" (itoa whole)))
  (if (> n 0) (setq s (strcat s " " (itoa n) "/" (itoa den))))
  (setq s (strcat s "\""))
  (if neg (strcat "-" s) s))

;;; --------------------------------------------------------------------------
;;;  Multilateration
;;;
;;;  CORNERS : list of (x y) corner coordinates that have a distance
;;;  DISTS   : matching list of measured distances
;;;  Returns : (x y rms res1 res2 ...)  in the same local frame as CORNERS.
;;;
;;;  A linear (circle-difference) solution seeds a Gauss-Newton refinement
;;;  of  min  S( |P-Ci| - di )^2 , which is exactly "spread the rounding
;;;  error evenly over the distances".  Needs >= 2 corners; 3+ give a unique
;;;  fix.  With only 2, the frame centre is used as the seed so the interior
;;;  intersection is chosen.
;;; --------------------------------------------------------------------------

(defun abcdef:solve (corners dists cx cy / n x y i c d dx dy r jx jy f
                             saa sab sbb sac sbc a b cc det xr yr dr
                             jaa jab jbb ga gb ddx ddy res rms iter)
  (setq n (length corners))
  ;; ---- seed --------------------------------------------------------------
  (if (>= n 3)
    (progn                                   ; linear least squares seed
      (setq xr (car (car corners)) yr (cadr (car corners)) dr (car dists))
      (setq saa 0.0 sab 0.0 sbb 0.0 sac 0.0 sbc 0.0 i 1)
      (while (< i n)
        (setq c (nth i corners) d (nth i dists))
        (setq a (* 2.0 (- (car c) xr))
              b (* 2.0 (- (cadr c) yr))
              cc (- (- (+ (* (car c) (car c)) (* (cadr c) (cadr c)))
                       (+ (* xr xr) (* yr yr)))
                    (- (* d d) (* dr dr))))
        (setq saa (+ saa (* a a)) sab (+ sab (* a b)) sbb (+ sbb (* b b))
              sac (+ sac (* a cc)) sbc (+ sbc (* b cc)))
        (setq i (1+ i)))
      (setq det (- (* saa sbb) (* sab sab)))
      (if (> (abs det) 1e-9)
        (setq x (/ (- (* sac sbb) (* sbc sab)) det)
              y (/ (- (* saa sbc) (* sab sac)) det))
        (setq x cx y cy)))                    ; degenerate -> centre
    (setq x cx y cy))                         ; only 2 circles -> centre seed
  ;; ---- Gauss-Newton refinement ------------------------------------------
  (setq iter 0)
  (while (< iter 60)
    (setq jaa 0.0 jab 0.0 jbb 0.0 ga 0.0 gb 0.0 i 0)
    (while (< i n)
      (setq c (nth i corners) d (nth i dists))
      (setq dx (- x (car c)) dy (- y (cadr c)) r (sqrt (+ (* dx dx) (* dy dy))))
      (if (< r 1e-9) (setq r 1e-9))
      (setq jx (/ dx r) jy (/ dy r) f (- r d))
      (setq jaa (+ jaa (* jx jx)) jab (+ jab (* jx jy)) jbb (+ jbb (* jy jy))
            ga (+ ga (* jx f)) gb (+ gb (* jy f)))
      (setq i (1+ i)))
    (setq det (- (* jaa jbb) (* jab jab)))
    (if (< (abs det) 1e-12)
      (setq iter 60)                          ; singular -> stop
      (progn
        (setq ddx (/ (- (- (* ga jbb)) (- (* gb jab)))
                     det)
              ddy (/ (- (- (* jaa gb)) (- (* jab ga)))
                     det))
        ;; ddx = -(ga*jbb - gb*jab)/det ; ddy = -(jaa*gb - jab*ga)/det
        (setq x (+ x ddx) y (+ y ddy))
        (if (and (< (abs ddx) 1e-7) (< (abs ddy) 1e-7)) (setq iter 60))))
    (setq iter (1+ iter)))
  ;; ---- residuals ---------------------------------------------------------
  (setq res '() rms 0.0 i 0)
  (while (< i n)
    (setq c (nth i corners) d (nth i dists))
    (setq f (- (sqrt (+ (expt (- x (car c)) 2) (expt (- y (cadr c)) 2))) d))
    (setq res (cons f res) rms (+ rms (* f f)) i (1+ i)))
  (setq rms (sqrt (/ rms n)))
  (cons x (cons y (cons rms (reverse res)))))

;;; --------------------------------------------------------------------------
;;;  Where a point really is
;;;
;;;  Four tapes to four corners is one measurement more than the geometry
;;;  needs, and in field data that spare one is the whole point: it is what
;;;  turns "here is an answer" into "here is an answer, and here is how much
;;;  the readings argued about it".
;;;
;;;  A row therefore arrives as a small pile of possible answers - every
;;;  pair of tapes, every triple, and the all-four fit.  What follows builds
;;;  that pile, picks from it under the method the user chose, and scores
;;;  the pick.  A tape is only ever discarded on evidence (see abcdef:auto).
;;; --------------------------------------------------------------------------

;; Plain 2-D distance between two (x y ...) points.
(defun abcdef:d2p (p q)
  (sqrt (+ (expt (- (car q) (car p)) 2) (expt (- (cadr q) (cadr p)) 2))))

;; The points at distance RA from CA and RB from CB, as a list of one or
;; two (x y).
;;
;; Quarter-inch tapes routinely describe circles that miss each other, or
;; one that swallows the other, by a fraction of an inch.  Giving up on
;; those rows would throw away most of a real sheet, so instead the
;; shortfall is shared equally between the two radii until the circles just
;; touch, and the single touching point comes back.  Neither tape is called
;; the liar, which is the same principle the least-squares fit works on.
(defun abcdef:cc-int (ca ra cb rb / d ux uy m h2 h bx by gap)
  (setq d (abcdef:d2p ca cb))
  (if (< d abcdef:*fuzz*)
    nil                                  ; the same corner twice: no crossing
    (progn
      (setq ux (/ (- (car cb) (car ca)) d)
            uy (/ (- (cadr cb) (cadr ca)) d))
      (cond
        ((< (+ ra rb) d)                 ; circles fall short of each other
         (setq gap (- d (+ ra rb))
               ra  (+ ra (* 0.5 gap))
               rb  (+ rb (* 0.5 gap))))
        ((< d (abs (- ra rb)))           ; one circle inside the other
         (setq gap (- (abs (- ra rb)) d))
         (if (> ra rb)
           (setq ra (- ra (* 0.5 gap)) rb (+ rb (* 0.5 gap)))
           (setq ra (+ ra (* 0.5 gap)) rb (- rb (* 0.5 gap))))))
      (setq m  (/ (+ (* d d) (* ra ra) (- (* rb rb))) (* 2.0 d))
            h2 (- (* ra ra) (* m m)))
      (if (< h2 0.0) (setq h2 0.0))      ; only rounding can get here now
      (setq h  (sqrt h2)
            bx (+ (car ca) (* m ux))
            by (+ (cadr ca) (* m uy)))
      (if (< h abcdef:*fuzz*)
        (list (list bx by))
        (list (list (- bx (* h uy)) (+ by (* h ux)))
              (list (+ bx (* h uy)) (- by (* h ux))))))))

;; T when (X Y) is inside RECT - (xmin ymin xmax ymax) - allowing TOL of
;; slop on every side.
(defun abcdef:inside-p (x y rect tol)
  (and (>= x (- (nth 0 rect) tol)) (<= x (+ (nth 2 rect) tol))
       (>= y (- (nth 1 rect) tol)) (<= y (+ (nth 3 rect) tol))))

;; (X Y SNAP) with X Y pulled back onto RECT and SNAP the distance moved.
;; A point measured from four corners of a rectangle belongs inside it; a
;; solution that lands outside is at best rounding and at worst a bad tape,
;; and either way the snap distance is the size of the problem.
(defun abcdef:clamp-in (x y rect / cx cy)
  (setq cx (max (nth 0 rect) (min (nth 2 rect) x))
        cy (max (nth 1 rect) (min (nth 3 rect) y)))
  (list cx cy (abcdef:d2p (list x y) (list cx cy))))

;; The angle in degrees, measured at (X Y), between the lines out to corners
;; CA and CB.  This is the "cut" of the two arcs: near 90 degrees they cross
;; cleanly and a quarter inch of tape error stays a quarter inch on the
;; ground, while near 0 or 180 they cross at a glance and that same quarter
;; inch walks the answer several inches along the crossing.  It is the
;; geometry, not the reading, that makes such a point weak - which is why
;; the confidence score has to see it.
(defun abcdef:cut-ang (x y ca cb / ux uy vx vy la lb dot)
  (setq ux (- (car ca) x) uy (- (cadr ca) y)
        vx (- (car cb) x) vy (- (cadr cb) y)
        la (sqrt (+ (* ux ux) (* uy uy)))
        lb (sqrt (+ (* vx vx) (* vy vy))))
  (if (or (< la abcdef:*fuzz*) (< lb abcdef:*fuzz*))
    0.0
    (progn
      (setq dot (/ (+ (* ux vx) (* uy vy)) (* la lb)))
      (if (> dot  1.0) (setq dot  1.0))
      (if (< dot -1.0) (setq dot -1.0))
      (* 180.0 (/ (atan (sqrt (- 1.0 (* dot dot))) dot) pi)))))

;; The widest cut angle any pair of the used tapes makes at (X Y) - the best
;; crossing the point actually had going for it.
(defun abcdef:best-cut (x y sub / best a i j n)
  (setq best 0.0 n (length sub) i 0)
  (while (< i n)
    (setq j (1+ i))
    (while (< j n)
      (setq a (abcdef:cut-ang x y (cadr (nth i sub)) (cadr (nth j sub))))
      (if (> a 90.0) (setq a (- 180.0 a)))   ; 170 deg cuts as badly as 10
      (if (> a best) (setq best a))
      (setq j (1+ j)))
    (setq i (1+ i)))
  best)

;;; --------------------------------------------------------------------------
;;;  Subsets of the tapes a row supplied
;;; --------------------------------------------------------------------------

;; One row's measured tapes as (INDEX CORNER DIST) triples - index 0-3 for
;; A B C D - with the blank cells left out.  Everything downstream works on
;; these triples, so a row that gave two tapes and a row that gave four take
;; exactly the same path.
(defun abcdef:avail (din pts / out i)
  (setq out '() i 0)
  (repeat 4
    (if (nth i din)
      (setq out (cons (list i (nth i pts) (nth i din)) out)))
    (setq i (1+ i)))
  (reverse out))

;; Every K-element subset of LST, order preserved.  K is 2 or 3 and LST
;; never holds more than four tapes, so the plain recursion is cheap.
(defun abcdef:subsets (lst k)
  (cond ((= k 0) (list '()))
        ((null lst) '())
        (T (append
             (mapcar '(lambda (s) (cons (car lst) s))
                     (abcdef:subsets (cdr lst) (1- k)))
             (abcdef:subsets (cdr lst) k)))))

;; The triples of AV that SUB left out.
(defun abcdef:missing (av sub / out e)
  (setq out nil)
  (foreach e av (if (not (member e sub)) (setq out (cons e out))))
  (if out (reverse out)))

;; "ABD" - the corner letters of a list of triples, in sheet order.
(defun abcdef:letters (sub / s e)
  (setq s "")
  (foreach e (list 0 1 2 3)
    (if (assoc e sub) (setq s (strcat s (nth e '("A" "B" "C" "D"))))))
  (if (= s "") "-" s))

;; Fit one subset of tapes: (X Y RMS RESIDUALS...) in the subset's order.
;;
;; Three or more tapes go to the least-squares fit, which shares the
;; leftover error over all of them.  Exactly two are crossed as circles and
;; the root inside the frame is taken - the mirror root of a pair measured
;; from two rectangle corners sits on the far side of a rectangle side, so
;; there is normally exactly one candidate inside, and the seed only breaks
;; a tie.  Two tapes cross-check nothing, so their RMS is reported as the
;; zero it genuinely is rather than as a fit anyone should be reassured by.
(defun abcdef:fit (sub rect seed / corners dists cands best bd p sc)
  (setq corners (mapcar 'cadr sub) dists (mapcar 'caddr sub))
  (cond
    ((>= (length sub) 3)
     (abcdef:solve corners dists (car seed) (cadr seed)))
    ((= (length sub) 2)
     (setq cands (abcdef:cc-int (nth 0 corners) (nth 0 dists)
                                (nth 1 corners) (nth 1 dists)))
     (if (null cands)
       nil
       (progn
         (setq best nil bd nil)
         (foreach p cands
           (setq sc (+ (if (abcdef:inside-p (car p) (cadr p) rect
                                            abcdef:*edge-tol*)
                         0.0 1.0e6)
                       (abcdef:d2p p seed)))
           (if (or (null bd) (< sc bd)) (setq bd sc best p)))
         (list (car best) (cadr best) 0.0 0.0 0.0))))
    (T nil)))

;; RMS of an already-chosen position against EVERY tape the row supplied.
;; Furthest and Mean place a point from part of the data; this scores that
;; point against all of it, so the four methods stay comparable and a tape
;; the method ignored still gets to object.
(defun abcdef:rms-at (av x y / s n e f)
  (setq s 0.0 n 0)
  (foreach e av
    (setq f (- (abcdef:d2p (list x y) (cadr e)) (caddr e))
          s (+ s (* f f))
          n (1+ n)))
  (if (> n 0) (sqrt (/ s n)) 0.0))

;; Signed leftover error against each tape of AV, in sheet order, for the
;; position (X Y).
(defun abcdef:resids (av x y / out e)
  (setq out '())
  (foreach e av
    (setq out (cons (cons (car e)
                          (- (abcdef:d2p (list x y) (cadr e)) (caddr e)))
                    out)))
  (reverse out))

;; How far the answer moves when any ONE tape of SUB is taken away.
;;
;; This is the disagreement between the tapes said where it matters - in
;; inches on the ground, rather than as a residual that has already been
;; averaged down.  nil for two tapes, because dropping one of those leaves
;; nothing to solve.
(defun abcdef:spread (sub rect seed pt / worst s f d)
  (if (< (length sub) 3)
    nil
    (progn
      (setq worst 0.0)
      (foreach s (abcdef:subsets sub (1- (length sub)))
        (setq f (abcdef:fit s rect seed))
        (if f
          (progn
            (setq d (abcdef:d2p pt (list (car f) (cadr f))))
            (if (> d worst) (setq worst d)))))
      worst)))

;;; --------------------------------------------------------------------------
;;;  The four placement methods
;;;
;;;  Each returns (FIT USED DROPPED), where FIT is what abcdef:fit returns,
;;;  USED the triples that placed the point and DROPPED the supplied ones
;;;  that did not - or nil when the row cannot be placed at all.
;;; --------------------------------------------------------------------------

;; Auto - every tape has a say, minus one that can be PROVEN wrong.
;;
;; With four tapes and a poor fit, leaving each one out in turn is a real
;; experiment: three tapes are still one more than the geometry needs, so if
;; removing a particular tape settles the other three, that tape was the bad
;; one and the evidence is the settling.  With three tapes there is no such
;; evidence - every pair of three fits perfectly, whichever pair you pick -
;; so a poor three-tape row keeps all three and is flagged.  Making it look
;; exact by dropping to a pair would be inventing confidence, which is the
;; one thing a report like this must never do.
;;
;; The experiment has to be DECISIVE as well as successful, and that is not
;; a formality.  A point sitting near a diagonal of the rectangle is barely
;; constrained along that diagonal: the two corners it lies between cross at
;; a glancing angle, so a wrong third tape can drag the answer six inches
;; along the diagonal and still leave a fit of a few hundredths.  Dropping
;; the tape with the lowest leftover error would then throw out a GOOD tape
;; and quietly move the point.  Seen from the numbers, the giveaway is that
;; the best and second-best triples fit equally well - the data cannot tell
;; which tape is wrong.  So a drop needs the runner-up to be clearly worse;
;; when it is not, every tape is kept and the point is graded down instead,
;; which is the same rule the three-tape case already follows.
(defun abcdef:auto (av rect seed / n f rms bs br nr best s trial)
  (setq n (length av) f (abcdef:fit av rect seed))
  (cond
    ((null f) nil)
    ((or (< n 4) (<= (caddr f) abcdef:*fit-ok*))
     (list f av nil))
    (T
     (setq rms (caddr f) bs nil br nil nr nil best nil)
     (foreach s (abcdef:subsets av 3)
       (setq trial (abcdef:fit s rect seed))
       (if trial
         (cond ((or (null br) (< (caddr trial) br))
                (setq nr br br (caddr trial) bs s best trial))
               ((or (null nr) (< (caddr trial) nr))
                (setq nr (caddr trial))))))
     (if (and bs
              (<= br abcdef:*fit-ok*)
              (< br (* 0.5 rms))
              nr
              (> nr (max (* 3.0 br) (+ br 0.25))))   ; the runner-up must lose
       (list best bs (abcdef:missing av bs))
       (list f av nil)))))

;; Furthest - only the two supplied corners furthest apart from each other.
;; On a rectangle that is a diagonal pair whenever both ends were measured,
;; which is the widest base the sheet can offer.
(defun abcdef:furthest (av rect seed / best bd p d f)
  (if (< (length av) 2)
    nil
    (progn
      (setq best nil bd nil)
      (foreach p (abcdef:subsets av 2)
        (setq d (abcdef:d2p (cadr (car p)) (cadr (cadr p))))
        (if (or (null bd) (> d bd)) (setq bd d best p)))
      (setq f (abcdef:fit best rect seed))
      (if f (list f best (abcdef:missing av best))))))

;; Mean - solve every 2- and 3-tape subset on its own and average the
;; answers.  No subset is trusted over any other, so a single bad tape is
;; diluted rather than removed; the report's spread column is what tells
;; you whether the answers being averaged agreed in the first place.
(defun abcdef:mean (av rect seed / subs s f sx sy n x y)
  (if (< (length av) 2)
    nil
    (progn
      (setq subs (abcdef:subsets av 2))
      (if (>= (length av) 3)
        (setq subs (append subs (abcdef:subsets av 3))))
      (setq sx 0.0 sy 0.0 n 0)
      (foreach s subs
        (setq f (abcdef:fit s rect seed))
        (if f (setq sx (+ sx (car f)) sy (+ sy (cadr f)) n (1+ n))))
      (if (= n 0)
        nil
        (progn
          (setq x (/ sx n) y (/ sy n))
          (list (list x y (abcdef:rms-at av x y)) av '()))))))

;; Least - least-squares over every tape supplied, nothing dropped.  This is
;; what every earlier revision of ABCDEF did, kept so an old plot can be
;; reproduced exactly.
(defun abcdef:least (av rect seed / f)
  (setq f (abcdef:fit av rect seed))
  (if f (list f av nil)))

;; Run one row under the chosen method.  Returns
;;   (X Y RMS USED DROPPED SPREAD CUT SNAP URMS)
;; or nil when the row has too little to place.
;;
;; RMS is scored against every tape the sheet gave, URMS against only the
;; tapes that placed the point, and the two are deliberately different
;; numbers.  A row whose bad tape was found and dropped should read as what
;; it is - a well-located point from a sheet with one bad reading in it - so
;; the report shows RMS, which still carries the dropped tape's objection,
;; while the confidence is built on URMS.  Scoring confidence on RMS instead
;; would punish a correctly repaired row exactly as hard as an unrepaired
;; one, leaving no way to tell the two apart in the column that exists to
;; tell them apart.
(defun abcdef:locate (av method rect seed / r f used dropped x y c sp cut)
  (setq r (cond ((= method "Furthest") (abcdef:furthest av rect seed))
                ((= method "Mean")     (abcdef:mean     av rect seed))
                ((= method "Least")    (abcdef:least    av rect seed))
                (T                     (abcdef:auto     av rect seed))))
  (if (null r)
    nil
    (progn
      (setq f (car r) used (cadr r) dropped (caddr r)
            x (car f) y (cadr f))
      ;; the frame has the last word on where a surveyed point can be
      (setq c (abcdef:clamp-in x y rect) x (car c) y (cadr c))
      (setq sp  (abcdef:spread used rect seed (list x y))
            cut (abcdef:best-cut x y used))
      (list x y (abcdef:rms-at av x y) used dropped sp cut (caddr c)
            (abcdef:rms-at used x y)))))

;;; --------------------------------------------------------------------------
;;;  Confidence
;;;
;;;  One number, 1-99, built only from things the sheet actually shows:
;;;
;;;    redundancy  how many tapes had a say.  Four cross-check three, three
;;;                cross-check two, a bare pair cross-checks nothing at all
;;;                and can be exactly wrong without ever looking it.
;;;    fit         the leftover error the tapes could not agree away (RMS).
;;;    spread      how far the answer moves when any one tape is dropped.
;;;    cut         the angle the best pair of tapes crosses at, at the
;;;                point - shallow crossings turn small tape errors into
;;;                large position errors.
;;;
;;;  A dropped tape costs a few points too: the row needed repairing, and a
;;;  repair is a judgement even when the evidence for it was good.
;;; --------------------------------------------------------------------------

(defun abcdef:confidence (used rms spread cut dropped / p)
  (setq p 100.0)
  (cond ((>= used 4) (setq p (- p  0.0)))
        ((= used 3)  (setq p (- p  8.0)))
        (T           (setq p (- p 26.0))))
  (setq p (- p (min 55.0 (* 110.0 rms))))
  (if spread (setq p (- p (min 20.0 (* 12.0 spread)))))
  (cond ((< cut 20.0) (setq p (- p 22.0)))
        ((< cut 35.0) (setq p (- p 10.0)))
        ((< cut 50.0) (setq p (- p  3.0))))
  (if dropped (setq p (- p 6.0)))
  (max 1.0 (min 99.0 p)))

;; The word that goes with a confidence number.
(defun abcdef:grade (pct)
  (cond ((>= pct 90.0) "HIGH")
        ((>= pct 75.0) "GOOD")
        ((>= pct 60.0) "FAIR")
        ((>= pct 40.0) "WEAK")
        (T             "POOR")))


;;; --------------------------------------------------------------------------
;;;  Drawing helpers
;;; --------------------------------------------------------------------------

;; Make sure a layer exists (create it with COLOR if not).
(defun abcdef:layer (name color)
  (if (not (tblsearch "LAYER" name))
    (entmake (list '(0 . "LAYER") '(100 . "AcDbSymbolTableRecord")
                   '(100 . "AcDbLayerTableRecord") (cons 2 name)
                   '(70 . 0) (cons 62 color) '(6 . "Continuous")))))

(defun abcdef:text (pt hgt str layer)
  (entmake (list '(0 . "TEXT") (cons 8 layer)
                 (cons 10 (list (car pt) (cadr pt) 0.0))
                 (cons 11 (list (car pt) (cadr pt) 0.0))
                 (cons 40 hgt) (cons 1 str) (cons 72 0) (cons 73 0))))

;; Closed 4-vertex polyline through P1 P2 P3 P4, given in PERIMETER order.
;; (With the Z corner naming the perimeter is A-B-D-C; passing A-B-C-D here
;; would draw a bow-tie, so callers hand in positions, not corner names.)
(defun abcdef:frame (p1 p2 p3 p4 layer)
  (entmake (list '(0 . "LWPOLYLINE") '(100 . "AcDbEntity") (cons 8 layer)
                 '(100 . "AcDbPolyline") '(90 . 4) '(70 . 1)
                 (cons 10 p1) (cons 10 p2) (cons 10 p3) (cons 10 p4))))

;;; --------------------------------------------------------------------------
;;;  Survey points the rest of the toolkit already understands
;;;
;;;  ABHD, CABHD, ADAB, ABFIND, BPCALLOUT and LHD all read a survey the same
;;;  way: an "ab_pt" block INSERT carrying its point number in an attribute,
;;;  or a plain POINT on layer POINTS.  Plotting into that block instead of
;;;  into private ABCDEF-POINTS markers is the whole reason this import can
;;;  become a pool perimeter without a conversion step in between - and it
;;;  is why nothing else drawn here goes on the POINTS layer.
;;; --------------------------------------------------------------------------

(setq abcdef:*point-layer* "POINTS")   ; where the survey points land
(setq abcdef:*point-block* "ab_pt")    ; the block every fitter reads
(setq abcdef:*point-tag*   "number")   ; its point-number attribute

;; Make sure ab_pt exists, building it the way the office template has it
;; when the drawing has never seen one.  (Same definition XFTCONV creates
;; for a Leica import, so a drawing can hold both without a clash.)
(defun abcdef:ensure-block (/ sty)
  (if (not (tblsearch "BLOCK" abcdef:*point-block*))
    (progn
      (setq sty (if (tblsearch "STYLE" "STANDARD")
                  "STANDARD"
                  (getvar "TEXTSTYLE")))
      (entmake (list '(0 . "BLOCK") '(100 . "AcDbEntity") '(8 . "0")
                     '(100 . "AcDbBlockBegin")
                     (cons 2 abcdef:*point-block*) '(70 . 2)
                     '(10 0.0 0.0 0.0)
                     (cons 3 abcdef:*point-block*) '(1 . "")))
      (entmake '((0 . "POINT") (100 . "AcDbEntity") (8 . "0")
                 (100 . "AcDbPoint") (10 0.0 0.0 0.0)))
      (entmake (list '(0 . "ATTDEF") '(100 . "AcDbEntity") '(8 . "0")
                     '(100 . "AcDbText") '(10 1.0 -2.0 0.0) '(40 . 1.0)
                     '(1 . "0") (cons 7 sty)
                     '(100 . "AcDbAttributeDefinition")
                     '(3 . "Type_Point_Number")
                     (cons 2 abcdef:*point-tag*) '(70 . 4)))
      (entmake '((0 . "ENDBLK") (100 . "AcDbEntity") (8 . "0")
                 (100 . "AcDbBlockEnd")))
      (princ (strcat "\n  block \"" abcdef:*point-block*
                     "\" was not in this drawing - created it."))))
  (tblsearch "BLOCK" abcdef:*point-block*))

;; One survey point: ab_pt at PT, its number attribute set to NAME, scaled
;; so the number reads at height TH.
(defun abcdef:insert-pt (pt name th)
  (entmake (list '(0 . "INSERT") '(100 . "AcDbEntity")
                 (cons 8 abcdef:*point-layer*)
                 '(100 . "AcDbBlockReference") '(66 . 1)
                 (cons 2 abcdef:*point-block*)
                 (list 10 (car pt) (cadr pt) 0.0)
                 (cons 41 th) (cons 42 th) (cons 43 th)))
  (entmake (list '(0 . "ATTRIB") '(100 . "AcDbEntity")
                 (cons 8 abcdef:*point-layer*) '(100 . "AcDbText")
                 (list 10 (+ (car pt) th) (- (cadr pt) (* 2.0 th)) 0.0)
                 (cons 40 th) (cons 1 name) '(100 . "AcDbAttribute")
                 (cons 2 abcdef:*point-tag*) '(70 . 0)))
  (entmake (list '(0 . "SEQEND") '(100 . "AcDbEntity")
                 (cons 8 abcdef:*point-layer*))))

;; Every ab_pt INSERT made since MARK (the entlast taken before plotting
;; began, or nil for an empty drawing), as a selection set.
;;
;; Walking forward from a mark is what keeps a second import in the same
;; drawing honest: an "_X" filter on the block name would sweep up the
;; previous survey too and hand ABHD two pools at once.
(defun abcdef:new-points (mark / ss e ed)
  (setq ss (ssadd) e (if mark (entnext mark) (entnext)))
  (while e
    (setq ed (entget e))
    (if (and (= (cdr (assoc 0 ed)) "INSERT")
             (= (strcase (cdr (assoc 2 ed))) (strcase abcdef:*point-block*)))
      (ssadd e ss))
    (setq e (entnext e)))
  ss)

;;; --------------------------------------------------------------------------
;;;  Excel reading (via COM automation)
;;;
;;;  Returns a list of rows, each  (name dA dB dC dD)  where any dX is a real
;;;  (inches) or nil when that cell was blank.  Column order is discovered
;;;  from the header row, so the sheet's columns may be in any order as long
;;;  as the headers contain NAME / FROM A / FROM B / FROM C / FROM D.
;;; --------------------------------------------------------------------------

;; Coerce a COM cell value to a trimmed string.
(defun abcdef:cellstr (v)
  (cond ((null v) "")
        ((= (type v) 'STR) (cal:trim v))
        ((= (type v) 'REAL) (cal:trim (rtos v 2 6)))
        ((= (type v) 'INT) (itoa v))
        (T "")))

(defun abcdef:xl-cell (sheet r c / res)
  (setq res (vl-catch-all-apply
              '(lambda ()
                 (vlax-variant-value
                   (vlax-get-property
                     (vlax-get-property
                       (vlax-get-property sheet "Cells") "Item" r c)
                     "Text")))))
  (if (vl-catch-all-error-p res) "" (abcdef:cellstr res)))

;; Classify a header cell (already upper-cased) as 'name / 'a / 'b / 'c / 'd.
(defun abcdef:col-of (up)
  (cond ((vl-string-search "FROM A" up) 'a)
        ((vl-string-search "FROM B" up) 'b)
        ((vl-string-search "FROM C" up) 'c)
        ((vl-string-search "FROM D" up) 'd)
        ((or (vl-string-search "NAME" up) (vl-string-search "POINT" up)
             (vl-string-search "LABEL" up)) 'name)
        (T nil)))

;; nth (1-based) element of a list, or "" when the index is nil / out of range.
(defun abcdef:nth-field (lst idx)
  (if (and idx (> idx 0) (<= idx (length lst))) (nth (1- idx) lst) ""))

;; Print the accumulated cleanup / unreadable report (if any).
(defun abcdef:report-fixes (/ m)
  (if abcdef:*fixes*
    (progn
      (princ "\n\n--- dirty values cleaned before import ---")
      (foreach m (reverse abcdef:*fixes*) (princ (strcat "\n" m)))
      (princ "\n  ( * = auto-corrected, ? = unreadable. Verify these! )"))))

;; Parse RAW to inches, logging into abcdef:*fixes* if the value had to be
;; cleaned up (a risky repair) or could not be read at all.  LABEL identifies
;; the cell in the log, e.g. "P3 / FROM C".  MAXD is the rectangle diagonal.
(defun abcdef:parse-log (raw label maxd / clean v)
  (setq clean (cal:trim raw))
  (if (= clean "")
    nil                                     ; blank cell: not measured
    (progn
      (setq abcdef:*dirty* nil)
      (setq v (abcdef:ftin->in raw maxd))
      (cond
        ((null v)                           ; nonblank but unreadable
         (setq abcdef:*fixes*
               (cons (strcat "  ? " label ": \"" clean
                             "\"  could not be read - left blank")
                     abcdef:*fixes*)))
        (abcdef:*dirty*                     ; cleaned something up
         (setq abcdef:*fixes*
               (cons (strcat "  * " label ": \"" clean "\"  ->  "
                             (abcdef:in->ftin v))
                     abcdef:*fixes*))))
      v)))

;;; --------------------------------------------------------------------------
;;;  Native CSV reading (no Excel needed).  Preferred for .csv because it also
;;;  avoids Excel silently turning cells like "28-11" or "7-0" into dates.
;;; --------------------------------------------------------------------------

;; Split one CSV line into a list of field strings, honouring "quoted" fields
;; and "" escaped quotes.
(defun abcdef:parse-csv-line (line / fields cur i n c inq)
  (setq fields '() cur "" i 1 n (strlen line))
  ;; state: inq = inside a quoted field
  (setq inq nil)
  (while (<= i n)
    (setq c (substr line i 1))
    (cond
      (inq
        (if (= c "\"")
          (if (= (substr line (1+ i) 1) "\"")   ; "" -> literal quote
            (progn (setq cur (strcat cur "\"")) (setq i (1+ i)))
            (setq inq nil))
          (setq cur (strcat cur c))))
      ((= c "\"") (setq inq T))
      ((= c ",") (setq fields (cons cur fields) cur ""))
      (T (setq cur (strcat cur c))))
    (setq i (1+ i)))
  (setq fields (cons cur fields))
  (reverse fields))

(defun abcdef:read-csv (file maxd / fp line fields i h up kind
                                    name-c a-c b-c c-c d-c rows nm)
  (setq fp (open file "r"))
  (if (null fp)
    (progn (princ "\n** Could not open the file for reading.") nil)
    (progn
      (setq name-c nil a-c nil b-c nil c-c nil d-c nil)
      ;; --- header row (skip any leading blank lines) --------------------
      (setq line (read-line fp))
      (while (and line (= (cal:trim (abcdef:strip line (chr 13))) ""))
        (setq line (read-line fp)))
      (if line
        (progn
          (setq fields (abcdef:parse-csv-line (abcdef:strip line (chr 13))) i 1)
          (foreach h fields
            (setq up (strcase (cal:trim h)) kind (abcdef:col-of up))
            (cond ((and (eq kind 'name) (null name-c)) (setq name-c i))
                  ((eq kind 'a) (setq a-c i))
                  ((eq kind 'b) (setq b-c i))
                  ((eq kind 'c) (setq c-c i))
                  ((eq kind 'd) (setq d-c i)))
            (setq i (1+ i)))))
      (if (null name-c) (setq name-c 1))     ; fall back to first column
      ;; --- data rows -----------------------------------------------------
      (setq rows '() abcdef:*fixes* '())
      (while (setq line (read-line fp))
        (setq line (abcdef:strip line (chr 13)))
        (if (/= (cal:trim line) "")
          (progn
            (setq fields (abcdef:parse-csv-line line))
            (setq nm (cal:trim (abcdef:nth-field fields name-c)))
            (if (/= nm "")
              (setq rows
                (cons (list nm
                    (abcdef:parse-log (abcdef:nth-field fields a-c)
                                      (strcat nm " / FROM A") maxd)
                    (abcdef:parse-log (abcdef:nth-field fields b-c)
                                      (strcat nm " / FROM B") maxd)
                    (abcdef:parse-log (abcdef:nth-field fields c-c)
                                      (strcat nm " / FROM C") maxd)
                    (abcdef:parse-log (abcdef:nth-field fields d-c)
                                      (strcat nm " / FROM D") maxd))
                      rows))))))
      (close fp)
      (abcdef:report-fixes)
      (reverse rows))))

;;; --------------------------------------------------------------------------
;;;  Dispatcher: pick the CSV reader for .csv, else Excel COM automation.
;;; --------------------------------------------------------------------------
(defun abcdef:read-file (file maxd / ext n)
  (setq n (strlen file) ext "")
  (if (> n 4) (setq ext (strcase (substr file (- n 3)))))
  (if (= ext ".CSV")
    (abcdef:read-csv file maxd)
    (abcdef:read-excel file maxd)))

(defun abcdef:read-excel (file maxd / xl created wbs wb sheet used rng nrows ncols
                                  hdr r c txt up kind name-c a-c b-c d-c c-c
                                  rows nm da db dc dd err m)
  ;; connect to an existing Excel, else start one
  (setq xl (vl-catch-all-apply 'vlax-get-object (list "Excel.Application")))
  (if (vl-catch-all-error-p xl)
    (progn (setq xl (vlax-create-object "Excel.Application") created T)))
  (if (or (null xl) (vl-catch-all-error-p xl))
    (progn (princ "\n** Could not start Excel (is it installed?).") nil)
    (progn
      (vl-catch-all-apply '(lambda () (vlax-put-property xl "Visible" :vlax-false)))
      (vl-catch-all-apply '(lambda () (vlax-put-property xl "DisplayAlerts" :vlax-false)))
      (setq err (vl-catch-all-apply
                  '(lambda ()
                     (setq wbs (vlax-get-property xl "Workbooks"))
                     (setq wb (vlax-invoke-method wbs "Open" file))
                     (setq sheet (vlax-get-property wb "ActiveSheet"))
                     (setq used (vlax-get-property sheet "UsedRange"))
                     ;; widen columns so "Text" is never truncated to ####
                     (vl-catch-all-apply
                       '(lambda () (vlax-invoke-method
                                     (vlax-get-property used "Columns") "AutoFit")))
                     (setq nrows (vlax-get-property
                                   (vlax-get-property used "Rows") "Count"))
                     (setq ncols (vlax-get-property
                                   (vlax-get-property used "Columns") "Count")))))
      (if (vl-catch-all-error-p err)
        (progn
          (princ (strcat "\n** Could not open the spreadsheet: "
                         (vl-catch-all-error-message err)))
          (if created (vl-catch-all-apply '(lambda () (vlax-invoke-method xl "Quit"))))
          nil)
        (progn
          ;; --- locate columns from the header row ------------------------
          (setq name-c nil a-c nil b-c nil c-c nil d-c nil c 1)
          (while (<= c ncols)
            (setq up (strcase (abcdef:xl-cell sheet 1 c)) kind (abcdef:col-of up))
            (cond ((and (eq kind 'name) (null name-c)) (setq name-c c))
                  ((eq kind 'a) (setq a-c c))
                  ((eq kind 'b) (setq b-c c))
                  ((eq kind 'c) (setq c-c c))
                  ((eq kind 'd) (setq d-c c)))
            (setq c (1+ c)))
          (if (null name-c) (setq name-c 1))   ; fall back to first column
          ;; --- read the data rows ----------------------------------------
          (setq rows '() abcdef:*fixes* '() r 2)
          (while (<= r nrows)
            (setq nm (abcdef:xl-cell sheet r name-c))
            (if (/= nm "")
              (setq rows
                (cons (list nm
                    (if a-c (abcdef:parse-log (abcdef:xl-cell sheet r a-c)
                                              (strcat nm " / FROM A") maxd))
                    (if b-c (abcdef:parse-log (abcdef:xl-cell sheet r b-c)
                                              (strcat nm " / FROM B") maxd))
                    (if c-c (abcdef:parse-log (abcdef:xl-cell sheet r c-c)
                                              (strcat nm " / FROM C") maxd))
                    (if d-c (abcdef:parse-log (abcdef:xl-cell sheet r d-c)
                                              (strcat nm " / FROM D") maxd)))
                      rows)))
            (setq r (1+ r)))
          (abcdef:report-fixes)
          ;; --- close up --------------------------------------------------
          (vl-catch-all-apply '(lambda () (vlax-invoke-method wb "Close" :vlax-false)))
          (if created (vl-catch-all-apply '(lambda () (vlax-invoke-method xl "Quit"))))
          (vl-catch-all-apply '(lambda () (vlax-release-object wb)))
          (vl-catch-all-apply '(lambda () (vlax-release-object wbs)))
          (vl-catch-all-apply '(lambda () (vlax-release-object xl)))
          (reverse rows))))))

;;; --------------------------------------------------------------------------
;;;  Prompt helper: read a feet-inch dimension from the keyboard.
;;; --------------------------------------------------------------------------

;; With BACK non-nil, typing B (Back; Undo works too) returns the
;; symbol AB-BACK so the caller can re-open its previous question.
;;; --------------------------------------------------------------------------
;;;  Asking
;;; --------------------------------------------------------------------------

;; Keyword question in the house format (STANDARDS.md section 1): the
;; bracket text is built from the keyword list so the two cannot drift, and
;; Back / Undo come back as the symbol AB-BACK.
(defun abcdef:askkw (msg kws shown dflt back / v)
  (initget (if dflt 0 (if back 0 1))
           (if back (strcat kws " Back Undo") kws))
  (setq v (getkword (strcat "\n" msg " [" shown
                            (if back "/Back" "") "]"
                            (if dflt (strcat " <" dflt ">") "") ": ")))
  (cond ((member v '("Back" "Undo")) 'AB-BACK)
        ((null v) (if dflt dflt (abcdef:askkw msg kws shown dflt back)))
        (T v)))

(defun abcdef:getdim (prompt back / s v)
  (setq v nil)
  (while (null v)
    (setq s (getstring T (strcat "\n" prompt " (e.g. 20'-6\""
                                 (if back ", B = back" "") "): ")))
    (cond
      ((and back (member (strcase s) '("B" "BACK" "U" "UNDO")))
       (setq v 'AB-BACK))
      (T
       (setq v (abcdef:ftin->in s nil))
       (if (or (null v) (<= v 0.0))
         (progn (princ "  ** enter a positive dimension, e.g. 20'-6\"")
                (setq v nil))))))
  v)

;;; --------------------------------------------------------------------------
;;;  Row geometry helpers
;;; --------------------------------------------------------------------------

;; Build (corners dists) for a row's non-blank distances.  DIN is the row's
;; (dA dB dC dD); PA PB PC PD are the matching corner points as (x y) lists.
(defun abcdef:row-geom (din pa pb pc pd / corners dists)
  (setq corners '() dists '())
  (if (nth 0 din) (setq corners (cons pa corners) dists (cons (nth 0 din) dists)))
  (if (nth 1 din) (setq corners (cons pb corners) dists (cons (nth 1 din) dists)))
  (if (nth 2 din) (setq corners (cons pc corners) dists (cons (nth 2 din) dists)))
  (if (nth 3 din) (setq corners (cons pd corners) dists (cons (nth 3 din) dists)))
  (list (reverse corners) (reverse dists)))

;; RMS fit error of one row solved against the given corner points, or nil
;; when the row has fewer than 2 distances.  CX CY seed the solver.
(defun abcdef:row-rms (din pa pb pc pd cx cy / g)
  (setq g (abcdef:row-geom din pa pb pc pd))
  (if (>= (length (car g)) 2)
    (caddr (abcdef:solve (car g) (cadr g) cx cy))))

;; Verify the named corner variables really form the W x H rectangle they
;; are documented to be: A-B and C-D horizontal sides of length W, A-C and
;; B-D vertical sides of length H, and matching diagonals.  Returns nil when
;; everything is right, else a message naming the first bad measurement.
;; This exists because two field failures traced back to a stale or
;; hand-edited copy of this file whose corner block no longer matched the
;; solver's assumptions - cheap to test on every run, loud when wrong.
(defun abcdef:frame-check (ax ay bx by cx cy dx dy w h / dg chk d bad)
  (setq dg (sqrt (+ (* w w) (* h h))) bad nil)
  (foreach chk (list (list "A-B" ax ay bx by w)
                     (list "C-D" cx cy dx dy w)
                     (list "A-C" ax ay cx cy h)
                     (list "B-D" bx by dx dy h)
                     (list "A-D (diagonal)" ax ay dx dy dg)
                     (list "B-C (diagonal)" bx by cx cy dg))
    (setq d (sqrt (+ (expt (- (nth 3 chk) (nth 1 chk)) 2)
                     (expt (- (nth 4 chk) (nth 2 chk)) 2))))
    (if (and (null bad) (> (abs (- d (nth 5 chk))) 0.001))
      (setq bad (strcat (car chk) " measures " (rtos d 2 2)
                        "\" but should be " (rtos (nth 5 chk) 2 2) "\""))))
  bad)

;; Interior angle in degrees at corner (px py), looking toward (qx qy) and
;; (rx ry).  Measured from the coordinates, NOT assumed - this is what lets
;; the command report honestly that the frame it drew has square corners.
(defun abcdef:corner-ang (px py qx qy rx ry / ux uy vx vy cross dot)
  (setq ux (- qx px) uy (- qy py) vx (- rx px) vy (- ry py))
  (setq cross (- (* ux vy) (* uy vx)) dot (+ (* ux vx) (* uy vy)))
  (if (and (< (abs cross) 1e-12) (< (abs dot) 1e-12))
    0.0
    (* 180.0 (/ (atan (abs cross) dot) pi))))

;;; --------------------------------------------------------------------------
;;;  The report file
;;;
;;;  The command line report scrolls away, and the numbers behind a plot are
;;;  exactly what gets argued about a week later.  So the same report is
;;;  written to a text file beside the spreadsheet it came from.
;;; --------------------------------------------------------------------------

;; Push one report line onto the accumulating list (newest first).
(defun abcdef:say (rep line)
  (cons line rep))

;; SHEET with its extension replaced by SUFFIX.
(defun abcdef:sibling (sheet suffix / n i cut)
  (setq n (strlen sheet) i n cut nil)
  (while (and (> i 0) (null cut))
    (cond ((= (substr sheet i 1) ".") (setq cut i))
          ((member (substr sheet i 1) '("\\" "/")) (setq i 1)))
    (setq i (1- i)))
  (strcat (if cut (substr sheet 1 (1- cut)) sheet) suffix))

;; Write LINES (newest first, as they were accumulated) to a text file
;; beside SHEET.  Returns the path written, or nil - a report that cannot
;; be saved is worth a note, never worth losing the plot over.
(defun abcdef:write-report (sheet lines / path fp ln)
  (setq path (abcdef:sibling sheet "_ABCDEF_report.txt"))
  (setq fp (vl-catch-all-apply 'open (list path "w")))
  (if (or (vl-catch-all-error-p fp) (null fp))
    nil
    (progn
      (foreach ln (reverse lines) (write-line ln fp))
      (close fp)
      path)))

;;; --------------------------------------------------------------------------
;;;  Handing the survey on to the perimeter fitter
;;; --------------------------------------------------------------------------

;; Pre-select the points just plotted and start ABHD on them.  ABHD reads
;; ab_pt blocks, which is what was drawn, so nothing is converted here - the
;; selection is simply put in front of it and it asks its own questions.
;;
;; ABHD lives in its own file.  Loaded as part of the calofin build it is
;; already here; APPLOADed on its own, abcdef.lsp has no business pretending
;; otherwise, so the absence is reported rather than discovered at the
;; command line.
(defun abcdef:to-abhd (ss / n)
  (setq n (if ss (sslength ss) 0))
  (cond
    ((= n 0)
     (princ "\n  Nothing was plotted, so there is no survey to fit."))
    ((null (boundp 'c:ABHD))
     (princ (strcat "\n  ABHD is not loaded in this drawing, so the points"
                    "\n  were left ready for it instead: they are ab_pt"
                    "\n  blocks on layer " abcdef:*point-layer*
                    ".  APPLOAD abhd.lsp (or the"
                    "\n  whole LAZPASS.lsp build), then run ABHD and"
                    "\n  window the points.")))
    (T
     (princ (strcat "\n  Starting ABHD on the " (itoa n)
                    " point(s) just plotted ..."))
     (sssetfirst nil ss)
     (vl-cmdf "_.ABHD"))))

;;; --------------------------------------------------------------------------
;;;  Main command
;;; --------------------------------------------------------------------------

(defun c:ABCDEF (/ *error* undo-open file rows base bpx bpy W H method
                    Ax Ay Bx By Cx Cy Dx Dy th
                    good bad r nm din d k rr av loc x y rms used dropped
                    sp cut snap urms pct gr rect seed tags tg tx ty placed p
                    flag totn tots n3 swapcd tmp angs chk rstr rl
                    stage done mark ss rep line nby4 nby3 nby2 ndrop
                    nlow path)
  (vl-load-com)
  (princ (strcat "\nABCDEF " *abcdef-version*))
  ;; the plot is one undo group, so a cancelled run backs out with a
  ;; single U instead of one per entity; the group is only closed if it
  ;; was opened (STANDARDS section 5)
  (defun *error* (msg)
    (if undo-open (command "_.UNDO" "_End"))
    (setq undo-open nil)
    (if (and msg (not (wcmatch (strcase msg)
                               "*BREAK*,*CANCEL*,*QUIT*,*EXIT*")))
        (princ (strcat "\nABCDEF error: " msg)))
    (princ))
  (command "_.UNDO" "_Begin")
  (setq undo-open T)
  ;; ---- the questions, staged: Back (or Undo) at a later prompt
  ;; ---- re-opens the previous one, back to the file dialog itself
  (setq stage 1 done nil method "Auto")
  (while (not done)
    (cond
      ;; ---- get the spreadsheet ------------------------------------------
      ((= stage 1)
       (setq file (getfiled "Select points spreadsheet"
                            "" "xlsx;xls;xlsm;csv" 16))
       (if (null file)
         (setq done 'quit)
         (progn
           (princ "\n--- Rectangle A(top-left) B(top-right) C(bottom-left) D(bottom-right) ---")
           (setq stage 2))))
      ((= stage 2)
       (setq W (abcdef:getdim "Dimension A-B (width across the top)" T))
       (if (eq W 'AB-BACK) (setq stage 1) (setq stage 3)))
      ((= stage 3)
       (setq H (abcdef:getdim "Dimension A-C (height down the side)" T))
       (if (eq H 'AB-BACK) (setq stage 2) (setq stage 4)))
      ;; ---- how much of each row gets a say -------------------------------
      ((= stage 4)
       (setq method (abcdef:askkw "How should each point be placed?"
                                  "Auto Furthest Mean Least"
                                  "Auto/Furthest/Mean/Least" "Auto" T))
       (if (eq method 'AB-BACK) (setq stage 3) (setq stage 5)))
      ;; ---- where does corner A land? -------------------------------------
      ;; take the pick in WCS so the rectangle is built square to the world
      ;; axes even when the current UCS is rotated (entmake writes WCS).
      (T
       (initget "Back Undo")
       (setq base (getpoint "\nInsertion point for corner A <0,0> [Back]: "))
       (if (= (type base) 'STR) (setq stage 4) (setq done T)))))
  (if (eq done 'quit)
    (progn (princ "\nCancelled.") (princ))
    (progn
      (if base (setq base (trans base 1 0)) (setq base '(0.0 0.0 0.0)))
      (setq bpx (car base) bpy (cadr base))
      ;; Corner coordinates.  A-B runs across the top; C and D sit DIRECTLY
      ;; BELOW A and B (the sheet's "Z" order), so every side is horizontal
      ;; or vertical and all four corners are true right angles:
      ;;    A = (bx, by)       B = (bx+W, by)
      ;;    C = (bx, by-H)     D = (bx+W, by-H)
      (setq Ax bpx        Ay bpy
            Bx (+ bpx W)  By bpy
            Cx bpx        Cy (- bpy H)
            Dx (+ bpx W)  Dy (- bpy H))
      ;; ---- corner self-check ----------------------------------------------
      ;; refuse to plot anything if the corner variables above no longer form
      ;; the W x H rectangle (i.e. this file was edited or a stale copy is
      ;; loaded) - a wrong frame silently poisons every solved point.
      (setq chk (abcdef:frame-check Ax Ay Bx By Cx Cy Dx Dy W H))
      (if chk
        (progn
          (alert (strcat "ABCDEF " *abcdef-version*
                         " - corner layout self-check FAILED:\n\n" chk
                         "\n\nThe loaded copy of abcdef.lsp appears stale or"
                         "\nhand-edited.  Re-download lisp/abcdef/abcdef.lsp"
                         "\nand APPLOAD it again.  Nothing was drawn."))
          (princ (strcat "\n** ABORT - corner self-check failed: " chk))
          (princ))
        (progn
      ;; ---- read the sheet ------------------------------------------------
      ;; the rectangle diagonal is the largest distance any point can be from a
      ;; corner; pass it so the parser can spot a foot mark scanned as a digit
      ;; and reject impossible readings.
      (princ "\nReading spreadsheet ... ")
      (setq rows (abcdef:read-file file (sqrt (+ (* W W) (* H H)))))
      (if (null rows)
        (progn (princ "\nNo usable rows found - nothing plotted.") (princ))
        (progn
          (princ (strcat (itoa (length rows)) " row(s) found."))
          ;; ---- do the C / D columns match the corners we assumed? ---------
          ;; Some sheets label the bottom corners the other way round
          ;; (C = bottom-right, D = bottom-left).  The distances only fit the
          ;; rectangle under the labelling they were measured with, so solve
          ;; every 3+-distance row both ways; if swapping C and D fits
          ;; decisively better, adopt the swap and say so.
          (setq totn 0.0 tots 0.0 n3 0)
          (foreach r rows
            (setq din (cdr r) k 0)
            (foreach d din (if d (setq k (1+ k))))
            (if (>= k 3)
              (progn
                (setq rr (abcdef:row-rms din (list Ax Ay) (list Bx By)
                                         (list Cx Cy) (list Dx Dy)
                                         (+ bpx (/ W 2.0)) (- bpy (/ H 2.0))))
                (if rr (setq totn (+ totn rr)))
                (setq rr (abcdef:row-rms din (list Ax Ay) (list Bx By)
                                         (list Dx Dy) (list Cx Cy)
                                         (+ bpx (/ W 2.0)) (- bpy (/ H 2.0))))
                (if rr (setq tots (+ tots rr)))
                (setq n3 (1+ n3)))))
          (setq swapcd nil)
          (if (and (> n3 0)
                   (> totn (* 0.5 n3))        ; poor fit as labelled ...
                   (< tots (* 0.25 totn)))    ; ... and 4x better swapped
            (progn
              (setq swapcd T)
              (setq tmp Cx Cx Dx Dx tmp)
              (setq tmp Cy Cy Dy Dy tmp)
              (princ (strcat
                "\n\n  ** C/D NOTE: the distances fit the opposite bottom corners"
                "\n     far better (avg fit " (rtos (/ tots n3) 2 3)
                "\" swapped vs " (rtos (/ totn n3) 2 3) "\" as labelled)."
                "\n     This sheet labels C = bottom-RIGHT and D = bottom-LEFT;"
                "\n     C and D have been placed that way to match the data."))))
          (if (and (> n3 0) (> (if swapcd tots totn) (* 1.0 n3)))
            (progn
              (princ (strcat
                "\n\n  ** WARNING: the distances fit the rectangle poorly (avg fit "
                (rtos (/ (if swapcd tots totn) n3) 2 3)
                "\").  Check the A-B / A-C dimensions and the sheet values;"
                "\n     the confidence column below marks the worst points."))
              (alert (strcat
                "ABCDEF " *abcdef-version*
                ": the distances fit the rectangle POORLY\n(average fit error "
                (rtos (/ (if swapcd tots totn) n3) 2 2)
                "\" - quarter-inch data should fit under 0.10\").\n"
                "\nCheck the A-B / A-C dimensions you entered and the"
                "\nsheet's values.  Points ARE plotted, but the report"
                "\ngrades every one of them and flags the doubtful."))))
          ;; ---- layers & sizing --------------------------------------------
          (abcdef:layer "ABCDEF-FRAME"  1)     ; red
          (abcdef:layer "ABCDEF-WARN"   1)     ; red - notes on doubtful fits
          (abcdef:layer abcdef:*point-layer* 2) ; yellow - the survey itself
          (abcdef:ensure-block)
          (setq th (/ (max W H) 120.0))        ; text height
          (if (< th 0.5) (setq th 0.5))
          ;; ---- draw the rectangle + corner tags ---------------------------
          ;; perimeter order TL -> TR -> BR -> BL, by position (so the frame
          ;; stays a rectangle no matter which naming the sheet used).
          (abcdef:frame (list bpx bpy)
                        (list (+ bpx W) bpy)
                        (list (+ bpx W) (- bpy H))
                        (list bpx (- bpy H))
                        "ABCDEF-FRAME")
          ;; corner name tags, offset outward from whichever corner each
          ;; letter ended up on.
          (setq tags (list (list "A" Ax Ay) (list "B" Bx By)
                           (list "C" Cx Cy) (list "D" Dx Dy)))
          (foreach tg tags
            (setq tx (if (> (cadr tg)  (+ bpx (* 0.5 W))) th (* -1 th))
                  ty (if (> (caddr tg) (- bpy (* 0.5 H))) th (* -1.6 th)))
            (abcdef:text (list (+ (cadr tg) tx) (+ (caddr tg) ty))
                         (* th 1.4) (car tg) "ABCDEF-FRAME"))
          ;; ---- plot each measured point -----------------------------------
          ;; RECT is the frame every solution is held inside; SEED is its
          ;; middle, which is where an ambiguous two-tape crossing starts
          ;; looking from.  MARK is the drawing's last entity before any
          ;; point exists, so the ABHD handoff can pick out exactly the
          ;; points this run made.
          (setq rect (list bpx (- bpy H) (+ bpx W) bpy)
                seed (list (+ bpx (/ W 2.0)) (- bpy (/ H 2.0)))
                mark (entlast))
          (setq good 0 bad 0 placed '()
                nby4 0 nby3 0 nby2 0 ndrop 0 nlow 0)
          (foreach r rows
            (setq nm (car r) din (cdr r))
            (setq av (abcdef:avail din (list (list Ax Ay) (list Bx By)
                                             (list Cx Cy) (list Dx Dy))))
            (setq loc (if (>= (length av) 2)
                        (abcdef:locate av method rect seed)))
            (if loc
              (progn
                (setq x    (nth 0 loc) y       (nth 1 loc)
                      rms  (nth 2 loc) used    (nth 3 loc)
                      dropped (nth 4 loc)
                      sp   (nth 5 loc) cut     (nth 6 loc)
                      snap (nth 7 loc) urms    (nth 8 loc))
                (setq pct (abcdef:confidence (length used) urms sp cut dropped)
                      gr  (abcdef:grade pct))
                ;; signed leftover error against each supplied tape, in sheet
                ;; order A B C D ("--" = not measured) - what each tape still
                ;; disagrees with after the point was placed
                (setq rl (abcdef:resids av x y) rstr "")
                (foreach k '(0 1 2 3)
                  (setq rstr (strcat rstr
                    (cal:pad (if (assoc k rl)
                                  (abcdef:signres (cdr (assoc k rl)))
                                  "  --")
                                7))))
                (abcdef:insert-pt (list x y) nm th)
                ;; a doubtful point says so in the drawing too, not only in
                ;; the report that scrolls away
                (setq flag "")
                (if (> rms abcdef:*fit-bad*) (setq flag "  **CHECK"))
                (if (> snap 0.001)
                  (setq flag (strcat flag "  (snapped "
                                     (rtos snap 2 2) "\" into frame)")))
                (if dropped
                  (setq flag (strcat flag "  (dropped "
                                     (abcdef:letters dropped) ")")))
                ;; four tapes that argue, with no one of them provably the
                ;; liar, is a different problem from a bad reading and gets
                ;; said out loud rather than hidden behind the grade
                (if (and (null dropped) (= (length used) 4)
                         (> rms abcdef:*fit-ok*))
                  (setq flag (strcat flag "  (tapes disagree, none provably wrong)")))
                (if (or (> rms abcdef:*fit-bad*) (< pct 60.0)
                        (> snap abcdef:*edge-tol*))
                  (progn
                    (setq nlow (1+ nlow))
                    (abcdef:text (list (+ x (* th 0.6)) (+ y (* th 0.6)))
                                 th (strcat nm " " gr) "ABCDEF-WARN")))
                (cond ((>= (length used) 4) (setq nby4 (1+ nby4)))
                      ((= (length used) 3)  (setq nby3 (1+ nby3)))
                      (T                    (setq nby2 (1+ nby2))))
                (if dropped (setq ndrop (1+ ndrop)))
                (setq placed (cons (list nm x y (length used) (length av)
                                         (abcdef:letters used) rms sp cut
                                         pct gr flag rstr)
                                   placed))
                (setq good (1+ good)))
              (progn
                (princ (strcat "\n  ! " nm
                               " : fewer than 2 distances given - skipped."))
                (setq bad (1+ bad)))))
          ;; ---- report ------------------------------------------------------
          ;; built as a list of lines so the same text goes to the command
          ;; line and to the file beside the sheet
          (setq rep '())
          (setq rep (abcdef:say rep (strcat "===== ABCDEF " *abcdef-version*
                                            " results (inches) =====")))
          (setq rep (abcdef:say rep (strcat "  sheet  : " file)))
          (setq rep (abcdef:say rep (strcat "  method : " method)))
          (setq rep (abcdef:say rep (strcat "  frame  : " (rtos W 2 2)
                                            "\" (A-B) x " (rtos H 2 2)
                                            "\" (A-C)"
                                            (if swapcd
                                              ", C/D read swapped" ""))))
          (setq rep (abcdef:say rep ""))
          (setq rep (abcdef:say rep
            (strcat "  POINT            X          Y     TAPES  USED"
                    "   FIT     SPREAD  CUT    CONF"
                    "      err vs A      B      C      D")))
          (foreach p (reverse placed)
            (setq rep (abcdef:say rep (strcat
              "  " (cal:pad (nth 0 p) 14)
              (abcdef:padnum (nth 1 p) 10)
              (abcdef:padnum (nth 2 p) 11)
              "   " (itoa (nth 3 p)) " of " (itoa (nth 4 p))
              "  " (cal:pad (nth 5 p) 6)
              (cal:pad (strcat (rtos (nth 6 p) 2 3) "\"") 8)
              (cal:pad (if (nth 7 p)
                            (strcat (rtos (nth 7 p) 2 2) "\"") "   --") 8)
              (cal:pad (strcat (rtos (nth 8 p) 2 0) "d") 7)
              (cal:pad (strcat (rtos (nth 9 p) 2 0) "% " (nth 10 p)) 10)
              (nth 12 p) (nth 11 p)))))
          (setq rep (abcdef:say rep
            "-------------------------------------------------------------"))
          (setq rep (abcdef:say rep (strcat
            "  " (itoa good) " point(s) plotted"
            (if (> bad 0) (strcat ", " (itoa bad) " skipped (under 2 tapes)")
              "") ".")))
          (setq rep (abcdef:say rep (strcat
            "  placed by 4 tapes: " (itoa nby4)
            "   by 3: " (itoa nby3)
            "   by 2: " (itoa nby2)
            (if (> ndrop 0)
              (strcat "   (" (itoa ndrop) " with one tape dropped)") ""))))
          (setq rep (abcdef:say rep (strcat
            "  " (itoa nlow) " point(s) want checking"
            " (FIT over " (rtos abcdef:*fit-bad* 2 2)
            "\", confidence under 60%, or snapped over "
            (rtos abcdef:*edge-tol* 2 2) "\").")))
          (setq rep (abcdef:say rep ""))
          (setq rep (abcdef:say rep
            "  TAPES  how many of the four distances the sheet gave."))
          (setq rep (abcdef:say rep
            "  USED   which corners actually placed the point.  Under Auto a"))
          (setq rep (abcdef:say rep
            "         tape is only left out when four were given and leaving"))
          (setq rep (abcdef:say rep
            "         that one out settles the other three: three tapes that"))
          (setq rep (abcdef:say rep
            "         disagree never say which of them is the wrong one, so"))
          (setq rep (abcdef:say rep
            "         they are all kept and the point is graded down instead."))
          (setq rep (abcdef:say rep
            "  FIT    RMS leftover error against every tape the sheet gave."))
          (setq rep (abcdef:say rep
            "  SPREAD how far the point moves if any one tape is dropped."))
          (setq rep (abcdef:say rep
            "  CUT    angle the best pair of tapes crosses at, at the point."))
          (setq rep (abcdef:say rep
            "  CONF   all four of those together, 1-99%.  Two tapes cross-"))
          (setq rep (abcdef:say rep
            "         check nothing, so a 2-tape point is capped well short"))
          (setq rep (abcdef:say rep
            "         of certainty however neatly the circles crossed."))
          ;; ---- confirm the frame really is a rectangle --------------------
          ;; measure the corner angles from the coordinates that were drawn,
          ;; rather than asserting them - so a future corner-math regression
          ;; shows up right here instead of printing a reassuring constant.
          (setq angs (list
            (abcdef:corner-ang bpx bpy (+ bpx W) bpy bpx (- bpy H))
            (abcdef:corner-ang (+ bpx W) bpy bpx bpy (+ bpx W) (- bpy H))
            (abcdef:corner-ang (+ bpx W) (- bpy H) (+ bpx W) bpy bpx (- bpy H))
            (abcdef:corner-ang bpx (- bpy H) bpx bpy (+ bpx W) (- bpy H))))
          (setq rep (abcdef:say rep ""))
          (setq rep (abcdef:say rep (strcat
            "  Frame corner angles, measured off the drawn coordinates: "
            (rtos (nth 0 angs) 2 2) " / " (rtos (nth 1 angs) 2 2) " / "
            (rtos (nth 2 angs) 2 2) " / " (rtos (nth 3 angs) 2 2) " deg."
            "  Every point above is inside it.")))
          (foreach line (reverse rep) (princ (strcat "\n" line)))
          ;; ---- the same thing, on disk ------------------------------------
          (setq path (abcdef:write-report file rep))
          (princ (if path
                   (strcat "\n\n  Report saved: " path)
                   "\n\n  ** the report file could not be written (read-only folder?)"))
          ;; vl-catch-all-apply takes the argument list as its second argument;
          ;; called with only the lambda it raises "too few arguments" and
          ;; takes the end of the run down with it, which is exactly what
          ;; the catch was there to prevent.
          (vl-catch-all-apply
            '(lambda ()
               (vl-cmdf "_.plan" "_World")
               (vl-cmdf "_.zoom" "_Extents"))
            '())
          (princ "\n  View reset to plan (top).")
          ;; ---- on to the pool perimeter -----------------------------------
          (setq ss (abcdef:new-points mark))
          (princ (strcat "\n\n  The " (itoa good)
                         " point(s) are ab_pt blocks on layer "
                         abcdef:*point-layer* ", numbered from the sheet."))
          (if (and (> good 0)
                   (= "Yes" (abcdef:askkw
                              "Fit a pool perimeter through these points now?"
                              "Yes No" "Yes/No" "Yes" nil)))
            (abcdef:to-abhd ss)
            (princ "\n  Left as points - run ABHD (or CABHD) when ready."))
          (princ)))))))
  (if undo-open (command "_.UNDO" "_End"))
  (setq undo-open nil)
  (princ))

;; Print the loaded version.
(defun c:ABCDEFVER ()
  (princ (strcat "\nABCDEF " *abcdef-version* " (abcdef.lsp)"))
  (princ))


;; format a signed inches value like "+0.08" (sign always shown, 2 decimals)
(defun abcdef:signres (v)
  (strcat (if (< v 0.0) "-" "+") (rtos (abs v) 2 2)))

;; format a real to 3 decimals, left-padded into WIDTH
(defun abcdef:padnum (v width / s)
  (setq s (rtos v 2 3))
  (while (< (strlen s) width) (setq s (strcat " " s)))
  s)

(princ (strcat "\nABCDEF.lsp rev " *abcdef-version*
               " loaded.  Type ABCDEF to plot points from a spreadsheet."))
(princ)


;;; ======================================================================
;;; >>> ABFIND.lsp
;;; ======================================================================

;;; ======================================================================
;;; ABFIND.lsp  --  tie a survey point back to the A and B stakes
;;; ----------------------------------------------------------------------
;;; For AutoCAD 2018 and later (plain AutoLISP; needs the Visual LISP
;;; engine that ships with full AutoCAD -- LT cannot run this).
;;;
;;; Commands:  ABFIND      dimension Pt.## from A and from B, point
;;;                        after point until Enter - and offer to move
;;;                        each one before it asks for the next
;;;            ABMOVE      ONE point: the same two ties, and then every
;;;                        place it could sit if one of the two tapes
;;;                        was written down wrong; pick one, it moves,
;;;                        and the command is done
;;;            ABFINDVER   print the loaded version
;;; ======================================================================
;;;
;;; SHARED BUILD: requires CALOFIN-LIB.lsp (load via CALOFIN-LOADER.lsp).
;;; Generic helpers live there under cal: - see STANDARDS.md.
;;;
;;; A pool is surveyed off two stakes, A and B: every point on the sheet
;;; is two tape readings, one from each stake, and the point is wherever
;;; those two distances cross.  These two commands work that way round.
;;;
;;; ABFIND
;;;   Name a point -- type its number, or click the point itself: the
;;;   one prompt takes either.  Two aligned dimensions are drawn, A to
;;;   the point and B to the point -- the pair of readings the point was
;;;   plotted from -- in the "CROSS DIMENSIONS" dimension style, on the
;;;   "DIMENSION" layer, ByLayer, the dimension line sitting right on
;;;   the tie, exactly the convention CDCALLOUT and CDCREATE use.  It
;;;   keeps asking for the next point until you press Enter.  The
;;;   stakes are found by name.
;;;
;;; ABMOVE
;;;   ABFIND asks this itself, once its two ties are drawn:
;;;
;;;       Move Pt.17 to a different reading? [Yes/No] <No>:
;;;
;;;   Yes runs everything below, and when the point is settled ABFIND
;;;   asks for the next number as usual.  ABMOVE is the same flow
;;;   without the question -- it was typed to move a point, so it goes
;;;   straight to the readings and ends when that point is settled.
;;;
;;;   Either way: if this point is in the wrong place, where SHOULD it
;;;   be?  One tape
;;;   is held exactly as it is and the other's reading is varied, and
;;;   each pair of distances is crossed back to a position.  Two
;;;   families of reading are tried:
;;;
;;;     * THE FOOT SWEEP -- the moved tape a whole foot out, a foot at
;;;       a time, abf:*foot-steps* of them EACH WAY (10 up and 10 down
;;;       as shipped).  A foot is the unit a tape gets miscounted in,
;;;       so every foot within reach is worth seeing whether or not
;;;       the number looks like another one.
;;;     * THE LOOK-ALIKES -- a reading that could be read as this one:
;;;         the inches lost or gained a leading 1     1"  <->  11"
;;;         a digit read as its look-alike            21'-1" -> 21'-7"
;;;           (abf:*digit-pairs*: 1/7, 1/4, 3/8, 3/5, 5/6, 6/8, 0/9,
;;;           4/9, 7/9), in the inches or in the feet
;;;         two feet digits changed places            21' -> 12'
;;;
;;;   Both ways round, as two groups: the readings that move A (B
;;;   held), then the ones that move B.  Nothing further than
;;;   abf:*max-shift* (10 feet, the reach of the foot sweep) is
;;;   offered, and a reading the held tape can no longer reach has no
;;;   crossing and is left out.  A look-alike that lands on a whole
;;;   foot is already in the sweep and is not listed twice.
;;;
;;;   Every suggestion carries a TAG, which is both its label on screen
;;;   and the answer you type: the moved tape's letter after the number
;;;   of feet it moved -- 1A, 2A, -1A, -2A for the sweep on A, 1B, -1B
;;;   for the sweep on B -- or R1A, R2A for a look-alike reading of A
;;;   that is not a whole foot out, in the same nearest-first order.
;;;   The candidates are drawn on abf:*sug-layer* ("ABMOVE-POINTS") in
;;;   abf:*sug-color* (yellow) -- a layer of their OWN, never the
;;;   points layer.  They are throwaway, they would inherit the points
;;;   layer's colour, and while they existed every other tool in the
;;;   toolset would count them as real survey points.  They are listed
;;;   on the command line nearest miss first within each group: type a
;;;   tag, or Pick and click the marker you want.  The ONE that is
;;;   chosen is a survey point, and that is what goes on POINTS.
;;;
;;;   Each group also gets the line it sits on, dashed and grey: a
;;;   held tape is a fixed radius off its stake, so everything that
;;;   holds it lies on one arc centred there - through the point as it
;;;   is drawn now, and out to the furthest suggestion each way.  Two
;;;   arcs, then: one through all the A readings and one through all
;;;   the B readings, crossing at the point itself.  They are
;;;   scaffolding like the markers and go when the round does.
;;;
;;;   Picking one:
;;;     * the point is COPIED to there and numbered "17m" -- the
;;;       original number with abf:*moved-suffix* on it, so the drawing
;;;       says plainly that this one was moved.  A COPY: the same
;;;       block, the same layer, colour, linetype, lineweight, scale
;;;       and rotation, and every attribute it carries, each keeping
;;;       the offset it had -- only the number is different.  A survey
;;;       point is more than a position, and the moved one is the SAME
;;;       point one reading further on, so it has to read as one:
;;;       building a fresh point from this file's defaults threw the
;;;       drawing's own away.  Only a drawing whose point block is not
;;;       in its block table has nothing to copy, and that one falls
;;;       back to a POINT on the points layer with a text label beside
;;;       it,
;;;     * the ORIGINAL point is ringed with a 5" radius circle on the
;;;       FGStep layer, so the spot it came off is still visible,
;;;     * a note is written on FGStep reading
;;;
;;;           Moved Pt.17 B from 21'-1" to 21'-7"
;;;
;;;       naming the tape that moved -- the one that was NOT held --
;;;       and both of its readings, and
;;;     * the two dimensions are redrawn to where the point now is, so
;;;       the sheet measures the position it is claiming.  The old
;;;       reading is not lost: the note carries it.
;;;
;;;   None (the Enter answer) leaves the point alone and keeps the two
;;;   dimensions -- ABMOVE has then done exactly what ABFIND does.
;;;
;;;   For ABMOVE that is the end of the run: it settles ONE point and
;;;   stops -- run it again for the next one.  ABFIND carries on to the
;;;   next point number, and the point it has just made is a point like
;;;   any other from there: it can be named in a later round of the
;;;   same run.
;;;
;;; THE STAKES.  A and B are looked up by name among the survey points,
;;; the same way any other point is: an "ab_pt" INSERT anywhere or any
;;; other INSERT on the POINTS layer, named by its "number" attribute
;;; (the classifier BPCALLOUT, CDCALLOUT and LHD all share).  A drawing
;;; that does not name them asks you to click each one instead, once
;;; per run, snapping to the nearest survey point within abf:*snap*.
;;;
;;; NAMING THE POINT.  Type its number the way it reads in the drawing
;;; -- "35", "Pt.35", "pt 35", "#35" and "035" all name the same point
;;; -- or click the point on screen: the one prompt takes both, because
;;; (initget 128) hands typed text back from getpoint as the string it
;;; is while a click comes back as the point it is.  A click is snapped
;;; to the survey point within abf:*snap* of it, so it names a point
;;; exactly as a typed number does.  A number that names nothing, and a
;;; click with no survey point under it, are both reported and the
;;; prompt re-asks -- nothing is drawn from a typo or a stray click.
;;;
;;; Going back a step follows the shared Back convention (see the root
;;; README).  In ABFIND, B/BACK/U/UNDO typed at the point number undoes
;;; the whole of the last round -- its ties, and, if that round moved a
;;; point, the moved point, its ring and its note, with the original
;;; ties put back.  Back at "Move Pt.17?" un-draws that point's ties
;;; and re-asks the number; Back at the suggestions re-asks "Move
;;; Pt.17?"; Back at the note re-asks the suggestion.  ABMOVE is the
;;; same minus its own question: Back at the suggestions re-asks the
;;; point number, its first question has nothing to go back to, and
;;; once the point is settled the run is over.  A single U undoes a
;;; whole run either way -- it is one undo group.
;;;
;;; A missing "CROSS DIMENSIONS" style is NOT invented: the dims are
;;; drawn in whatever style is current and the routine says so, so a
;;; drawing started from the wrong template is obvious instead of
;;; silently producing wrong-looking dims (CDCREATE's rule, kept).
;;;
;;; The whole run is one undo group: a single U takes it all away.
;;;
;;; Assumes drawing units are INCHES (architectural) and plan north is
;;; +Y -- the compass letter in the table is read off that.
;;;
;;; Versioning: see tools/release_lisp.py at the repo root.  It reads
;;; *abfind-version* below and stamps a dated, REV-numbered twin of
;;; this file into releases/.
;;; ======================================================================

(vl-load-com)

;;; ---------------------- configuration ---------------------------------

(setq *abfind-version* "v1.7")      ; announced on load; release_lisp.py
                                    ; reads this banner and stamps the
                                    ; dated twin in releases/ from it

(setq abf:*style*        "CROSS DIMENSIONS") ; dimension style to use
(setq abf:*layer*        "DIMENSION")   ; layer the dims land on
(setq abf:*offset*       0.0)       ; distance the dimension line is
                                    ; pushed off the tie it measures,
                                    ; drawing units (0.0 = right on the
                                    ; tie -- CDCREATE's convention)
(setq abf:*point-block*  "ab_pt")   ; block name whose INSERTs mark
                                    ; points wherever they sit
(setq abf:*point-layer*  "POINTS")  ; layer whose INSERTs are always
                                    ; points, and where the moved point
                                    ; lands once one is chosen
(setq abf:*point-color*  6)         ; colour to give that layer if the
                                    ; drawing somehow lacks it - the
                                    ; magenta the standard uses.  An
                                    ; existing POINTS keeps its own
(setq abf:*pt-tag*       "number")  ; attribute tag on the point block
                                    ; naming the point, as in "Pt.17"
(setq abf:*a-name*       "A")       ; what the two stakes are numbered
(setq abf:*b-name*       "B")       ; in the drawing
(setq abf:*snap*         12.0)      ; a click within this of a survey
                                    ; point takes THAT point
(setq abf:*ring-layer*   "FGStep")  ; layer the ring round the point
                                    ; that moved, and its note, go on -
                                    ; the same layer BPCALLOUT rings
                                    ; bad points on
(setq abf:*ring-radius*  5.0)       ; ring RADIUS (5 inches)
(setq abf:*note-hgt*     6.0)       ; height of the "Moved Pt.##" note
(setq abf:*moved-suffix* "m")       ; added to the number of a point
                                    ; that moved: Pt.17 -> Pt.17m
(setq abf:*sug-radius*   3.0)       ; radius of a suggestion's marker
                                    ; circle - smaller than the ring so
                                    ; the two never read as the same
                                    ; mark
(setq abf:*sug-layer*    "ABMOVE-POINTS") ; the suggestions get a layer
                                    ; of their OWN, never the points
                                    ; layer: they are throwaway, they
                                    ; would inherit the points layer's
                                    ; colour, and while they existed
                                    ; every other tool in the toolset
                                    ; would count them as real survey
                                    ; points.  Created when missing,
                                    ; and swept clear at the end of
                                    ; every round
(setq abf:*sug-color*    2)         ; colour of that layer, and an
                                    ; entity override to match: yellow,
                                    ; so a suggestion reads as a
                                    ; suggestion whatever the layer was
                                    ; set to by hand
(setq abf:*sug-hgt*      6.0)       ; height of a suggestion's tag
(setq abf:*locus-color*  8)         ; colour of the guide line each
                                    ; group of suggestions sits on:
                                    ; grey, so it reads as a guide and
                                    ; not as drawn work
(setq abf:*locus-ltype*  "DASHED")  ; and its linetype - created at
                                    ; pool scale when the drawing has
                                    ; no linetype by that name
(setq abf:*foot-steps*   10)        ; how many 1-foot steps are offered
                                    ; each way when a tape is swept: 10
                                    ; up and 10 down, per held stake
(setq abf:*max-shift*    120.0)     ; furthest a suggestion may sit from
                                    ; the reading, in inches.  It bounds
                                    ; BOTH families, so the shipped 10
                                    ; feet is exactly the reach of the
                                    ; foot sweep; lower it and the sweep
                                    ; shortens with the look-alikes
(setq abf:*max-sugg*     nil)       ; most suggestions per held stake,
                                    ; nil = as many as there are
(setq abf:*prec*         4)         ; rtos precision for every distance
                                    ; printed or written: 4 = 1/16"
(setq abf:*same-eps*     0.125)     ; two suggestions this close are
                                    ; the same place; only one is kept
(setq abf:*fuzz*         1e-6)      ; zero-length / same-spot tolerance
(setq abf:*att-height*   4.0)       ; height of the moved point's
(setq abf:*att-offset*   '(0.8697246 -3.5316825)) ; number, and where
                                    ; it sits relative to the point
                                    ; (both as the ab_pt block has it).
                                    ; The FALLBACK's only: a point that
                                    ; is copied keeps the attribute the
                                    ; point it came from had, height,
                                    ; place and all
(setq abf:*digit-pairs*             ; digits a field sheet confuses for
  '(("1" "7") ("1" "4") ("3" "8")   ; each other, both ways round
    ("3" "5") ("5" "6") ("6" "8")
    ("0" "9") ("4" "9") ("7" "9")))

;;; ---------------------- ask helpers -----------------------------------
;;; Copied from CALOFIN-LIB.lsp (cal:askkw, cal:back-word-p) under this
;;; file's own prefix, so the standalone file loads alone -- see
;;; STANDARDS.md section 4.  Back sentinel: CAL-BACK.

;;; ---------------------- layers ----------------------------------------

;; Make a layer current, creating it first when the drawing lacks it.
(defun abf:setlayer (name)
  (cal:ensure-layer name 7)
  (setvar "CLAYER" name))

;;; ---------------------- point lookup ----------------------------------

;; WHICH attribute of a point block carries its number, and what that
;; number is, as (index tag value): the abf:*pt-tag* one when the block
;; has it, otherwise the first whose value reads as a number (survey
;; exports do not all use the ab_pt tag).  nil when neither exists.
;; The index is what copying the point needs - it is the one attribute
;; of the copy whose value is not the original's.
(defun abf:number-att (en / sub ed hit fall v i)
  (setq sub (entnext en) hit nil fall nil i 0)
  (while (and sub
              (setq ed (entget sub))
              (= "ATTRIB" (cdr (assoc 0 ed))))
    (setq v (cdr (assoc 1 ed)))
    (if (and (null hit) v
             (cdr (assoc 2 ed))
             (= (strcase (cdr (assoc 2 ed))) (strcase abf:*pt-tag*)))
      (setq hit (list i (cdr (assoc 2 ed)) v)))
    (if (and (null fall) v (distof v 2))
      (setq fall (list i (cdr (assoc 2 ed)) v)))
    (setq sub (entnext sub) i (1+ i)))
  (if hit hit fall))

;; What the routine knows about one survey point: where it is, what it
;; is called, and the ENTITY it is.  The entity is carried so that a
;; point which moves can be COPIED rather than re-invented from this
;; file's defaults - it is what makes the moved point the same point.
(defun abf:cd-pt (c) (car c))       ; (x y z)
(defun abf:cd-nm (c) (cadr c))      ; "17"
(defun abf:cd-en (c) (caddr c))     ; the INSERT it was read from

;; Every NAMED survey point in the drawing, as (position name entity).
;; What counts as a point matches BPCALLOUT/CDCALLOUT/LHD; a point
;; whose number cannot be read is left out -- it cannot be asked for by
;; name, and it cannot be a stake either.
(defun abf:collect-points (/ ss i en ed p nm out)
  (setq out nil
        ss  (ssget "_X" '((0 . "INSERT"))))
  (if ss
    (progn
      (setq i 0)
      (repeat (sslength ss)
        (setq en (ssname ss i)
              ed (entget en)
              p  (cdr (assoc 10 ed)))
        (if (or (= (strcase (cdr (assoc 2 ed)))
                   (strcase abf:*point-block*))
                (= (strcase (cdr (assoc 8 ed)))
                   (strcase abf:*point-layer*)))
          (progn
            (setq nm (cal:block-number en abf:*pt-tag*))
            (if (and nm (/= nm ""))
              (setq out (cons (list (list (car p) (cadr p) 0.0) nm en)
                              out)))))
        (setq i (1+ i)))))
  (reverse out))

;; One comparable form for a point number, so "35", "Pt.35", "pt 35",
;; "#35" and "035" all meet in the middle: uppercase, spaces and hashes
;; dropped, a leading "PT" / "PT." dropped, and a value that reads as a
;; number rendered numerically (so leading zeros do not matter).  Only
;; the dot right after PT is a prefix dot - a point genuinely named
;; "40.5" keeps its decimal.  (CDCALLOUT's cdo:canon.)
(defun abf:canon (s / out i ch)
  (setq s (strcase s) out "" i 1)
  (while (<= i (strlen s))
    (setq ch (substr s i 1))
    (if (not (member ch '(" " "#")))
      (setq out (strcat out ch)))
    (setq i (1+ i)))
  (if (and (>= (strlen out) 2) (= (substr out 1 2) "PT"))
    (progn
      (setq out (substr out 3))
      (if (= (substr out 1 1) ".") (setq out (substr out 2)))))
  (if (distof out 2)
    (rtos (distof out 2) 2 8)
    out))

;; The survey point the typed number names, or nil.  The first match
;; wins when a drawing carries the same number twice.
(defun abf:find-point (s cands / want found c)
  (setq want (abf:canon s) found nil)
  (foreach c cands
    (if (and (null found) (= (abf:canon (abf:cd-nm c)) want))
      (setq found c)))
  found)

;; The survey point nearest to pick PK, when one sits within
;; abf:*snap* of it; nil otherwise.  Returns the ((x y z) . name) pair.
(defun abf:nearest (pk cands / best bd c d)
  (setq best nil bd nil)
  (foreach c cands
    (setq d (cal:dist pk (abf:cd-pt c)))
    (if (and (<= d abf:*snap*) (or (null bd) (< d bd)))
      (setq best c bd d)))
  best)

;; Where a stake is: the point named NAME when the drawing names one,
;; otherwise a click (snapped to the nearest survey point when there is
;; one under it).  nil when the user presses Enter instead.
(defun abf:stake (name cands / hit pk)
  (if (setq hit (abf:find-point name cands))
    (progn
      (princ (strcat "\n  Stake " name " found at Pt."
                     (abf:cd-nm hit) "."))
      (abf:cd-pt hit))
    (progn
      (princ (strcat "\nNo point is numbered \"" name
                     "\" in this drawing - click the " name
                     " stake instead."))
      (if (setq pk (getpoint (strcat "\nPick the " name
                                     " stake (Enter to cancel): ")))
        (progn
          (setq hit (abf:nearest pk cands))
          (if hit
            (progn
              (princ (strcat "\n  Taken from Pt." (abf:cd-nm hit) "."))
              (abf:cd-pt hit))
            (progn
              (princ (strcat "\n  No survey point within "
                             (rtos abf:*snap* 4 0)
                             " of the click - using the click itself."))
              (list (car pk) (cadr pk) 0.0))))))))

;;; ---------------------- geometry --------------------------------------

;; The 8-point compass name for ANG (0 = east), reading the drawing the
;; way it is plotted: plan north is +Y.
(defun abf:compass (ang / i)
  (setq i (rem (fix (+ 0.5 (/ (cal:angnorm ang) (/ pi 4.0)))) 8))
  (nth i '("E" "NE" "N" "NW" "W" "SW" "S" "SE")))

;; Where circle (ca ra) meets circle (cb rb), as a 3-D point.  The two
;; circles meet twice, mirrored across the A-B line; a misread tape
;; never flips a point to the far side of the stakes, so the crossing
;; nearer NEAR - the point as it is drawn now - is the one meant.  nil
;; when the two circles never reach each other at all.
(defun abf:circint (ca ra cb rb near / d ux uy m h2 h bx by p1 p2)
  (setq d (cal:dist ca cb))
  (if (> d abf:*fuzz*)
    (progn
      (setq ux (/ (- (car cb) (car ca)) d)
            uy (/ (- (cadr cb) (cadr ca)) d)
            m  (/ (+ (* d d) (* ra ra) (- (* rb rb))) (* 2.0 d))
            h2 (- (* ra ra) (* m m)))
      (if (>= h2 0.0)
        (progn
          (setq h  (sqrt h2)
                bx (+ (car ca) (* m ux))
                by (+ (cadr ca) (* m uy))
                p1 (list (- bx (* h uy)) (+ by (* h ux)) 0.0)
                p2 (list (+ bx (* h uy)) (- by (* h ux)) 0.0))
          (if (< (cal:dist p1 near) (cal:dist p2 near)) p1 p2))))))

;; Midpoint of p1->p2, pushed perpendicular to the tie by dist (dist
;; 0.0 puts the dimension line straight inbetween, on the tie itself).
;; (CDCALLOUT's cdo:loc.)
(defun abf:loc (p1 p2 dist / dx dy d m)
  (setq m (list (* 0.5 (+ (car  p1) (car  p2)))
                (* 0.5 (+ (cadr p1) (cadr p2)))
                0.0))
  (if (equal dist 0.0 1e-12)
    m
    (progn
      (setq dx (- (car  p2) (car  p1))
            dy (- (cadr p2) (cadr p1))
            d  (sqrt (+ (* dx dx) (* dy dy))))
      (if (> d 1e-9)
        (list (+ (car  m) (* dist (/ (- dy) d)))
              (+ (cadr m) (* dist (/ dx d)))
              0.0)
        m))))

;;; ---------------------- readings and misreadings ----------------------

;; A distance the way the sheet writes it.
(defun abf:fmt (d) (rtos d 4 abf:*prec*))

;; D's architectural reading as (feet whole-inches).  Rounded to the
;; nearest 1/16 first, so a distance a hair under a whole inch reads as
;; that inch and not as the one below it.
(defun abf:reading (d / w ft)
  (setq w  (fix (/ (+ (* (abs d) 16.0) 0.5) 16.0))
        ft (fix (/ (float w) 12.0)))
  (list ft (- w (* 12 ft))))

;; Every number N could have been, one digit at a time, when a digit is
;; read as its look-alike (abf:*digit-pairs*, both ways round).
(defun abf:digit-swaps (n / s i out ch pr alt new)
  (setq s (itoa n) i 1 out nil)
  (while (<= i (strlen s))
    (setq ch (substr s i 1))
    (foreach pr abf:*digit-pairs*
      (setq alt (cond ((= ch (car  pr)) (cadr pr))
                      ((= ch (cadr pr)) (car  pr))))
      (if alt
        (progn
          (setq new (atoi (strcat (substr s 1 (1- i)) alt (substr s (1+ i)))))
          (if (and (>= new 0) (/= new n) (not (member new out)))
            (setq out (cons new out))))))
    (setq i (1+ i)))
  (reverse out))

;; Every number N could have been with two neighbouring digits written
;; the other way round (21 -> 12).
(defun abf:digit-flips (n / s i out new)
  (setq s (itoa n) i 1 out nil)
  (while (< i (strlen s))
    (setq new (atoi (strcat (substr s 1 (1- i))
                            (substr s (1+ i) 1)
                            (substr s i 1)
                            (substr s (+ i 2)))))
    (if (and (/= new n) (not (member new out)))
      (setq out (cons new out)))
    (setq i (1+ i)))
  (reverse out))

;; V inserted into the already-sorted LST, smallest miss first.  A tie
;; goes up before down, so the sweep always reads 1, -1, 2, -2 ... and
;; never flips a pair round because a look-alike happened to land on
;; that foot first.
(defun abf:ins-delta (v lst)
  (cond ((null lst) (list v))
        ((< (abs v) (abs (car lst))) (cons v lst))
        ((and (equal (abs v) (abs (car lst)) 1e-9) (> v 0.0))
         (cons v lst))
        (t (cons (car lst) (abf:ins-delta v (cdr lst))))))

;; Every reading D could have been instead, as a signed shift in
;; inches.  Two families:
;;
;;   * THE FOOT SWEEP - the tape read a whole number of feet out, one
;;     foot at a time, abf:*foot-steps* of them each way.  It does not
;;     care whether the number looks like another one: a foot is the
;;     unit a tape gets miscounted in, so every foot within reach is
;;     worth seeing.
;;   * THE LOOK-ALIKES - the reading was written down as a number that
;;     resembles it: the inches losing or gaining a leading 1
;;     (1" <-> 11"), a digit read as its look-alike in the inches or
;;     in the feet (abf:*digit-pairs*), and two feet digits changing
;;     places (21' -> 12').
;;
;; Only shifts up to abf:*max-shift* survive - it bounds both families
;; - and a reading that would come out at or below zero is dropped.
;; Nearest miss first, no repeats: a look-alike that lands on a whole
;; foot is already in the sweep and is not listed twice.
(defun abf:deltas (d / r ft inch raw out v k)
  (setq r    (abf:reading d)
        ft   (car  r)
        inch (cadr r)
        raw  nil
        k    1)
  (repeat abf:*foot-steps*                       ; the foot sweep
    (setq raw (cons (* 12.0 k) (cons (* -12.0 k) raw))
          k   (1+ k)))
  (foreach v '(10.0 -10.0)
    (if (and (>= (+ inch v) 0.0) (<= (+ inch v) 11.0))
      (setq raw (cons v raw))))
  (foreach v (abf:digit-swaps inch)
    (if (<= v 11) (setq raw (cons (float (- v inch)) raw))))
  (foreach v (append (abf:digit-swaps ft) (abf:digit-flips ft))
    (setq raw (cons (float (* 12 (- v ft))) raw)))
  (setq out nil)
  (foreach v raw
    (if (and (> (abs v) abf:*fuzz*)
             (<= (abs v) abf:*max-shift*)
             (> (+ d v) 0.0)
             (not (member v out)))
      (setq out (abf:ins-delta v out))))
  out)

;; C inserted into the already-sorted LST, smallest miss first.
(defun abf:ins-cand (c lst)
  (cond ((null lst) (list c))
        ((< (car c) (car (car lst))) (cons c lst))
        (t (cons (car lst) (abf:ins-cand c (cdr lst))))))

;; T when P is already where one of the candidates in LST sits, or
;; where the point itself sits - the same place twice is one choice.
(defun abf:seen-p (p pp lst / hit c)
  (setq hit (< (cal:dist p pp) abf:*same-eps*))
  (foreach c lst
    (if (< (cal:dist p (nth 5 c)) abf:*same-eps*) (setq hit T)))
  hit)

;; One group of candidates: one stake's reading is HELD exactly as it
;; is and the other's is walked through abf:deltas.  movea non-nil
;; varies A's reading and holds B's; nil is the other way round.  Each
;; entry is (miss held moved old-reading new-reading point tag),
;; smallest miss first, capped at abf:*max-sugg* (nil = uncapped).  A
;; reading the held tape can no longer reach has no crossing and is
;; left out.
(defun abf:group (pa a pb b pp held moved movea
                  / was out dl nd np n cut one k tag reads)
  (setq was   (if movea a b)
        out   nil
        reads 0)
  (foreach dl (abf:deltas was)
    (setq nd (+ was dl)
          np (if movea
               (abf:circint pa nd pb b pp)
               (abf:circint pa a pb nd pp)))
    (if (and np (not (abf:seen-p np pp out)))
      (progn
        ;; the tag is the answer the user types, so it says what the
        ;; suggestion IS: the moved tape's letter, after either the
        ;; number of feet it moved (2B, -3B) or, for a reading that is
        ;; not a whole foot, its place in this tape's look-alikes
        ;; (R1B).  Numbering only what is actually offered keeps the
        ;; R numbers unbroken when a reading is out of reach.
        (setq k (/ dl 12.0))
        (if (equal k (float (fix k)) 1e-9)
          (setq tag (strcat (itoa (fix k)) moved))
          (setq reads (1+ reads)
                tag   (strcat "R" (itoa reads) moved)))
        (setq out (abf:ins-cand
                    (list (abs dl) held moved was nd np tag) out)))))
  (if (and abf:*max-sugg* (> (length out) abf:*max-sugg*))
    (progn
      (setq cut nil n 0)
      (foreach one out
        (if (< n abf:*max-sugg*) (setq cut (cons one cut)))
        (setq n (1+ n)))
      (setq out (reverse cut))))
  out)

;; Every place PP could sit if ONE of its two tapes was read wrong, in
;; the two groups that answer separately: the ones that move A (B held)
;; first, so their tags run 1A, -1A, R1A ..., then the ones that move
;; B.  A candidate can never appear in both - a B-held one keeps its
;; distance from B exactly and an A-held one does not - so the groups
;; are simply run together, each nearest miss first.
(defun abf:candidates (pa pb pp / a b)
  (setq a (cal:dist pa pp)
        b (cal:dist pb pp))
  (if (and (> a abf:*fuzz*) (> b abf:*fuzz*))
    (append (abf:group pa a pb b pp abf:*b-name* abf:*a-name* T)
            (abf:group pa a pb b pp abf:*a-name* abf:*b-name* nil))))

;;; ---------------------- what gets drawn -------------------------------

;; Restore a dimension style by name when the drawing has it; returns T
;; when the style was set.
(defun abf:setstyle (name)
  (if (and name (tblsearch "DIMSTYLE" name))
    (progn (command "_.-DIMSTYLE" "_Restore" name) t)))

;; A copy of an entget list with every entry for group CODE dropped.
(defun abf:strip (code lst / out g)
  (foreach g lst (if (/= code (car g)) (setq out (cons g out))))
  (reverse out))

;; Force a freshly drawn dimension onto the layer and style ABFIND
;; promises, ByLayer -- DIMLAYER, a style-owned layer or a leftover
;; per-entity override would otherwise have the last word.
(defun abf:fixdim (en havestyle / ed code)
  (if (and en (setq ed (entget en))
           (= "DIMENSION" (cdr (assoc 0 ed))))
    (progn
      (setq ed (if (assoc 8 ed)
                 (subst (cons 8 abf:*layer*) (assoc 8 ed) ed)
                 (append ed (list (cons 8 abf:*layer*)))))
      (if havestyle
        (setq ed (if (assoc 3 ed)
                   (subst (cons 3 abf:*style*) (assoc 3 ed) ed)
                   (append ed (list (cons 3 abf:*style*))))))
      (foreach code '(62 6 370) (setq ed (abf:strip code ed)))
      (entmod ed)
      (entupd en)
      t)))

;; One aligned dimension from P1 to P2, on the tie.  Returns the new
;; entity, or nil when there was nothing to measure.
(defun abf:dim1 (p1 p2 havestyle / pre new)
  (if (> (cal:dist p1 p2) abf:*fuzz*)
    (progn
      (setq pre (entlast))
      (command "_.DIMALIGNED"
               "_non" (trans p1 0 1)
               "_non" (trans p2 0 1)
               "_non" (trans (abf:loc p1 p2 abf:*offset*) 0 1))
      (setq new (entlast))
      (if (and new (not (eq new pre)))
        (progn (abf:fixdim new havestyle) new)))))

;; The pair of ties a point is surveyed by: A to it and B to it.
(defun abf:dim-pair (pa pb pp havestyle / e out)
  (setq out nil)
  (if (setq e (abf:dim1 pa pp havestyle)) (setq out (cons e out)))
  (if (setq e (abf:dim1 pb pp havestyle)) (setq out (cons e out)))
  (reverse out))

;; The ring round the point that moved.
(defun abf:ring (ctr)
  (entmake (list '(0 . "CIRCLE") '(100 . "AcDbEntity")
                 (cons 8 abf:*ring-layer*) '(100 . "AcDbCircle")
                 (list 10 (car ctr) (cadr ctr) 0.0)
                 (cons 40 abf:*ring-radius*)))
  (entlast))

;; The note that says what moved, and from what reading to what.
(defun abf:note (p str)
  (entmake (list '(0 . "TEXT") '(100 . "AcDbEntity")
                 (cons 8 abf:*ring-layer*) '(100 . "AcDbText")
                 (list 10 (car p) (cadr p) 0.0)
                 (cons 40 abf:*note-hgt*) (cons 1 str)))
  (entlast))

;; Where the note goes when it is not placed by hand: beside the ring,
;; clear of it, the way BPCALLOUT tucks its callout.
(defun abf:note-spot (ctr)
  (list (+ (car  ctr) (* 2.0 abf:*ring-radius*))
        (- (cadr ctr) (* 2.0 abf:*ring-radius*))
        0.0))

;; A survey point at P numbered NM, built from this file's defaults:
;; the drawing's own point block when it has one, a POINT with a text
;; label beside it when it does not.  Returns the entities it made.
;;
;; This is the FALLBACK.  A point that moves is copied from the point
;; it came from (abf:copy-point) so that it keeps that point's layer,
;; block, scale and attributes; only a drawing whose point block is not
;; in its block table has nothing to copy from and comes here.
(defun abf:make-point (p nm / out apt)
  (setq out nil
        apt (list (+ (car  p) (car  abf:*att-offset*))
                  (+ (cadr p) (cadr abf:*att-offset*))
                  0.0))
  (if (tblsearch "BLOCK" abf:*point-block*)
    (progn
      (entmake (list '(0 . "INSERT") '(100 . "AcDbEntity")
                     (cons 8 abf:*point-layer*)
                     '(100 . "AcDbBlockReference") '(66 . 1)
                     (cons 2 abf:*point-block*)
                     (list 10 (car p) (cadr p) 0.0)
                     '(41 . 1.0) '(42 . 1.0) '(43 . 1.0) '(50 . 0.0)))
      (setq out (cons (entlast) out))
      (entmake (list '(0 . "ATTRIB") '(100 . "AcDbEntity") '(8 . "0")
                     '(100 . "AcDbText") (cons 10 apt)
                     (cons 40 abf:*att-height*) (cons 1 nm)
                     '(100 . "AcDbAttribute")
                     (cons 2 abf:*pt-tag*) '(70 . 0)))
      (setq out (cons (entlast) out))
      (entmake (list '(0 . "SEQEND") '(100 . "AcDbEntity")
                     (cons 8 abf:*point-layer*)))
      (setq out (cons (entlast) out)))
    (progn
      (entmake (list '(0 . "POINT") '(100 . "AcDbEntity")
                     (cons 8 abf:*point-layer*) '(100 . "AcDbPoint")
                     (list 10 (car p) (cadr p) 0.0)))
      (setq out (cons (entlast) out))
      (entmake (list '(0 . "TEXT") '(100 . "AcDbEntity")
                     (cons 8 abf:*point-layer*) '(100 . "AcDbText")
                     (cons 10 apt) (cons 40 abf:*att-height*)
                     (cons 1 nm)))
      (setq out (cons (entlast) out))))
  (reverse out))

;; An entget list ready to be entmade as a NEW entity: the codes that
;; name the entity it was read from, rather than describe it, are
;; dropped.  Everything else - layer, colour, linetype, lineweight,
;; block name, scale, rotation, extrusion, extended data - is what
;; makes the copy the same thing as the original, and stays.
(defun abf:cloneable (ed / out g)
  (foreach g ed
    (if (not (member (car g) '(-1 -2 5 102 330 331 340 360 361)))
      (setq out (cons g out))))
  (reverse out))

;; ED with CODE set to VAL: the entry it has replaced, or a new one on
;; the end when it has none.
(defun abf:put (ed code val / g)
  (if (setq g (assoc code ed))
    (subst (cons code val) g ed)
    (append ed (list (cons code val)))))

;; ED's point at CODE moved by (DX DY), when it has one.  An attribute
;; travels with the block it belongs to, keeping the offset it had.
(defun abf:shift (ed code dx dy / g)
  (if (setq g (assoc code ed))
    (abf:put ed code (list (+ (cadr g) dx) (+ (caddr g) dy)
                           (if (cdddr g) (cadddr g) 0.0)))
    ed))

;; A COPY of the survey point EN, standing at P and numbered NM.  The
;; same point in every other way: the same block, layer, colour,
;; linetype, lineweight, scale, rotation and extended data, and every
;; attribute it carries - same tag, same height, same style, each
;; keeping the offset it had from the point.  Only the attribute that
;; holds the number is written, and only with NM.
;;
;; A survey point carries more than a position: the layer the survey
;; put it on, a block scaled to the sheet, an elevation or a
;; description in a second attribute.  A moved point is that same point
;; one reading further on, so it is copied rather than rebuilt - a
;; rebuilt one silently dropped all of it.
;;
;; Returns the entities it made, or nil when EN is not a block
;; reference this drawing can insert again - the caller falls back to
;; abf:make-point then.
(defun abf:copy-point (en p nm / ed atts sub sd base dx dy lay numi
                                 out i)
  (setq ed (if en (entget en '("*"))))
  (if (and ed
           (= "INSERT" (cdr (assoc 0 ed)))
           (assoc 10 ed)
           (assoc 2 ed)
           (tblsearch "BLOCK" (cdr (assoc 2 ed))))
    (progn
      (setq base (cdr (assoc 10 ed))
            dx   (- (car  p) (car  base))
            dy   (- (cadr p) (cadr base))
            lay  (if (assoc 8 ed) (cdr (assoc 8 ed)) "0")
            numi (car (abf:number-att en))
            atts nil
            sub  (entnext en)
            i    0)
      ;; the attributes first, so the INSERT can be made knowing
      ;; whether it needs the (66 . 1) that says it has some
      (while (and sub
                  (setq sd (entget sub '("*")))
                  (= "ATTRIB" (cdr (assoc 0 sd))))
        (setq sd (abf:shift (abf:shift (abf:cloneable sd) 10 dx dy)
                            11 dx dy))
        (if (and numi (= i numi)) (setq sd (abf:put sd 1 nm)))
        (setq atts (cons sd atts)
              sub  (entnext sub)
              i    (1+ i)))
      (setq atts (reverse atts)
            ed   (abf:put (abf:cloneable ed) 10
                          (list (car p) (cadr p) 0.0))
            ed   (if atts (abf:put ed 66 1) (abf:strip 66 ed))
            out  nil)
      ;; the point goes back on its own layer, so that layer has to be
      ;; visible for the same reason every other output layer does
      (cal:ensure-layer lay abf:*point-color*)
      (if (entmake ed)                     ; nil when the copy is
        (progn                             ; refused - fall back then
          (setq out (list (entlast)))
          (foreach sd atts
            (if (entmake sd) (setq out (cons (entlast) out))))
          (if atts
            (if (entmake (list '(0 . "SEQEND") '(100 . "AcDbEntity")
                               (cons 8 lay)))
              (setq out (cons (entlast) out))))
          (reverse out))))))

;; One suggestion on screen: a point where it would sit, a small circle
;; so it can be seen and clicked, and its tag beside it.  On
;; abf:*sug-layer*, never the points layer - a suggestion is not one of
;; the drawing's own points and must not read as one, to the eye or to
;; the next tool - in abf:*sug-color*, and all of it swept again as
;; soon as the round ends.
(defun abf:draw-sug (p tag / out)
  (setq out nil)
  (entmake (list '(0 . "POINT") '(100 . "AcDbEntity")
                 (cons 8 abf:*sug-layer*)
                 (cons 62 abf:*sug-color*) '(100 . "AcDbPoint")
                 (list 10 (car p) (cadr p) 0.0)))
  (setq out (cons (entlast) out))
  (entmake (list '(0 . "CIRCLE") '(100 . "AcDbEntity")
                 (cons 8 abf:*sug-layer*)
                 (cons 62 abf:*sug-color*) '(100 . "AcDbCircle")
                 (list 10 (car p) (cadr p) 0.0)
                 (cons 40 abf:*sug-radius*)))
  (setq out (cons (entlast) out))
  (entmake (list '(0 . "TEXT") '(100 . "AcDbEntity")
                 (cons 8 abf:*sug-layer*)
                 (cons 62 abf:*sug-color*) '(100 . "AcDbText")
                 (list 10 (+ (car  p) abf:*sug-radius*)
                          (+ (cadr p) abf:*sug-radius*) 0.0)
                 (cons 40 abf:*sug-hgt*) (cons 1 tag)))
  (setq out (cons (entlast) out))
  (reverse out))

;; Make sure the guide line's linetype exists, with dashes sized for a
;; drawing in inches so they read at pool scale.  Pure entmake, no
;; command calls.  (pf:ensure-dashed, abhd.lsp:1566.)  A drawing that
;; already has a linetype by that name keeps its own.
(defun abf:ensure-dashed ()
  (if (not (tblsearch "LTYPE" abf:*locus-ltype*))
    (entmake (list '(0 . "LTYPE") '(100 . "AcDbSymbolTableRecord")
                   '(100 . "AcDbLinetypeTableRecord")
                   (cons 2 abf:*locus-ltype*) '(70 . 0)
                   '(3 . "Dashed __ __ __ __ __")
                   '(72 . 65) '(73 . 2) '(40 . 18.0)
                   '(49 . 12.0) '(74 . 0)
                   '(49 . -6.0) '(74 . 0)))))

;; The guide line one group of suggestions lies on.  Every candidate
;; that HELD the same tape sits at exactly that tape's reading off its
;; stake - and so does the point as it is drawn now - so the whole
;; group is on one circle centred there.  The arc runs from the
;; furthest candidate one way round to the furthest the other, through
;; the point itself: a dashed grey line through all of them.  Returns
;; what it made, in a list, or nil when the group is empty.
(defun abf:draw-locus (ctr rad pp sugs held / a0 lo hi c d)
  (setq a0 (angle (cal:2d ctr) (cal:2d pp))
        lo 0.0
        hi 0.0)
  (foreach c sugs
    (if (= (cadr c) held)
      (progn
        (setq d (cal:signed-dang
                  a0 (angle (cal:2d ctr) (cal:2d (nth 5 c)))))
        (if (< d lo) (setq lo d))
        (if (> d hi) (setq hi d)))))
  (if (> (- hi lo) abf:*fuzz*)
    (progn
      (abf:ensure-dashed)
      (entmake (list '(0 . "ARC") '(100 . "AcDbEntity")
                     (cons 8 abf:*sug-layer*)
                     (cons 62 abf:*locus-color*)
                     (cons 6 abf:*locus-ltype*)
                     '(100 . "AcDbCircle")
                     (list 10 (car ctr) (cadr ctr) 0.0)
                     (cons 40 rad)
                     '(100 . "AcDbArc")
                     (cons 50 (+ a0 lo)) (cons 51 (+ a0 hi))))
      (list (entlast)))))

;; Erase a list of entities, skipping any that has gone already.
(defun abf:drop (lst / e)
  (foreach e lst (if (and e (entget e)) (entdel e))))

;; Bring a list of erased entities back (entdel un-deletes what it
;; deleted), skipping any that is still there.
(defun abf:undrop (lst / e)
  (foreach e lst (if (and e (null (entget e))) (entdel e))))

;;; ---------------------- the engine ------------------------------------
;;; ABFIND and ABMOVE are one flow: ABMOVE is ABFIND plus the two
;;; questions that move the point, so they share this and differ by the
;;; MOVEP flag.  The *error* handler lives here rather than in the
;;; command defuns because this is where the state it has to put back
;;; is - it is localized in the arglist just the same, so the previous
;;; handler comes back when the run ends (STANDARDS.md section 5).
;;;
;;; The two differ in shape as well as in questions.  ABFIND rinses and
;;; repeats, so it keeps a history and Back takes the last round away
;;; again, whatever that round did:
;;;
;;;     ("DIM"  pair)
;;;     ("MOVE" old-pair new-pair moved-point-ents ring note)
;;;
;;; ABMOVE does ONE point - it was typed to move one - and ends as soon
;;; as that point is settled, so it keeps no history.  A single U
;;; undoes the whole run either way.

(defun abf:undo-round (r)
  (if (= (car r) "DIM")
    (abf:drop (cadr r))
    (progn
      (abf:drop (caddr r))                 ; the dims to where it moved
      (abf:drop (cadddr r))                ; the moved point
      (abf:drop (list (nth 4 r) (nth 5 r))); its ring and its note
      (abf:undrop (cadr r)))))             ; the dims it had before

;; NOTE: no local here may be named after a function this routine calls
;; - an AutoLISP local SHADOWS the function of the same name for the
;; whole call (the BPCALLOUT v1.0 lesson).
(defun abf:run (movep / *error* undo-open oce ocl oos odim cmd cands
                        pa pb hist stage done made moves hit sce nm pp
                        pair sugs temps c kws shown ans sug havestyle
                        np newpt newnm tried lasthold ments ring note
                        npair)

  (defun *error* (m)
    ;; user settings come back FIRST so nothing below can skip them
    (abf:drop temps)
    (if (and odim (not (equal odim (getvar "DIMSTYLE"))))
      (vl-catch-all-apply 'command-s (list "_.-DIMSTYLE" "_Restore" odim)))
    (if ocl (setvar "CLAYER"  ocl))
    (if oos (setvar "OSMODE"  oos))
    (if oce (setvar "CMDECHO" oce))
    (if undo-open
      (vl-catch-all-apply 'command-s (list "_.UNDO" "_End")))
    (if (and m (not (wcmatch (strcase m)
                             "*BREAK*,*CANCEL*,*QUIT*,*EXIT*")))
      (princ (strcat "\n" (if cmd cmd "ABFIND") " error: " m)))
    (princ))

  (setq cmd  (if movep "ABMOVE" "ABFIND")
        oce  (getvar "CMDECHO")
        ocl  (getvar "CLAYER")
        oos  (getvar "OSMODE")
        odim (getvar "DIMSTYLE"))
  (princ (strcat "\n" cmd " " *abfind-version*))

  (setq cands (abf:collect-points))
  (if (null cands)
    (princ (strcat "\nNo named survey points found in the drawing - "
                   cmd " has nothing to tie to."))
    (progn
      (princ (strcat "\n" (itoa (length cands)) " named survey point(s)"
                     " found.  Click one, or type its number as it"
                     " reads in the drawing (\"35\" or \"Pt.35\")."))
      ;; -- the two stakes, before OSMODE goes down: a drawing that
      ;;    does not name them wants object snap for the clicks
      (setq pa (abf:stake abf:*a-name* cands))
      (if pa (setq pb (abf:stake abf:*b-name* cands)))
      (cond
        ((null pa)
         (princ (strcat "\nNo " abf:*a-name* " stake - nothing drawn.")))
        ((null pb)
         (princ (strcat "\nNo " abf:*b-name* " stake - nothing drawn.")))
        ((< (cal:dist pa pb) abf:*fuzz*)
         (princ (strcat "\nThe " abf:*a-name* " and " abf:*b-name*
                        " stakes sit on the same spot - two tapes off"
                        " one stake cannot place anything.")))
        (t
         (setvar "CMDECHO" 0)
         (setvar "OSMODE"  0)
         (command "_.UNDO" "_Begin")
         (setq undo-open T)
         (abf:setlayer abf:*layer*)
         (setq havestyle (abf:setstyle abf:*style*))
         (if (not havestyle)
           (princ (strcat "\n** This drawing has no \"" abf:*style*
                          "\" dimension style -- dims drawn in \""
                          (getvar "DIMSTYLE")
                          "\" instead.  Create the style (or start"
                          " from the standard template) and re-run.")))

         ;; -- the round loop.  A round is one point:
         ;;      1  which point       -- its two ties are drawn
         ;;      2  move it?          -- ABFIND only: it measures, so
         ;;                              it asks before going looking.
         ;;                              ABMOVE was typed to move a
         ;;                              point and goes straight on
         ;;      3  work out where it could go, and show it (no
         ;;         question of its own)
         ;;      4  which suggestion
         ;;      5  where the note goes, and then the move itself
         ;;    Each question backs out into the one before it.  ABFIND
         ;;    goes round again after every round, moved or not;
         ;;    ABMOVE settles its one point and ends.
         (setq hist nil stage 1 done nil made 0 moves 0 temps nil)
         (while (not done)
           (cond

             ;; -- 1: which point.  Typed or clicked, the one prompt
             ;;       takes both: (initget 128) hands typed text back
             ;;       from getpoint as the string it is, and a click
             ;;       comes back as the point it is.  Back is typed
             ;;       like a value here, the way it is at every prompt
             ;;       that is not a keyword one.
             ((= stage 1)
              (initget 128)
              (setq ans (getpoint
                          (if movep
                            (strcat "\nPick the point, or type its"
                                    " number (Enter to cancel): ")
                            (strcat "\nPick the point, or type its"
                                    " number"
                                    (if hist " [Back]" "")
                                    " <Enter = done>: ")))
                    hit nil)
              (cond
                ((null ans) (setq done T))
                ((and (not (listp ans)) (cal:back-word-p ans))
                 (if hist
                   (progn
                     (abf:undo-round (car hist))
                     ;; a MOVE round put exactly one point into the
                     ;; lookup, and Back always pops the newest round,
                     ;; so the newest entry is the one it added
                     (if (= (car (car hist)) "MOVE")
                       (setq moves (1- moves)
                             cands (cdr cands)))
                     (setq hist (cdr hist)
                           made (1- made))
                     (princ "\nStepping back one point."))
                   (princ "\nAlready at the first point.")))
                (t
                 ;; a click names the survey point under it, exactly as
                 ;; a typed number names one; nothing under it names
                 ;; nothing, and is reported the way a typo is
                 (setq hit (if (listp ans)
                             (abf:nearest ans cands)
                             (abf:find-point ans cands)))
                 (cond
                   ((null hit)
                    (if (listp ans)
                      (princ (strcat "\n  No survey point within "
                                     (rtos abf:*snap* 4 0)
                                     " of that click - nothing drawn."))
                      (princ (strcat "\n  No point numbered \"" ans
                                     "\" in the drawing - nothing"
                                     " drawn."))))
                   ((or (< (cal:dist (abf:cd-pt hit) pa) abf:*fuzz*)
                        (< (cal:dist (abf:cd-pt hit) pb) abf:*fuzz*))
                    (princ (strcat "\n  Pt." (abf:cd-nm hit) " IS a"
                                   " stake - the ties are measured"
                                   " FROM it.")))
                   (t
                    (setq nm   (abf:cd-nm hit)
                          sce  (abf:cd-en hit)   ; what a move copies
                          pp   (abf:cd-pt hit)
                          pair (abf:dim-pair pa pb pp havestyle))
                    (if (null pair)
                      (princ (strcat "\n  Pt." nm " sits on a stake - "
                                     "there is nothing to measure."))
                      (progn
                        (setq made  (1+ made)
                              stage (if movep 3 2))
                        (princ (strcat "\n  Pt." nm ":  "
                                       abf:*a-name* " "
                                       (abf:fmt (cal:dist pa pp)) "   "
                                       abf:*b-name* " "
                                       (abf:fmt (cal:dist pb pp))
                                       "  dimensioned.")))))))))

             ;; -- 2: does this one want moving?  (ABFIND only)
             ((= stage 2)
              (setq ans (cal:askyn (strcat "  Move Pt." nm
                                           " to a different reading?")
                                   "No" T))
              (cond
                ((eq ans 'CAL-BACK)
                 (abf:drop pair)
                 (setq made  (1- made)
                       stage 1)
                 (princ "\nStepping back one point."))
                (ans (setq stage 3))
                (t (setq hist  (cons (list "DIM" pair) hist)
                         stage 1))))

             ;; -- 3: where else could this point be?  Nothing is asked
             ;;       here - the readings are worked out and drawn, and
             ;;       the next stage is the one that asks.
             ((= stage 3)
              (setq sugs  (abf:candidates pa pb pp)
                    temps nil)
              (if (null sugs)
                (progn
                  (princ (strcat "\n  No reading within "
                                 (abf:fmt abf:*max-shift*)
                                 " puts Pt." nm " anywhere the other"
                                 " tape can reach - left where it is."))
                  (if movep
                    (setq done T)
                    (setq hist  (cons (list "DIM" pair) hist)
                          stage 1)))
                (progn
                  (cal:ensure-layer abf:*sug-layer* abf:*sug-color*)
                  (foreach c sugs
                    (setq temps (append temps
                                        (abf:draw-sug (nth 5 c)
                                                      (nth 6 c)))))
                  ;; and the line each group sits on, in the order the
                  ;; table lists them
                  (setq temps (append temps
                                      (abf:draw-locus
                                        pb (cal:dist pb pp) pp sugs
                                        abf:*b-name*)
                                      (abf:draw-locus
                                        pa (cal:dist pa pp) pp sugs
                                        abf:*a-name*)))
                  (setq tried (+ (length (abf:deltas (cal:dist pa pp)))
                                 (length (abf:deltas (cal:dist pb pp)))))
                  (princ (strcat "\n\n  Where Pt." nm
                                 " lands if one tape was read wrong -"
                                 " the ones that move " abf:*a-name*
                                 " first, then " abf:*b-name*
                                 " (nearest miss first):"))
                  (if (> tried (length sugs))
                    (princ (strcat "\n  "
                                   (itoa (- tried (length sugs)))
                                   " of the " (itoa tried)
                                   " readings are not offered: out of"
                                   " the other tape's reach"
                                   (if abf:*max-sugg*
                                     ", or past the list cap" "")
                                   ".")))
                  (princ (strcat "\n   tag   held  moved  from"
                                 "          to            the point"
                                 " moves"))
                  (princ (strcat "\n   ----  ----  -----  ---------"
                                 "--   -----------   -------------"
                                 "--"))
                  (setq lasthold nil)
                  (foreach c sugs
                    ;; a blank line where the held stake changes: the
                    ;; two answers read as two blocks, not one long
                    ;; list
                    (if (and lasthold (/= lasthold (cadr c)))
                      (princ "\n"))
                    (setq lasthold (cadr c))
                    (princ (strcat "\n   " (cal:pad (nth 6 c) 6)
                                   (cal:pad (cadr c) 6)
                                   (cal:pad (caddr c) 7)
                                   (cal:pad (abf:fmt (cadddr c)) 14)
                                   (cal:pad (abf:fmt (nth 4 c)) 14)
                                   (abf:fmt (cal:dist pp (nth 5 c)))
                                   " "
                                   (abf:compass
                                     (angle (cal:2d pp)
                                            (cal:2d (nth 5 c)))))))
                  (setq stage 4))))

             ;; -- 4: which suggestion
             ((= stage 4)
              ;; every tag is a keyword, so any of them can be typed -
              ;; but a bracket listing forty-odd of them is unreadable,
              ;; so the bracket shows only the words that are not in
              ;; the table.  Everything it DOES show is a keyword, so
              ;; nothing shown fails when it is clicked.
              (setq kws "")
              (foreach c sugs (setq kws (strcat kws (nth 6 c) " ")))
              (setq kws   (strcat kws "Pick None")
                    shown "Pick/None"
                    ans   (cal:askkw
                            (strcat "  Move Pt." nm
                                    " - type a tag from the table")
                            kws shown "None" T))
              (cond
                ((eq ans 'CAL-BACK)
                 (abf:drop temps)
                 (setq temps nil)
                 ;; ABFIND came here from its own question, so Back
                 ;; re-asks that; ABMOVE came straight from the point
                 ;; number, so Back re-asks that instead
                 (if movep
                   (progn
                     (abf:drop pair)
                     (setq made  (1- made)
                           stage 1)
                     (princ "\nStepping back one point."))
                   (setq stage 2)))
                ((= ans "None")
                 (abf:drop temps)
                 (setq temps nil)
                 (princ (strcat "\n  Pt." nm " left where it is."))
                 (if movep
                   (setq done T)
                   (setq hist  (cons (list "DIM" pair) hist)
                         stage 1)))
                ((= ans "Pick")
                 (initget "Back Undo")
                 (setq np (getpoint "\n  Click the one you want [Back]: "))
                 (cond
                   ((null np)
                    (princ "\n  Nothing clicked - pick from the list."))
                   ((member np '("Back" "Undo"))
                    (princ "\n  Back to the list."))
                   (t
                    (setq sug nil)
                    (foreach c sugs
                      (if (and (null sug)
                               (<= (cal:dist np (nth 5 c)) abf:*snap*))
                        (setq sug c)))
                    (if sug
                      (setq stage 5)
                      (princ (strcat "\n  No suggestion within "
                                     (rtos abf:*snap* 4 0)
                                     " of that click - try again."))))))
                (t
                 ;; initget refuses anything that is not one of the
                 ;; tags, so the lookup cannot miss - the guard is
                 ;; there so a future keyword cannot walk off the list
                 (setq sug nil)
                 (foreach c sugs
                   (if (and (null sug) (= (nth 6 c) ans)) (setq sug c)))
                 (if sug
                   (setq stage 5)
                   (princ (strcat "\n  \"" ans "\" is not one of the"
                                  " tags - nothing moved."))))))

             ;; -- 5: where the note goes, and then the move itself
             (t
              (princ "\n  Auto tucks the note beside the ring.")
              (initget "Auto Back Undo")
              (setq np (getpoint (strcat "\n  Place the note for Pt." nm
                                         " [Auto/Back] <Auto>: ")))
              (if (and np (member np '("Back" "Undo")))
                (setq stage 4)
                (progn
                  ;; nil is Enter and a string is the Auto keyword;
                  ;; only a real list is a spot the user clicked
                  (if (or (null np) (not (listp np)))
                    (setq np (abf:note-spot pp)))
                  ;; the suggestions have done their job
                  (abf:drop temps)
                  (setq temps nil
                        newpt (nth 5 sug)
                        ments nil)
                  ;; the chosen one is a survey point, so THIS is what
                  ;; lands on the points layer - and it is the point it
                  ;; came from, copied: same block, same layer, same
                  ;; scale, same attributes, one number different.
                  ;; Only a drawing whose point block is not in its
                  ;; block table has nothing to copy from
                  (cal:ensure-layer abf:*point-layer* abf:*point-color*)
                  (setq newnm (strcat nm abf:*moved-suffix*)
                        ments (if (setq ments
                                    (abf:copy-point sce newpt newnm))
                                ments
                                (abf:make-point newpt newnm)))
                  (cal:ensure-layer abf:*ring-layer* 1)
                  (setq ring (abf:ring pp)
                        note (abf:note np
                               (strcat "Moved Pt." nm " " (caddr sug)
                                       " from " (abf:fmt (cadddr sug))
                                       " to "   (abf:fmt (nth 4 sug)))))
                  ;; the ties belong to where the point is now; the old
                  ;; reading is not lost - the note carries it
                  (abf:drop pair)
                  (setq npair (abf:dim-pair pa pb newpt havestyle)
                        moves (1+ moves))
                  (if movep
                    ;; that point is settled, and settling one is all
                    ;; ABMOVE is for
                    (setq done T)
                    ;; ABFIND carries on, and the point it just made is
                    ;; a point like any other from here
                    (setq hist  (cons (list "MOVE" pair npair ments
                                            ring note)
                                      hist)
                          ;; the point it just made is a point like
                          ;; any other from here - and a later round
                          ;; that moves IT copies it in turn
                          cands (cons (list newpt newnm (car ments))
                                      cands)
                          stage 1))
                  (princ (strcat "\n  Pt." nm " moved to Pt." newnm
                                 " - " (cadr sug)
                                 " held at "
                                 (abf:fmt (cal:dist
                                            (if (= (cadr sug) abf:*a-name*)
                                              pa pb)
                                            newpt))
                                 ", " (caddr sug) " "
                                 (abf:fmt (cadddr sug)) " -> "
                                 (abf:fmt (nth 4 sug)) ".")))))))

         ;; -- put the drawing back the way it was
         (abf:drop temps)
         (setq temps nil)
         (if (and odim (not (equal odim (getvar "DIMSTYLE"))))
           (abf:setstyle odim))
         (setvar "CLAYER"  ocl)
         (setvar "OSMODE"  oos)
         (setvar "CMDECHO" oce)
         (command "_.UNDO" "_End")
         (setq undo-open nil)

         (if (= made 0)
           (princ (strcat "\n" cmd ": nothing dimensioned."))
           (princ (strcat "\n" cmd ": " (itoa made) " point"
                          (if (= made 1) "" "s") " tied to "
                          abf:*a-name* " and " abf:*b-name*
                          " on layer " abf:*layer*
                          (if havestyle
                            (strcat " in style " abf:*style* ".")
                            " (current style)."))))
         (if (> moves 0)
           (princ (strcat "\n" cmd ": " (itoa moves) " point"
                          (if (= moves 1) "" "s") " moved - ringed on "
                          abf:*ring-layer* " where "
                          (if (= moves 1) "it" "they") " came off.")))))))
  (princ))

;;; ---------------------- commands --------------------------------------

(defun c:ABFIND ()
  (abf:run nil))

(defun c:ABMOVE ()
  (abf:run T))

(defun c:ABFINDVER ()
  (princ (strcat "\nABFIND " *abfind-version*
                 "  (commands: ABFIND, ABMOVE)"))
  (princ))

(princ (strcat "\nABFIND " *abfind-version*
               " loaded.  Commands: ABFIND (dim Pt.## from the "
               abf:*a-name* " and " abf:*b-name*
               " stakes), ABMOVE (the same, and move it to where a"
               " misread tape would put it)."))
(princ)


;;; ======================================================================
;;; >>> ALTABCDEF.lsp
;;; ======================================================================

;;; ==========================================================================
;;;  ALTABCDEF.lsp  -  Plot measured points into AutoCAD from an Excel sheet
;;; --------------------------------------------------------------------------
;;;  Points A B C D sit on the corners of a rectangle:
;;;
;;;        A --------- B         A = top-left, then clockwise:
;;;        |           |           B = top-right
;;;        |           |           C = bottom-right
;;;        D --------- C           D = bottom-left
;;;
;;;  Every labelled point in the sheet is located by its distance from each
;;;  of A, B, C and D.  The command asks for the two rectangle dimensions
;;;  A-B (width) and A-D (height), reads a spreadsheet with the columns
;;;
;;;      POINT NAME | DIST FROM A | DIST FROM B | DIST FROM C | DIST FROM D
;;;
;;;  and multilaterates each point.  Because the supplied distances are
;;;  rounded to the nearest 1/4", no single distance can be trusted exactly;
;;;  a least-squares fit is used so the residual error is shared equally
;;;  among all the distances provided for a point (rather than forcing two
;;;  of them to be exact and dumping all the slop on the rest).
;;;
;;;  Distances are entered / stored as architectural feet-inches, e.g.
;;;      12'-3 1/2"      3 1/2"      0'-6"      5'-0 3/4"
;;;
;;;  Command:  ALTABCDEF
;;;
;;; SHARED BUILD: requires CALOFIN-LIB.lsp (load via CALOFIN-LOADER.lsp).
;;; Generic helpers live there under cal: - see STANDARDS.md.
;;;
;;;  All geometry is created in inches (1 drawing unit = 1 inch).
;;; ==========================================================================

(setq *altabcdef-version* "v1.1")   ; announced on load; release_lisp.py
                                       ; stamps the dated twin in releases/

(vl-load-com)

;;; --------------------------------------------------------------------------
;;;  String helpers
;;; --------------------------------------------------------------------------

;; Replace every occurrence of the single char OLD with NEW in S.
(defun altabcdef:replace (s old new / out i c)
  (setq out "" i 1)
  (repeat (strlen s)
    (setq c (substr s i 1))
    (setq out (strcat out (if (= c old) new c)))
    (setq i (1+ i)))
  out)

;; Remove every occurrence of the single char CH from S.
(defun altabcdef:strip (s ch)
  (altabcdef:replace s ch ""))

;; Split S on spaces, returning a list of non-empty tokens.
(defun altabcdef:tokens (s / out tok i c)
  (setq out '() tok "" i 1)
  (repeat (strlen s)
    (setq c (substr s i 1))
    (if (= c " ")
      (progn (if (/= tok "") (setq out (cons tok out))) (setq tok ""))
      (setq tok (strcat tok c)))
    (setq i (1+ i)))
  (if (/= tok "") (setq out (cons tok out)))
  (reverse out))

;;; --------------------------------------------------------------------------
;;;  Dirty-data cleanup helpers (OCR / hand-transcription noise)
;;;
;;;  Field measurements often come back mangled by scanning or re-typing:
;;;    20'_114"      really 20'-1/4"    ( _->-,  114 is 1/4 with / read as 1 )
;;;    1 1'-IO 1/2"  really 11'-10 1/2" ( stray space, I->1, O->0 )
;;;    39'- 8 314"   really 39'-8 3/4"  ( 314 is 3/4 with / read as 1 )
;;;  These helpers repair that noise deterministically before parsing, and
;;;  flag altabcdef:*dirty* so the import can report what it changed.
;;; --------------------------------------------------------------------------

(setq altabcdef:*dirty* nil)   ; set T whenever a value needed cleaning
(setq altabcdef:*fixes* nil)   ; running list of cleanup / warning messages

;; True if S is one or more chars and every char is a digit 0-9.
(defun altabcdef:alldigits (s / ok i a)
  (if (= (strlen s) 0)
    nil
    (progn
      (setq ok T i 1)
      (repeat (strlen s)
        (setq a (ascii (substr s i 1)))
        (if (or (< a 48) (> a 57)) (setq ok nil))
        (setq i (1+ i)))
      ok)))

;; Return the 1-character string for Unicode code point N, but ONLY when this
;; AutoCAD's (chr)/(ascii) round-trip cleanly to that exact point.  On builds
;; where (chr) wraps code points > 255 modulo 256 (some pre-2019 releases),
;; e.g. (chr 8242) -> "2", the round-trip fails and we return nil rather than
;; corrupt real digits.  Everything is caught so it can never raise on load/run.
(defun altabcdef:safechr (n / r a)
  (setq r (vl-catch-all-apply 'chr (list n)))
  (if (or (vl-catch-all-error-p r) (/= (type r) 'STR) (/= (strlen r) 1))
    nil
    (progn
      (setq a (vl-catch-all-apply 'ascii (list r)))
      (if (and (not (vl-catch-all-error-p a)) (= a n)) r nil))))

;; True if S contains only characters a feet-inch value may legitimately hold
;; (digits, space, and  "  '  -  .  / ).  Anything else after scrubbing means a
;; genuinely corrupt cell we should flag rather than silently mis-read.
(defun altabcdef:parseable-p (s / ok i a)
  (setq ok T i 1)
  (repeat (strlen s)
    (setq a (ascii (substr s i 1)))
    (if (not (or (and (>= a 48) (<= a 57))   ; 0-9
                 (= a 32) (= a 34) (= a 39)   ; space  "  '
                 (= a 45) (= a 46) (= a 47))) ; -  .  /
      (setq ok nil))
    (setq i (1+ i)))
  ok)

;; Character-level scrub of a raw cell: letter / underscore / dash look-alikes
;; and the "smart quote" glyphs Excel/Word insert.  No non-ASCII bytes are
;; embedded in this source (some AutoCAD builds refuse to load such files);
;; single-byte look-alikes use (chr), higher code points go through
;; altabcdef:safechr so a build that can't represent them simply skips that pair:
;;   U+2019 ' / U+2032 prime -> '     U+201D " / U+2033 dbl prime -> "
;;   U+2013 en / U+2014 em dash and CP1252 bytes 150/151 -> -
;; These are high-confidence fixes and are NOT flagged as "needs verifying";
;; only the riskier repairs (fraction rebuild, apostrophe-as-1, split feet)
;; set altabcdef:*dirty*.
(defun altabcdef:scrub (raw / s q)
  (setq s raw)
  (setq s (altabcdef:replace s "_" "-"))    ; underscore read for a dash
  (setq s (altabcdef:replace s "O" "0"))    ; letter O -> zero
  (setq s (altabcdef:replace s "o" "0"))
  (setq s (altabcdef:replace s "I" "1"))    ; letter I / l / bar -> one
  (setq s (altabcdef:replace s "l" "1"))
  (setq s (altabcdef:replace s "|" "1"))
  (setq s (altabcdef:replace s (chr 150) "-"))   ; CP1252 en dash byte
  (setq s (altabcdef:replace s (chr 151) "-"))   ; CP1252 em dash byte
  (if (setq q (altabcdef:safechr 8217)) (setq s (altabcdef:replace s q "'")))
  (if (setq q (altabcdef:safechr 8242)) (setq s (altabcdef:replace s q "'")))
  (if (setq q (altabcdef:safechr 8221)) (setq s (altabcdef:replace s q "\"")))
  (if (setq q (altabcdef:safechr 8243)) (setq s (altabcdef:replace s q "\"")))
  (if (setq q (altabcdef:safechr 8211)) (setq s (altabcdef:replace s q "-")))
  (if (setq q (altabcdef:safechr 8212)) (setq s (altabcdef:replace s q "-")))
  s)

;; TOK is an all-digit run with no slash.  A fraction like 3/4 whose slash was
;; scanned as a 1 becomes 314; because that substitution keeps the length, a
;; valid inch fraction (den in 2..32, 0<num<den) has exactly one reconstruction.
;; Return "num/den" if one is found (scanning candidate slash positions left to
;; right), else nil.
(defun altabcdef:defrac (tok / len k num den ni di best)
  (setq len (strlen tok) k 1 best nil)
  (while (and (<= k len) (null best))
    (if (= (substr tok k 1) "1")
      (progn
        (setq num (substr tok 1 (1- k))
              den (substr tok (1+ k)))
        (if (and (> (strlen num) 0) (> (strlen den) 0)
                 (altabcdef:alldigits num) (altabcdef:alldigits den))
          (progn
            (setq ni (atoi num) di (atoi den))
            (if (and (member di '(2 4 8 16 32)) (> ni 0) (< ni di))
              (setq best (strcat num "/" den)))))))
    (setq k (1+ k)))
  best)

;;; --------------------------------------------------------------------------
;;;  Feet-inch parser  ->  inches (real).  Returns nil for an empty OR corrupt
;;;  cell.  MAXD, when supplied, is the largest geometrically-possible distance
;;;  (the rectangle's diagonal); it lets the parser recover a foot mark that was
;;;  scanned as a digit and reject impossible values.
;;;
;;;  Accepts, e.g.:  12'-3 1/2"   3 1/2"   0'-6"   5'-0 3/4"   1/2"   18
;;;  and repairs the dirty forms field data comes back in:
;;;    28-7"         missing foot mark    -> 28'-7"   (dash separates ft/in)
;;;    101-10"       foot mark read as 1  -> 10'-10"  (needs MAXD to detect)
;;;    20'-7 114"    "/" read as 1        -> 20'-7 1/4"
;;;    1 1'-IO 1/2"  split feet / O,I     -> 11'-10 1/2"
;;;  Only the non-obvious repairs set altabcdef:*dirty* (for the change report).
;;; --------------------------------------------------------------------------

(defun altabcdef:ftin->in (raw maxd / s neg feet ftstr rest inch p dp tok
                                    num den slash df val)
  (setq s (altabcdef:scrub (cal:trim raw)))
  (cond
    ((= s "") nil)                              ; blank cell
    ((not (altabcdef:parseable-p s))               ; corrupt char left over
     (setq altabcdef:*dirty* T) nil)
    (T
      (setq neg nil)
      (if (= (substr s 1 1) "-") (setq neg T s (cal:trim (substr s 2))))
      ;; --- split feet from inches ----------------------------------------
      (setq p (vl-string-search "'" s))
      (cond
        (p                                      ; explicit foot mark
          (setq ftstr (cal:trim (substr s 1 p)))
          (if (vl-string-search " " ftstr) (setq altabcdef:*dirty* T))
          (setq feet (atof (altabcdef:strip ftstr " ")))
          (setq rest (cal:trim (substr s (+ p 2)))))
        ((setq dp (vl-string-search "-" s))     ; no ' but a dash: it is the
          (setq ftstr (altabcdef:strip (cal:trim (substr s 1 dp)) " "))
          (if (vl-string-search " " (cal:trim (substr s 1 dp)))
            (setq altabcdef:*dirty* T))            ; feet/inch separator
          (setq feet (atof ftstr))
          (setq rest (cal:trim (substr s (+ dp 2)))))
        (T (setq feet 0.0 ftstr "" rest s)))    ; inches only
      ;; --- clean the inch remainder --------------------------------------
      (if (= (substr rest 1 1) "-") (setq rest (cal:trim (substr rest 2))))
      (setq rest (altabcdef:strip rest "\""))   ; drop inch marks
      (setq rest (altabcdef:strip rest "'"))    ; and a trailing ' misused as one
      (setq rest (altabcdef:replace rest "-" " "))
      (setq rest (cal:trim rest))
      ;; --- inches: sum whole-number and fraction tokens ------------------
      (setq inch 0.0)
      (foreach tok (altabcdef:tokens rest)
        ;; a slash-less all-digit run of 3+ digits is very likely a fraction
        ;; whose "/" was scanned as a "1" (114 -> 1/4); reconstruct it.
        (if (and (not (vl-string-search "/" tok))
                 (>= (strlen tok) 3)
                 (altabcdef:alldigits tok)
                 (setq df (altabcdef:defrac tok)))
          (setq tok df altabcdef:*dirty* T))
        (setq slash (vl-string-search "/" tok))
        (if slash
          (progn
            (setq num (atof (substr tok 1 slash)))
            (setq den (atof (substr tok (+ slash 2))))
            (if (/= den 0.0) (setq inch (+ inch (/ num den)))))
          (setq inch (+ inch (atof tok)))))
      (setq val (+ (* feet 12.0) inch))
      ;; --- foot mark scanned as a "1" ------------------------------------
      ;; e.g. 10'-10" -> "101-10": with no real ' and a value past the
      ;; diagonal, a trailing 1 on the feet was the apostrophe; drop it.
      (if (and maxd (null p) (> val (* maxd 1.05))
               (> (strlen ftstr) 1)
               (= (substr ftstr (strlen ftstr) 1) "1"))
        (progn
          (setq feet (atof (substr ftstr 1 (1- (strlen ftstr))))
                val  (+ (* feet 12.0) inch)
                altabcdef:*dirty* T)))
      (if neg (setq val (- val)))
      ;; --- final sanity: non-positive or still impossible -> unreadable --
      (if (or (<= val 0.0) (and maxd (> val (* maxd 1.1))))
        (progn (setq altabcdef:*dirty* T) nil)
        val))))

;;; --------------------------------------------------------------------------
;;;  Format inches back to a feet-inch string (for the correction log), to the
;;;  nearest 1/32", reduced.  e.g. 476.75 -> 39'-8 3/4"
;;; --------------------------------------------------------------------------

(defun altabcdef:in->ftin (v / neg feet whole frac n den ft s)
  (setq neg (< v 0.0) v (abs v))
  (setq n (fix (+ (* v 32.0) 0.5)))      ; total 1/32" units, rounded
  (setq feet (fix (/ n 384)))            ; 384 = 32*12
  (setq n (- n (* feet 384)))
  (setq whole (fix (/ n 32)))
  (setq n (- n (* whole 32)))            ; leftover 1/32 units, 0..31
  (setq den 32)
  (while (and (> n 0) (= (rem n 2) 0)) (setq n (/ n 2) den (/ den 2)))
  (setq s (strcat (itoa feet) "'-" (itoa whole)))
  (if (> n 0) (setq s (strcat s " " (itoa n) "/" (itoa den))))
  (setq s (strcat s "\""))
  (if neg (strcat "-" s) s))

;;; --------------------------------------------------------------------------
;;;  Multilateration
;;;
;;;  CORNERS : list of (x y) corner coordinates that have a distance
;;;  DISTS   : matching list of measured distances
;;;  Returns : (x y rms res1 res2 ...)  in the same local frame as CORNERS.
;;;
;;;  A linear (circle-difference) solution seeds a Gauss-Newton refinement
;;;  of  min  S( |P-Ci| - di )^2 , which is exactly "spread the rounding
;;;  error evenly over the distances".  Needs >= 2 corners; 3+ give a unique
;;;  fix.  With only 2, the frame centre is used as the seed so the interior
;;;  intersection is chosen.
;;; --------------------------------------------------------------------------

(defun altabcdef:solve (corners dists cx cy / n x y i c d dx dy r jx jy f
                             saa sab sbb sac sbc a b cc det xr yr dr
                             jaa jab jbb ga gb ddx ddy res rms iter)
  (setq n (length corners))
  ;; ---- seed --------------------------------------------------------------
  (if (>= n 3)
    (progn                                   ; linear least squares seed
      (setq xr (car (car corners)) yr (cadr (car corners)) dr (car dists))
      (setq saa 0.0 sab 0.0 sbb 0.0 sac 0.0 sbc 0.0 i 1)
      (while (< i n)
        (setq c (nth i corners) d (nth i dists))
        (setq a (* 2.0 (- (car c) xr))
              b (* 2.0 (- (cadr c) yr))
              cc (- (- (+ (* (car c) (car c)) (* (cadr c) (cadr c)))
                       (+ (* xr xr) (* yr yr)))
                    (- (* d d) (* dr dr))))
        (setq saa (+ saa (* a a)) sab (+ sab (* a b)) sbb (+ sbb (* b b))
              sac (+ sac (* a cc)) sbc (+ sbc (* b cc)))
        (setq i (1+ i)))
      (setq det (- (* saa sbb) (* sab sab)))
      (if (> (abs det) 1e-9)
        (setq x (/ (- (* sac sbb) (* sbc sab)) det)
              y (/ (- (* saa sbc) (* sab sac)) det))
        (setq x cx y cy)))                    ; degenerate -> centre
    (setq x cx y cy))                         ; only 2 circles -> centre seed
  ;; ---- Gauss-Newton refinement ------------------------------------------
  (setq iter 0)
  (while (< iter 60)
    (setq jaa 0.0 jab 0.0 jbb 0.0 ga 0.0 gb 0.0 i 0)
    (while (< i n)
      (setq c (nth i corners) d (nth i dists))
      (setq dx (- x (car c)) dy (- y (cadr c)) r (sqrt (+ (* dx dx) (* dy dy))))
      (if (< r 1e-9) (setq r 1e-9))
      (setq jx (/ dx r) jy (/ dy r) f (- r d))
      (setq jaa (+ jaa (* jx jx)) jab (+ jab (* jx jy)) jbb (+ jbb (* jy jy))
            ga (+ ga (* jx f)) gb (+ gb (* jy f)))
      (setq i (1+ i)))
    (setq det (- (* jaa jbb) (* jab jab)))
    (if (< (abs det) 1e-12)
      (setq iter 60)                          ; singular -> stop
      (progn
        (setq ddx (/ (- (- (* ga jbb)) (- (* gb jab)))
                     det)
              ddy (/ (- (- (* jaa gb)) (- (* jab ga)))
                     det))
        ;; ddx = -(ga*jbb - gb*jab)/det ; ddy = -(jaa*gb - jab*ga)/det
        (setq x (+ x ddx) y (+ y ddy))
        (if (and (< (abs ddx) 1e-7) (< (abs ddy) 1e-7)) (setq iter 60))))
    (setq iter (1+ iter)))
  ;; ---- residuals ---------------------------------------------------------
  (setq res '() rms 0.0 i 0)
  (while (< i n)
    (setq c (nth i corners) d (nth i dists))
    (setq f (- (sqrt (+ (expt (- x (car c)) 2) (expt (- y (cadr c)) 2))) d))
    (setq res (cons f res) rms (+ rms (* f f)) i (1+ i)))
  (setq rms (sqrt (/ rms n)))
  (cons x (cons y (cons rms (reverse res)))))

;;; --------------------------------------------------------------------------
;;;  Drawing helpers
;;; --------------------------------------------------------------------------

;; Make sure a layer exists (create it with COLOR if not).
(defun altabcdef:layer (name color)
  (if (not (tblsearch "LAYER" name))
    (entmake (list '(0 . "LAYER") '(100 . "AcDbSymbolTableRecord")
                   '(100 . "AcDbLayerTableRecord") (cons 2 name)
                   '(70 . 0) (cons 62 color) '(6 . "Continuous")))))

(defun altabcdef:point (pt layer)
  (entmake (list '(0 . "POINT") (cons 8 layer)
                 (cons 10 (list (car pt) (cadr pt) 0.0)))))

(defun altabcdef:circle (pt rad layer)
  (entmake (list '(0 . "CIRCLE") (cons 8 layer)
                 (cons 10 (list (car pt) (cadr pt) 0.0)) (cons 40 rad))))

(defun altabcdef:text (pt hgt str layer)
  (entmake (list '(0 . "TEXT") (cons 8 layer)
                 (cons 10 (list (car pt) (cadr pt) 0.0))
                 (cons 11 (list (car pt) (cadr pt) 0.0))
                 (cons 40 hgt) (cons 1 str) (cons 72 0) (cons 73 0))))

;; Closed 4-vertex polyline A B C D.
(defun altabcdef:frame (a b c d layer)
  (entmake (list '(0 . "LWPOLYLINE") '(100 . "AcDbEntity") (cons 8 layer)
                 '(100 . "AcDbPolyline") '(90 . 4) '(70 . 1)
                 (cons 10 a) (cons 10 b) (cons 10 c) (cons 10 d))))

;;; --------------------------------------------------------------------------
;;;  Excel reading (via COM automation)
;;;
;;;  Returns a list of rows, each  (name dA dB dC dD)  where any dX is a real
;;;  (inches) or nil when that cell was blank.  Column order is discovered
;;;  from the header row, so the sheet's columns may be in any order as long
;;;  as the headers contain NAME / FROM A / FROM B / FROM C / FROM D.
;;; --------------------------------------------------------------------------

;; Coerce a COM cell value to a trimmed string.
(defun altabcdef:cellstr (v)
  (cond ((null v) "")
        ((= (type v) 'STR) (cal:trim v))
        ((= (type v) 'REAL) (cal:trim (rtos v 2 6)))
        ((= (type v) 'INT) (itoa v))
        (T "")))

(defun altabcdef:xl-cell (sheet r c / res)
  (setq res (vl-catch-all-apply
              '(lambda ()
                 (vlax-variant-value
                   (vlax-get-property
                     (vlax-get-property
                       (vlax-get-property sheet "Cells") "Item" r c)
                     "Text")))))
  (if (vl-catch-all-error-p res) "" (altabcdef:cellstr res)))

;; Classify a header cell (already upper-cased) as 'name / 'a / 'b / 'c / 'd.
(defun altabcdef:col-of (up)
  (cond ((vl-string-search "FROM A" up) 'a)
        ((vl-string-search "FROM B" up) 'b)
        ((vl-string-search "FROM C" up) 'c)
        ((vl-string-search "FROM D" up) 'd)
        ((or (vl-string-search "NAME" up) (vl-string-search "POINT" up)
             (vl-string-search "LABEL" up)) 'name)
        (T nil)))

;; nth (1-based) element of a list, or "" when the index is nil / out of range.
(defun altabcdef:nth-field (lst idx)
  (if (and idx (> idx 0) (<= idx (length lst))) (nth (1- idx) lst) ""))

;; Print the accumulated cleanup / unreadable report (if any).
(defun altabcdef:report-fixes (/ m)
  (if altabcdef:*fixes*
    (progn
      (princ "\n\n--- dirty values cleaned before import ---")
      (foreach m (reverse altabcdef:*fixes*) (princ (strcat "\n" m)))
      (princ "\n  ( * = auto-corrected, ? = unreadable. Verify these! )"))))

;; Parse RAW to inches, logging into altabcdef:*fixes* if the value had to be
;; cleaned up (a risky repair) or could not be read at all.  LABEL identifies
;; the cell in the log, e.g. "P3 / FROM C".  MAXD is the rectangle diagonal.
(defun altabcdef:parse-log (raw label maxd / clean v)
  (setq clean (cal:trim raw))
  (if (= clean "")
    nil                                     ; blank cell: not measured
    (progn
      (setq altabcdef:*dirty* nil)
      (setq v (altabcdef:ftin->in raw maxd))
      (cond
        ((null v)                           ; nonblank but unreadable
         (setq altabcdef:*fixes*
               (cons (strcat "  ? " label ": \"" clean
                             "\"  could not be read - left blank")
                     altabcdef:*fixes*)))
        (altabcdef:*dirty*                     ; cleaned something up
         (setq altabcdef:*fixes*
               (cons (strcat "  * " label ": \"" clean "\"  ->  "
                             (altabcdef:in->ftin v))
                     altabcdef:*fixes*))))
      v)))

;;; --------------------------------------------------------------------------
;;;  Native CSV reading (no Excel needed).  Preferred for .csv because it also
;;;  avoids Excel silently turning cells like "28-11" or "7-0" into dates.
;;; --------------------------------------------------------------------------

;; Split one CSV line into a list of field strings, honouring "quoted" fields
;; and "" escaped quotes.
(defun altabcdef:parse-csv-line (line / fields cur i n c inq)
  (setq fields '() cur "" i 1 n (strlen line))
  ;; state: inq = inside a quoted field
  (setq inq nil)
  (while (<= i n)
    (setq c (substr line i 1))
    (cond
      (inq
        (if (= c "\"")
          (if (= (substr line (1+ i) 1) "\"")   ; "" -> literal quote
            (progn (setq cur (strcat cur "\"")) (setq i (1+ i)))
            (setq inq nil))
          (setq cur (strcat cur c))))
      ((= c "\"") (setq inq T))
      ((= c ",") (setq fields (cons cur fields) cur ""))
      (T (setq cur (strcat cur c))))
    (setq i (1+ i)))
  (setq fields (cons cur fields))
  (reverse fields))

(defun altabcdef:read-csv (file maxd / fp line fields i h up kind
                                    name-c a-c b-c c-c d-c rows nm)
  (setq fp (open file "r"))
  (if (null fp)
    (progn (princ "\n** Could not open the file for reading.") nil)
    (progn
      (setq name-c nil a-c nil b-c nil c-c nil d-c nil)
      ;; --- header row (skip any leading blank lines) --------------------
      (setq line (read-line fp))
      (while (and line (= (cal:trim (altabcdef:strip line (chr 13))) ""))
        (setq line (read-line fp)))
      (if line
        (progn
          (setq fields (altabcdef:parse-csv-line (altabcdef:strip line (chr 13))) i 1)
          (foreach h fields
            (setq up (strcase (cal:trim h)) kind (altabcdef:col-of up))
            (cond ((and (eq kind 'name) (null name-c)) (setq name-c i))
                  ((eq kind 'a) (setq a-c i))
                  ((eq kind 'b) (setq b-c i))
                  ((eq kind 'c) (setq c-c i))
                  ((eq kind 'd) (setq d-c i)))
            (setq i (1+ i)))))
      (if (null name-c) (setq name-c 1))     ; fall back to first column
      ;; --- data rows -----------------------------------------------------
      (setq rows '() altabcdef:*fixes* '())
      (while (setq line (read-line fp))
        (setq line (altabcdef:strip line (chr 13)))
        (if (/= (cal:trim line) "")
          (progn
            (setq fields (altabcdef:parse-csv-line line))
            (setq nm (cal:trim (altabcdef:nth-field fields name-c)))
            (if (/= nm "")
              (setq rows
                (cons (list nm
                    (altabcdef:parse-log (altabcdef:nth-field fields a-c)
                                      (strcat nm " / FROM A") maxd)
                    (altabcdef:parse-log (altabcdef:nth-field fields b-c)
                                      (strcat nm " / FROM B") maxd)
                    (altabcdef:parse-log (altabcdef:nth-field fields c-c)
                                      (strcat nm " / FROM C") maxd)
                    (altabcdef:parse-log (altabcdef:nth-field fields d-c)
                                      (strcat nm " / FROM D") maxd))
                      rows))))))
      (close fp)
      (altabcdef:report-fixes)
      (reverse rows))))

;;; --------------------------------------------------------------------------
;;;  Dispatcher: pick the CSV reader for .csv, else Excel COM automation.
;;; --------------------------------------------------------------------------
(defun altabcdef:read-file (file maxd / ext n)
  (setq n (strlen file) ext "")
  (if (> n 4) (setq ext (strcase (substr file (- n 3)))))
  (if (= ext ".CSV")
    (altabcdef:read-csv file maxd)
    (altabcdef:read-excel file maxd)))

(defun altabcdef:read-excel (file maxd / xl created wbs wb sheet used rng nrows ncols
                                  hdr r c txt up kind name-c a-c b-c d-c c-c
                                  rows nm da db dc dd err m)
  ;; connect to an existing Excel, else start one
  (setq xl (vl-catch-all-apply 'vlax-get-object (list "Excel.Application")))
  (if (vl-catch-all-error-p xl)
    (progn (setq xl (vlax-create-object "Excel.Application") created T)))
  (if (or (null xl) (vl-catch-all-error-p xl))
    (progn (princ "\n** Could not start Excel (is it installed?).") nil)
    (progn
      (vl-catch-all-apply '(lambda () (vlax-put-property xl "Visible" :vlax-false)))
      (vl-catch-all-apply '(lambda () (vlax-put-property xl "DisplayAlerts" :vlax-false)))
      (setq err (vl-catch-all-apply
                  '(lambda ()
                     (setq wbs (vlax-get-property xl "Workbooks"))
                     (setq wb (vlax-invoke-method wbs "Open" file))
                     (setq sheet (vlax-get-property wb "ActiveSheet"))
                     (setq used (vlax-get-property sheet "UsedRange"))
                     ;; widen columns so "Text" is never truncated to ####
                     (vl-catch-all-apply
                       '(lambda () (vlax-invoke-method
                                     (vlax-get-property used "Columns") "AutoFit")))
                     (setq nrows (vlax-get-property
                                   (vlax-get-property used "Rows") "Count"))
                     (setq ncols (vlax-get-property
                                   (vlax-get-property used "Columns") "Count")))))
      (if (vl-catch-all-error-p err)
        (progn
          (princ (strcat "\n** Could not open the spreadsheet: "
                         (vl-catch-all-error-message err)))
          (if created (vl-catch-all-apply '(lambda () (vlax-invoke-method xl "Quit"))))
          nil)
        (progn
          ;; --- locate columns from the header row ------------------------
          (setq name-c nil a-c nil b-c nil c-c nil d-c nil c 1)
          (while (<= c ncols)
            (setq up (strcase (altabcdef:xl-cell sheet 1 c)) kind (altabcdef:col-of up))
            (cond ((and (eq kind 'name) (null name-c)) (setq name-c c))
                  ((eq kind 'a) (setq a-c c))
                  ((eq kind 'b) (setq b-c c))
                  ((eq kind 'c) (setq c-c c))
                  ((eq kind 'd) (setq d-c c)))
            (setq c (1+ c)))
          (if (null name-c) (setq name-c 1))   ; fall back to first column
          ;; --- read the data rows ----------------------------------------
          (setq rows '() altabcdef:*fixes* '() r 2)
          (while (<= r nrows)
            (setq nm (altabcdef:xl-cell sheet r name-c))
            (if (/= nm "")
              (setq rows
                (cons (list nm
                    (if a-c (altabcdef:parse-log (altabcdef:xl-cell sheet r a-c)
                                              (strcat nm " / FROM A") maxd))
                    (if b-c (altabcdef:parse-log (altabcdef:xl-cell sheet r b-c)
                                              (strcat nm " / FROM B") maxd))
                    (if c-c (altabcdef:parse-log (altabcdef:xl-cell sheet r c-c)
                                              (strcat nm " / FROM C") maxd))
                    (if d-c (altabcdef:parse-log (altabcdef:xl-cell sheet r d-c)
                                              (strcat nm " / FROM D") maxd)))
                      rows)))
            (setq r (1+ r)))
          (altabcdef:report-fixes)
          ;; --- close up --------------------------------------------------
          (vl-catch-all-apply '(lambda () (vlax-invoke-method wb "Close" :vlax-false)))
          (if created (vl-catch-all-apply '(lambda () (vlax-invoke-method xl "Quit"))))
          (vl-catch-all-apply '(lambda () (vlax-release-object wb)))
          (vl-catch-all-apply '(lambda () (vlax-release-object wbs)))
          (vl-catch-all-apply '(lambda () (vlax-release-object xl)))
          (reverse rows))))))

;;; --------------------------------------------------------------------------
;;;  Prompt helper: read a feet-inch dimension from the keyboard.
;;; --------------------------------------------------------------------------

;; With BACK non-nil, typing B (Back; Undo works too) returns the
;; symbol AB-BACK so the caller can re-open its previous question.
(defun altabcdef:getdim (prompt back / s v)
  (setq v nil)
  (while (null v)
    (setq s (getstring T (strcat "\n" prompt " (e.g. 20'-6\""
                                 (if back ", B = back" "") "): ")))
    (cond
      ((and back (member (strcase s) '("B" "BACK" "U" "UNDO")))
       (setq v 'AB-BACK))
      (T
       (setq v (altabcdef:ftin->in s nil))
       (if (or (null v) (<= v 0.0))
         (progn (princ "  ** enter a positive dimension, e.g. 20'-6\"")
                (setq v nil))))))
  v)

;;; --------------------------------------------------------------------------
;;;  Main command
;;; --------------------------------------------------------------------------

(defun c:ALTABCDEF (/ *error* undo-open file rows base bpx bpy W H
                    Ax Ay Bx By Cx Cy Dx Dy th mrad
                    good bad r nm din corners dists lbl
                    sol x y rms i tags tg p placed stage done)
  (vl-load-com)
  ;; the plot is one undo group, so a cancelled run backs out with a
  ;; single U instead of one per entity; the group is only closed if it
  ;; was opened (STANDARDS section 5)
  (defun *error* (msg)
    (if undo-open (command "_.UNDO" "_End"))
    (setq undo-open nil)
    (if (and msg (not (wcmatch (strcase msg)
                               "*BREAK*,*CANCEL*,*QUIT*,*EXIT*")))
        (princ (strcat "\nALTABCDEF error: " msg)))
    (princ))
  (command "_.UNDO" "_Begin")
  (setq undo-open T)
  ;; ---- the questions, staged: Back (or Undo) at a later prompt
  ;; ---- re-opens the previous one, back to the file dialog itself
  (setq stage 1 done nil)
  (while (not done)
    (cond
      ;; ---- get the spreadsheet ------------------------------------------
      ((= stage 1)
       (setq file (getfiled "Select points spreadsheet"
                            "" "xlsx;xls;xlsm;csv" 16))
       (if (null file)
         (setq done 'quit)
         (progn
           ;; ---- rectangle dimensions ------------------------------------
           (princ "\n--- Rectangle A(top-left) B(top-right) C(bottom-right) D(bottom-left) ---")
           (setq stage 2))))
      ((= stage 2)
       (setq W (altabcdef:getdim "Dimension A-B (width across the top)" T))
       (if (eq W 'AB-BACK) (setq stage 1) (setq stage 3)))
      ((= stage 3)
       (setq H (altabcdef:getdim "Dimension A-D (height down the side)" T))
       (if (eq H 'AB-BACK) (setq stage 2) (setq stage 4)))
      ;; ---- where does corner A land? -------------------------------------
      ;; take the pick in WCS so the rectangle is built square to the world
      ;; axes even when the current UCS is rotated (entmake writes WCS).
      (T
       (initget "Back Undo")
       (setq base (getpoint "\nInsertion point for corner A <0,0> [Back]: "))
       (if (= (type base) 'STR) (setq stage 3) (setq done T)))))
  (if (eq done 'quit)
    (progn (princ "\nCancelled.") (princ))
    (progn
      (if base (setq base (trans base 1 0)) (setq base '(0.0 0.0 0.0)))
      (setq bpx (car base) bpy (cadr base))
      ;; corner coordinates: A top-left, clockwise, Y up (A-D goes down).
      ;; A-B is horizontal, A-D is vertical -> all four corners are 90 degrees.
      (setq Ax bpx        Ay bpy
            Bx (+ bpx W)  By bpy
            Cx (+ bpx W)  Cy (- bpy H)
            Dx bpx        Dy (- bpy H))
      ;; ---- read the sheet ------------------------------------------------
      ;; the rectangle diagonal is the largest distance any point can be from a
      ;; corner; pass it so the parser can spot a foot mark scanned as a digit
      ;; and reject impossible readings.
      (princ "\nReading spreadsheet ... ")
      (setq rows (altabcdef:read-file file (sqrt (+ (* W W) (* H H)))))
      (if (null rows)
        (progn (princ "\nNo usable rows found - nothing plotted.") (princ))
        (progn
          (princ (strcat (itoa (length rows)) " row(s) found."))
          ;; ---- layers & sizing --------------------------------------------
          (altabcdef:layer "ALTABCDEF-FRAME"  1)     ; red
          (altabcdef:layer "ALTABCDEF-POINTS" 2)     ; yellow
          (altabcdef:layer "ALTABCDEF-LABELS" 3)     ; green
          (setq th (/ (max W H) 120.0))        ; text height
          (if (< th 0.5) (setq th 0.5))
          (setq mrad (* th 0.4))               ; marker radius
          ;; ---- draw the rectangle + corner tags ---------------------------
          (altabcdef:frame (list Ax Ay) (list Bx By) (list Cx Cy) (list Dx Dy)
                        "ALTABCDEF-FRAME")
          (setq tags (list (list "A" Ax Ay (* -1 th) th)
                           (list "B" Bx By th th)
                           (list "C" Cx Cy th (* -1.6 th))
                           (list "D" Dx Dy (* -1 th) (* -1.6 th))))
          (foreach tg tags
            (altabcdef:text (list (+ (nth 1 tg) (nth 3 tg))
                               (+ (nth 2 tg) (nth 4 tg)))
                         (* th 1.4) (car tg) "ALTABCDEF-FRAME"))
          ;; ---- plot each measured point -----------------------------------
          (setq good 0 bad 0 placed '())
          (foreach r rows
            (setq nm (car r) din (cdr r))
            ;; build parallel corner / distance lists for the provided dims
            (setq corners '() dists '())
            (if (nth 0 din) (setq corners (cons (list Ax Ay) corners)
                                  dists   (cons (nth 0 din) dists)))
            (if (nth 1 din) (setq corners (cons (list Bx By) corners)
                                  dists   (cons (nth 1 din) dists)))
            (if (nth 2 din) (setq corners (cons (list Cx Cy) corners)
                                  dists   (cons (nth 2 din) dists)))
            (if (nth 3 din) (setq corners (cons (list Dx Dy) corners)
                                  dists   (cons (nth 3 din) dists)))
            (if (>= (length corners) 2)
              (progn
                (setq sol (altabcdef:solve (reverse corners) (reverse dists)
                                        (+ bpx (/ W 2.0)) (- bpy (/ H 2.0))))
                (setq x (car sol) y (cadr sol) rms (caddr sol))
                (altabcdef:point  (list x y) "ALTABCDEF-POINTS")
                (altabcdef:circle (list x y) mrad "ALTABCDEF-POINTS")
                (altabcdef:text   (list (+ x (* mrad 1.4)) (+ y (* mrad 1.4)))
                               th nm "ALTABCDEF-LABELS")
                (setq placed (cons (list nm x y rms (length corners)) placed))
                (setq good (1+ good)))
              (progn
                (princ (strcat "\n  ! " nm
                               " : fewer than 2 distances given - skipped."))
                (setq bad (1+ bad)))))
          ;; ---- report ------------------------------------------------------
          (princ "\n\n===== ALTABCDEF results (all values in inches) =====")
          (princ "\n  POINT            X          Y      #dims   fit err (RMS)")
          (foreach p (reverse placed)
            (princ (strcat "\n  " (cal:pad (nth 0 p) 14)
                           (altabcdef:padnum (nth 1 p) 10)
                           (altabcdef:padnum (nth 2 p) 11)
                           "    " (itoa (nth 4 p))
                           "      " (rtos (nth 3 p) 2 4) "\"")))
          (princ (strcat "\n-------------------------------------------------"
                         "\n  " (itoa good) " point(s) plotted"
                         (if (> bad 0) (strcat ", " (itoa bad) " skipped") "")
                         "."))
          (princ (strcat "\n  Fit err (RMS) is the leftover rounding error shared"
                         "\n  across the given distances - typically < 0.10\" for"
                         "\n  quarter-inch data.  A large value means a bad reading."))
          ;; ---- confirm the frame is a true rectangle ----------------------
          ;; A-B is horizontal and A-D is vertical, so every corner is exactly
          ;; 90 deg.  If it looked like a parallelogram, the view was a tilted
          ;; 3D orbit (a flat rectangle foreshortens) - reset to plan so it
          ;; reads square.  Geometry is unchanged.
          (princ (strcat "\n\n  Frame A-B-C-D: true rectangle "
                         (rtos W 2 2) "\" (A-B) x " (rtos H 2 2)
                         "\" (A-D), all corners 90.00 deg."))
          ;; vl-catch-all-apply takes the argument list as its second argument;
          ;; called with only the lambda it raises "too few arguments" and
          ;; takes the end of the run down with it, which is exactly what
          ;; the catch was there to prevent.
          (vl-catch-all-apply
            '(lambda ()
               (vl-cmdf "_.plan" "_World")
               (vl-cmdf "_.zoom" "_Extents"))
            '())
          (princ "\n  View reset to plan (top) so the rectangle shows square.")
          (princ)))))
  (if undo-open (command "_.UNDO" "_End"))
  (setq undo-open nil)
  (princ))

;; format a real to 3 decimals, left-padded into WIDTH
(defun altabcdef:padnum (v width / s)
  (setq s (rtos v 2 3))
  (while (< (strlen s) width) (setq s (strcat " " s)))
  s)

(princ "\nALTABCDEF.lsp loaded.  Type ALTABCDEF to plot points from a spreadsheet.")
(princ)


;;; ======================================================================
;;; >>> abhd.lsp
;;; ======================================================================

;;; ===================================================================
;;; ABHD.LSP  --  Fit a pool perimeter through surveyed points
;;; -------------------------------------------------------------------
;;; For AutoCAD 2018 and later (plain AutoLISP, no external libraries).
;;;
;;; Commands:  ABHD - fit the perimeter, then optionally the bottom
;;;            ADAB - the pool bottom on its own, over an existing
;;;                   perimeter (select the closed polyline or its
;;;                   exploded lines/arcs; the survey points sitting
;;;                   on it are found automatically)
;;;
;;; SHARED BUILD: requires CALOFIN-LIB.lsp (load via CALOFIN-LOADER.lsp).
;;; Generic helpers live there under cal: - see STANDARDS.md.
;;;
;;; The user window-selects an area containing:
;;;   * On layer "POOL"   : (optional) a closed perimeter drawn as ONE
;;;                         closed polyline OR an exploded set of
;;;                         LINEs/ARCs.
;;;   * On layer "POINTS" : POINT entities surveyed on the real pool
;;;                         edge.
;;;
;;; TWO MODES, chosen automatically from the selection:
;;;   * GUIDED  - the selection contains POOL geometry: the drawn
;;;               shape is used as the guide and re-fitted through the
;;;               points (described below).
;;;   * POINTS-ONLY - the selection contains no POOL geometry: the
;;;               program orders the points into a closed loop by
;;;               itself (nearest-neighbour tour + 2-opt uncrossing)
;;;               and covers them with as FEW long, overarching ARCS
;;;               as possible - each arc is grown to take in as many
;;;               consecutive points as it can hold.  No straight
;;;               lines are drawn (organic shapes have none); the only
;;;               exception is a stretch between two sharp corners
;;;               with no points in between, where an arc would be
;;;               pure invention.
;;;
;;; ON THE POINTS FIRST: every arc endpoint sits ON a survey point,
;;; and each arc is chosen so its MIDDLE passes exactly through one of
;;; its interior points too (a true 3-point arc) whenever such an arc
;;; holds the span.  Arcs that float between the points are a last
;;; resort and must cover at least 2 more points to be chosen - they
;;; should be the rare exception (roughly 1 arc in 10), not the rule.
;;;
;;; NEAR-TANGENT SMOOTHNESS: at every joint the new arc must start
;;; within *PF-TANG-TOL* (8 degrees) of the previous arc's end
;;; tangent - close enough to look smooth, loose enough that the
;;; points stay in charge.  Sharp corners (over *PF-CORNER-ANG*) stay
;;; free kinks; the closing seam is held to the same window (the fit
;;; is re-run once with a seeded start tangent when the seam comes
;;; out worse).
;;;
;;; NICE RADII: arc radii are snapped to friendly increments before a
;;; free ("weird") number is accepted - whole feet first, then half
;;; feet, then whole inches (*PF-NICE-RADII*, drawing units = inches).
;;; The points outrank pretty radii: a snap may move covered points at
;;; most *PF-SNAP-EPS* beyond where they already sat and may never
;;; pull an arc off its anchor point; endpoints never move.
;;;
;;; THE MISS ALLOWANCE: the perimeter no longer has to thread every
;;; point exactly.  A share of the points - asked per run, standard
;;; *PF-MISS-PCT* (15%), rounded UP to the nearest whole point - may
;;; sit off the result by up to the max distance (default 1 unit =
;;; about an inch, capped at *PF-TOL-MAX*); every other point stays on
;;; it (within *PF-ON-EPS*).  That slack is spent where it buys the
;;; most: longer arcs, fewer curves, nicer radii.
;;;
;;; DECLARED STRAIGHT WALLS: the user may declare dead-straight walls
;;; up front by picking their two end points; each is marked with a
;;; dashed line on *PF-WALL-LAYER* and comes out of the points-built
;;; fit as a straight LINE between exactly those two survey points -
;;; arcs never swallow or cross a declared wall.
;;;
;;; HELD POINTS: the user may also declare points that must be held
;;; ABSOLUTELY - control shots, tie-ins, anything surveyed as an
;;; exact position.  A held point is never buried inside a span, so
;;; every span ends ON it and the fitted line passes through it
;;; exactly, in every candidate; it costs nothing from the miss
;;; allowance and the tangency window still applies at its joint (it
;;; is not a corner).  In guided mode the drawn shape wins, as with
;;; declared walls - held points steer the points-built fit - and the
;;; report flags any held point the kept fit did not land on.
;;;
;;; THE CURVE CAP: the command also asks for a maximum number of
;;; curves ("None" = unlimited).  When a fit needs more, the whole
;;; loop is refitted with a progressively relaxed tolerance until the
;;; cap holds - merging arcs would break their tangency, so the chain
;;; is rebuilt instead and stays smooth.  The cap wins over the
;;; tolerance; whatever error it forces is shown in the hit report.
;;; The cap binds in EVERY mode: a guided run whose drawn perimeter
;;; needs more curves falls back to fitting from the points (the
;;; drawn shape still orders them), and an unreachably small cap
;;; returns the fewest-curves fit found - never the full-size one.
;;;
;;; THE THREE CANDIDATES: how much curve to spend on how much accuracy
;;; is a judgement, not a setting, so all three answers are drawn and
;;; the user points at one (*PF-COMPARE*).  Fit 1 is the accurate end:
;;; it fits to *PF-TIGHT-TOL*, writes off no point at all, and obeys
;;; neither the typed distance nor the curve cap - the most curves for
;;; the least error there is.  Fit 2 is the settings exactly as typed,
;;; cap included.  Fit 3 is the economical end: the same typed
;;; distance, but with the miss allowance and its per-span fair share
;;; lifted, so arcs run as long as that distance allows - the fewest
;;; curves that still hold it.  All three are then MEASURED against
;;; the typed distance, so the table compares like for like.
;;;
;;; The command rebuilds the perimeter as a single closed LWPOLYLINE
;;; (lines + arcs only, no splines); the candidates preview on layer
;;; "POOL-FIT" and the kept one moves onto the POOL layer:
;;;   * Every polyline vertex is snapped to the nearest surveyed point
;;;     within the tolerance (default 1 unit = 1 inch), so corners land
;;;     exactly on points whenever one is close enough.
;;;   * Every curved (arc/bulge) segment is re-fitted so that the arc
;;;     passes through the surveyed points lying along it.  A single
;;;     replacement arc is tried first (the best of the exact 3-point
;;;     arcs through the two snapped endpoints and the points, plus
;;;     their average), with its radius snapped to a nice increment
;;;     when possible; if it keeps every point within the tolerance
;;;     and the miss allowance can absorb the off ones, that ONE arc
;;;     is kept.  Only when that fails is the segment SUBDIVIDED into
;;;     a tangent-continuous chain of arcs through every point.
;;;   * Straight segments the user drew are trusted and kept straight
;;;     (only their endpoints snap to points); where the user found a
;;;     straight wall, the result has a straight wall.
;;;   * A point that turns more than *PF-CORNER-ANG* (45 deg) is a
;;;     sharp corner: it can start or end a span but is never buried
;;;     inside one, so polygonal shapes keep their corners as lines.
;;; Everything is fitted on the 2D plane - Z coordinates are ignored.
;;; Every segment shares its endpoints with its neighbours, so the
;;; result stays closed.
;;;
;;; A hit report is printed: how many points the new perimeter passes
;;; through exactly, how many are within tolerance, how many missed.
;;;
;;; THE POOL BOTTOM: once a perimeter is kept, the command offers to
;;; draw the floor too (Enter = No).  The user picks the two ends of
;;; the SHALLOW BREAK and the DEEP BREAK; the hopper - the flat
;;; deep-end floor - lies beyond the deep break, away from the
;;; shallow.  Its back is found automatically (the survey point
;;; nearest a perpendicular ray cast from the middle of the deep
;;; break), and three offsets - asked by point number, one at each
;;; deep break point, one at the back - pull the hopper in from the
;;; perimeter, blending gradually where they differ.  Slope lines
;;; join the hopper's ends to the shallow break points - each side is
;;; asked whether its line runs STRAIGHT, GUIDED (following the
;;; perimeter's curve, the offset easing to nothing at the shallow
;;; break), or through POINTS the user picks along that side, each
;;; with its own offset measured square off the wall - the line still
;;; runs guided between them.  Every prompt in the flow after the
;;; first offers Back ([Back] at the picks and choices, B typed at
;;; the offsets; Undo works too), re-opening the previous question -
;;; and in the POINTS loop, Back un-picks the last waypoint.  The
;;; hopper and the guided slopes are merged into as FEW long arcs as
;;; hold their shape (within *PF-BOTTOM-FIT*) - curves, not facets,
;;; and not many of them.
;;; Everything - the bottom's lines, the dimensions, and the kept
;;; perimeter itself - ends up on *PF-POOL-LAYER* (the deep break
;;; stubs dashed).
;;; ===================================================================

;; ---- configuration -------------------------------------------------
(setq pf:*version*      "082726 REV08") ; announced on load.  The
                                    ; versioned twin of this file is
                                    ; named ABHD_<MMDDYY>_REV<##>.lsp
                                    ; so anyone can see which iteration
                                    ; is in a colleague's stack; bump
                                    ; this with every revision and
                                    ; re-copy the file so the twins
                                    ; stay identical (the tests check
                                    ; the name, the match, and this)
;; Cover mode: the pool-bottom question in pf:bottom answers No without
;; being asked, so a cover sheet is fitted to its perimeter and stops
;; there.  Set by ABHDCOVER, cleared on both exits from c:ABHD; nil for
;; a typed ABHD, always.
(setq abhd:*nobottom* nil)

(setq *PF-POOL-LAYER*   "POOL")     ; layer holding the drawn perimeter
(setq *PF-POINT-LAYER*  "POINTS")   ; layer holding the survey points
(setq *PF-POINT-BLOCK*  "ab_pt")    ; block name whose INSERTs mark survey
                                    ; points; the block's insertion point
                                    ; is taken as the point location
(setq *PF-OUT-LAYER*    "POOL-FIT") ; layer the fitted polyline goes on
(setq *PF-MISS-LAYER*   "FGStep")   ; layer the "could not hold this
                                    ; point" circles and their list go
                                    ; on.  This may well be a layer you
                                    ; already use, so ABHD stamps the
                                    ; objects it makes and only ever
                                    ; erases its own (see pf:tag-mine)
(setq *PF-MISS-RADIUS*  4.0)        ; radius of those circles (4 inches)
(setq *PF-PT-TAG*       "number")   ; attribute tag on the point block
                                    ; holding the surveyed point number,
                                    ; used to label it as "Pt.17"
(setq *PF-WALL-LAYER*   "POOL-WALLS"); layer the dashed markers for
                                    ; user-declared straight walls go on
(setq *PF-TOL-MAX*      2.0)        ; hard ceiling on the max-distance
                                    ; prompt (2 inches): further than
                                    ; that and the line is no longer a
                                    ; trace of the points
(setq *PF-BOTTOM-LAYER* "POOL-BOTTOM") ; legacy: where earlier versions
                                    ; of this command put the bottom
                                    ; geometry and dims.  Everything
                                    ; goes on *PF-POOL-LAYER* now, but
                                    ; ADAB still skips this layer when
                                    ; reading a selection
(setq *PF-BOTTOM-STEP*  6.0)        ; sampling step for the hopper
                                    ; offset curve (6 inches keeps it
                                    ; smooth without a heavy polyline)
(setq *PF-BOTTOM-FIT*   0.25)       ; merging those samples into long
                                    ; arcs may leave no sample further
                                    ; than this off the drawn curve (a
                                    ; quarter inch - invisible at pool
                                    ; scale, a big cut in arc count)
(setq *PF-PICKUP-EPS*   3.0)        ; a survey point within this of the
                                    ; selected perimeter counts as one
                                    ; of ITS points when ADAB gathers
                                    ; or trims them (3 in - genuine
                                    ; edge points sit within the fit
                                    ; tolerance, depth shots and deck
                                    ; points are feet away)
(if (null *PF-HOP-OFF*) (setq *PF-HOP-OFF* 18.0)) ; default hopper
                                    ; offset (18 in), remembered per
                                    ; session like the tolerance
(setq *PF-DIM-FTIN* "SIDE DIMENSION") ; dimension style stamped on the
                                    ; offset dims NOT anchored to a
                                    ; break point (hopper back, slope
                                    ; waypoints) when the offset was
                                    ; typed as feet-and-inches (3'6)
(setq *PF-DIM-IN* "STANDARD INCHES") ; same dims when the offset was
                                    ; typed in plain inches (42).
                                    ; Either style missing from the
                                    ; drawing falls back to the
                                    ; current style, with a note
(setq *PF-DIM-OFF* 12.0)            ; the deep-end dimension string
                                    ; (wall-to-hopper, hopper width,
                                    ; hopper-to-wall) sits this far off
                                    ; the deep break line (a foot), on
                                    ; the shallow-end side
(setq *PF-COMPARE*                  ; the three candidate fits offered:
  '(("tight" 1 "red"    "most curves - least error")
    ("asked" 2 "yellow" "as asked")
    ("few"   4 "cyan"   "fewest curves - still within the distance")))
                                    ; (mode, AutoCAD colour, colour name,
                                    ; description).  The three ask three
                                    ; different questions of the same
                                    ; points, so what is being chosen is
                                    ; an aim, not a tolerance:
                                    ;   "tight" - accuracy above all: it
                                    ;     fits to *PF-TIGHT-TOL*, lets no
                                    ;     point miss and ignores both the
                                    ;     distance typed at step 2 and
                                    ;     the curve cap, so it draws the
                                    ;     most curves and the least error
                                    ;   "asked" - the settings exactly as
                                    ;     typed, curve cap and all
                                    ;   "few" - the fewest curves that
                                    ;     still hold every point within
                                    ;     the distance typed: the same
                                    ;     distance, but with the miss
                                    ;     allowance lifted so arcs run as
                                    ;     long as that distance permits
                                    ; Colours and wording are yours to
                                    ; edit; the three mode names are not
(setq *PF-TIGHT-TOL*    0.01)       ; the "tight" candidate's accuracy
                                    ; target (units) - what it fits to
                                    ; instead of the distance typed at
                                    ; step 2, or that distance when it
                                    ; happens to be tighter still
(setq *PF-EXACT-EPS*    0.001)      ; "exactly on" threshold (units)
(setq *PF-FIT-EPS*      0.01)       ; if a single arc misses any of its
                                    ; points by more than this, split it
                                    ; into several arcs that hit exactly
(setq *PF-ON-EPS*       0.25)       ; a point within this of the result
                                    ; counts as ON it; only points off by
                                    ; more than this eat into the miss
                                    ; allowance below.  Calibrated from a
                                    ; hand-drawn reference trace: ~87% of
                                    ; its points sat within a quarter inch
(setq *PF-MISS-PCT*     0.15)       ; share of the points (rounded UP to
                                    ; a whole point) that may sit off the
                                    ; result by up to the tolerance
                                    ; (about an inch by default) - this
                                    ; slack is what buys longer spans and
                                    ; fewer curves
(setq *PF-CORNER-ANG*   (/ pi 4.0)) ; a point that turns more than this
                                    ; (45 deg) is a sharp corner: it may
                                    ; start or end a span but never gets
                                    ; buried inside one, so polygonal
                                    ; shapes keep their corners.  Sample
                                    ; real tight curves with at least ~3
                                    ; points per quarter turn to stay
                                    ; under it.
(setq *PF-NICE-RADII* '(12.0 6.0 1.0)) ; preferred arc-radius increments,
                                    ; tried in order: whole feet, half
                                    ; feet, whole inches (drawing units
                                    ; are inches).  A radius is snapped
                                    ; to the first increment whose arc
                                    ; still holds the points; only when
                                    ; none does is the free-fit ("weird")
                                    ; radius kept.
(setq *PF-TANG-TOL* (/ pi 22.5))    ; wiggle room from perfect
                                    ; tangency at each joint between two
                                    ; arcs (8 degrees).  Being ON the
                                    ; points matters more than perfect
                                    ; tangency; this slack is what lets
                                    ; every arc endpoint sit on a survey
                                    ; point and radii stay nice.
                                    ; Calibrated from a hand-drawn
                                    ; reference trace whose joints ran up
                                    ; to 7.9 deg (median 3 deg); tighter
                                    ; values shatter the fit into many
                                    ; short arcs (5 deg is workable,
                                    ; 6 deg and below is not).
(setq *PF-TANG-STEPS* '(1.0 1.25 1.5)) ; when nothing fits inside the
                                    ; tangent window, stretch it by
                                    ; these multiples in turn rather
                                    ; than abandon it; if even the
                                    ; widest finds nothing, a one-point
                                    ; stub takes over, and that
                                    ; continues the previous tangent
                                    ; exactly.  Smoothness is worth
                                    ; more than one extra arc, so keep
                                    ; the last step small: dropping the
                                    ; window outright allowed joints to
                                    ; kink three times the limit.
(setq *PF-SNAP-EPS*     0.02)       ; a nice-radius snap may move the
                                    ; covered points at most this far
                                    ; beyond where they already sat, and
                                    ; it may never pull an arc off its
                                    ; anchor point entirely - the points
                                    ; outrank pretty radii
(setq *PF-CHAIN-FUZZ*   1.0e-4)     ; endpoint-matching fuzz for
                                    ; chaining exploded segments
(if (null *PF-TOL*) (setq *PF-TOL* 1.0)) ; default tolerance, 1 inch
;; *PF-MAX-ARCS* : cap on the number of curved segments in the output;
;; nil = no cap.  The command prompts for it (Enter keeps the current
;; value, "None" removes the cap) and remembers it for the session,
;; like *PF-TOL*.

;; ---- circle / arc geometry -----------------------------------------

;; Circumcenter of three points, nil when (nearly) collinear.
(defun pf:circumcenter (pa pb pc / x1 y1 x2 y2 x3 y3 d s1 s2 s3)
  (setq x1 (car pa) y1 (cadr pa)
        x2 (car pb) y2 (cadr pb)
        x3 (car pc) y3 (cadr pc)
        d  (* 2.0 (+ (* x1 (- y2 y3)) (* x2 (- y3 y1)) (* x3 (- y1 y2)))))
  (if (< (abs d) 1.0e-10)
    nil
    (progn
      (setq s1 (+ (* x1 x1) (* y1 y1))
            s2 (+ (* x2 x2) (* y2 y2))
            s3 (+ (* x3 x3) (* y3 y3)))
      (list (/ (+ (* s1 (- y2 y3)) (* s2 (- y3 y1)) (* s3 (- y1 y2))) d)
            (/ (+ (* s1 (- x3 x2)) (* s2 (- x1 x3)) (* s3 (- x2 x1))) d)))))

;; Bulge of the unique circular arc that starts at P1, ends at P2 and
;; passes through Q.  0.0 when the three points are collinear, and
;; also when the arc would be a (near) full circle - P1 and P2 lying
;; at the same angle from the center makes the sweep 0 or 2*pi, which
;; no single bulge can express.  Nearly-collinear noisy survey points
;; can produce exactly that, so both ends of the range are guarded.
(defun pf:bulge-3pt (p1 q p2 / c a1 a2 aq dccw dq)
  (setq p1 (cal:2d p1) q (cal:2d q) p2 (cal:2d p2)
        c  (pf:circumcenter p1 q p2))
  (if (null c)
    0.0
    (progn
      (setq a1   (angle c p1)
            a2   (angle c p2)
            aq   (angle c q)
            dccw (cal:angnorm (- a2 a1))
            dq   (cal:angnorm (- aq a1)))
      (cond
        ((< dccw 1.0e-9) 0.0)                       ; degenerate sweep
        ((> dccw (- (* 2.0 pi) 1.0e-9)) 0.0)        ; degenerate sweep
        ((<= dq dccw) (cal:tan (/ dccw 4.0)))        ; CCW arc through Q
        (T (- (cal:tan (/ (- (* 2.0 pi) dccw) 4.0)))))))) ; CW through Q

;; Arc geometry of a bulged segment: (center radius angStart angEnd)
;; where the arc runs CCW from angStart to angEnd when bulge > 0 and
;; CW when bulge < 0.  nil for a straight segment.
(defun pf:arc-geom (p1 p2 b / ch dir apex c)
  (if (< (abs b) 1.0e-9)
    nil
    (progn
      (setq p1   (cal:2d p1)
            p2   (cal:2d p2)
            ch   (cal:dist p1 p2)
            dir  (cal:v* (cal:v- p2 p1) (/ 1.0 ch))
            ;; sagitta = (chord/2)*bulge; a positive (CCW) bulge apex
            ;; lies to the RIGHT of the p1->p2 chord direction
            apex (cal:v+ (cal:mid p1 p2)
                         (cal:v* (cal:perp dir) (* -0.5 ch b)))
            c    (pf:circumcenter p1 apex p2))
      (if (null c)
        nil
        (list c (cal:dist c p1) (angle c p1) (angle c p2))))))

;; Distance from point P to segment (p1 p2 bulge).
(defun pf:seg-dist (p seg / p1 p2 b v w len2 t2 g c r a1 a2 ap sweep rel)
  (setq p  (cal:2d p)
        p1 (cal:2d (car seg))
        p2 (cal:2d (cadr seg))
        b  (caddr seg))
  (if (< (abs b) 1.0e-9)
    ;; straight: project onto the segment, clamp to its ends
    (progn
      (setq v    (cal:v- p2 p1)
            w    (cal:v- p p1)
            len2 (cal:dot v v))
      (if (< len2 1.0e-20)
        (cal:dist p p1)
        (progn
          (setq t2 (/ (cal:dot w v) len2))
          (if (< t2 0.0) (setq t2 0.0))
          (if (> t2 1.0) (setq t2 1.0))
          (cal:dist p (cal:v+ p1 (cal:v* v t2))))))
    ;; arc: radial distance when P falls inside the sweep, else the
    ;; nearer endpoint
    (progn
      (setq g (pf:arc-geom p1 p2 b))
      (if (null g)
        (min (cal:dist p p1) (cal:dist p p2))
        (progn
          (setq c  (car g)  r (cadr g)
                a1 (caddr g) a2 (cadddr g)
                ap (angle c p))
          (if (> b 0.0)
            (setq sweep (cal:angnorm (- a2 a1)) rel (cal:angnorm (- ap a1)))
            (setq sweep (cal:angnorm (- a1 a2)) rel (cal:angnorm (- ap a2))))
          (if (<= rel sweep)
            (abs (- (cal:dist p c) r))
            (min (cal:dist p p1) (cal:dist p p2))))))))

;; Bulge of the arc that starts at A with tangent direction TANG
;; (radians) and ends at B.  The angle between a chord and the tangent
;; at its end is half the included angle, so delta = 2*phi.
(defun pf:tangent-bulge (a tang b / phi)
  (setq phi (cal:signed-dang tang (angle (cal:2d a) (cal:2d b))))
  (cal:tan (/ phi 2.0)))

;; Tangent direction (radians) at the END of the arc from A to B with
;; the given bulge: chord direction + delta/2, delta = 4*atan(bulge).
(defun pf:end-tangent (a b bulge)
  (+ (angle (cal:2d a) (cal:2d b)) (* 2.0 (atan bulge))))

;; Position of P along segment (p1 p2 bulge) as a 0..1 parameter,
;; used only to ORDER candidate points along the segment.
(defun pf:seg-param (p seg / p1 p2 b v w len2 g c a1 a2 ap sweep rel)
  (setq p  (cal:2d p)
        p1 (cal:2d (car seg))
        p2 (cal:2d (cadr seg))
        b  (caddr seg))
  (if (< (abs b) 1.0e-9)
    (progn
      (setq v (cal:v- p2 p1) w (cal:v- p p1) len2 (cal:dot v v))
      (if (< len2 1.0e-20) 0.0 (/ (cal:dot w v) len2)))
    (progn
      (setq g (pf:arc-geom p1 p2 b))
      (if (null g)
        0.0
        (progn
          (setq c (car g) a1 (caddr g) a2 (cadddr g) ap (angle c p))
          (if (> b 0.0)
            (setq sweep (cal:angnorm (- a2 a1))
                  rel   (cal:angnorm (- ap a1)))
            (setq sweep (cal:angnorm (- a1 a2))
                  rel   (- (cal:angnorm (- a1 a2))
                           (cal:angnorm (- ap a2)))))
          (if (< sweep 1.0e-10) 0.0 (/ rel sweep)))))))

;; ---- entity -> segment extraction ----------------------------------
;; A segment is (startPt endPt bulge), 2D points.

(defun pf:lw-segs (ed / pts bls item segs n closed)
  ;; collect (10) vertices and their (42) bulges, in order
  (setq pts nil bls nil)
  (foreach item ed
    (cond
      ((= (car item) 10)
       (setq pts (cons (cal:2d (cdr item)) pts)
             bls (cons 0.0 bls)))
      ((and (= (car item) 42) bls)
       (setq bls (cons (cdr item) (cdr bls))))))
  (setq pts (reverse pts) bls (reverse bls)
        closed (= 1 (logand 1 (cdr (assoc 70 ed))))
        segs nil n 0)
  (while (< n (1- (length pts)))
    (setq segs (cons (list (nth n pts) (nth (1+ n) pts) (nth n bls)) segs)
          n    (1+ n)))
  (if (and (> (length pts) 2)
           (or closed
               (< (cal:dist (last pts) (car pts)) *PF-CHAIN-FUZZ*)))
    (if (>= (cal:dist (last pts) (car pts)) *PF-CHAIN-FUZZ*)
      (setq segs (cons (list (last pts) (car pts) (last bls)) segs))))
  (reverse segs))

(defun pf:pl-segs (en / ed sub pts bls segs n closed)
  ;; heavy (old-style) 2D POLYLINE: walk its VERTEX sub-entities
  (setq ed (entget en)
        closed (= 1 (logand 1 (cdr (assoc 70 ed))))
        pts nil bls nil
        sub (entnext en))
  (while (and sub (= "VERTEX" (cdr (assoc 0 (setq ed (entget sub))))))
    ;; skip spline/fit control vertices (flag bits 1 and 16)
    (if (= 0 (logand 17 (cond ((cdr (assoc 70 ed))) (0))))
      (setq pts (cons (cal:2d (cdr (assoc 10 ed))) pts)
            bls (cons (cond ((cdr (assoc 42 ed))) (0.0)) bls)))
    (setq sub (entnext sub)))
  (setq pts (reverse pts) bls (reverse bls) segs nil n 0)
  (while (< n (1- (length pts)))
    (setq segs (cons (list (nth n pts) (nth (1+ n) pts) (nth n bls)) segs)
          n    (1+ n)))
  (if (and closed (> (length pts) 2))
    (setq segs (cons (list (last pts) (car pts) (last bls)) segs)))
  (reverse segs))

(defun pf:ent-segs (en / ed typ c r a1 a2 delta)
  (setq ed  (entget en)
        typ (cdr (assoc 0 ed)))
  (cond
    ((= typ "LINE")
     (list (list (cal:2d (cdr (assoc 10 ed)))
                 (cal:2d (cdr (assoc 11 ed)))
                 0.0)))
    ((= typ "ARC")
     (setq c  (cal:2d (cdr (assoc 10 ed)))
           r  (cdr (assoc 40 ed))
           a1 (cdr (assoc 50 ed))
           a2 (cdr (assoc 51 ed))
           delta (cal:angnorm (- a2 a1)))
     (if (< delta 1.0e-10) (setq delta (* 2.0 pi)))
     ;; a full-circle arc cannot be one bulged segment (its bulge is
     ;; infinite): hand back two semicircles instead
     (if (> delta (- (* 2.0 pi) 1.0e-9))
       (list (list (polar c a1 r) (polar c (+ a1 pi) r) 1.0)
             (list (polar c (+ a1 pi) r) (polar c a1 r) 1.0))
       (list (list (polar c a1 r) (polar c a2 r) (cal:tan (/ delta 4.0))))))
    ;; a CIRCLE is a legitimate pool perimeter (round spa): two
    ;; semicircles, so the chaining and fitting code sees a normal
    ;; closed loop instead of reporting a gap
    ((= typ "CIRCLE")
     (setq c (cal:2d (cdr (assoc 10 ed)))
           r (cdr (assoc 40 ed)))
     (list (list (polar c 0.0 r) (polar c pi r) 1.0)
           (list (polar c pi r) (polar c 0.0 r) 1.0)))
    ((= typ "LWPOLYLINE") (pf:lw-segs ed))
    ((= typ "POLYLINE") (pf:pl-segs en))
    (T nil)))

;; ---- chain loose segments into one closed loop ----------------------
;; Returns the ordered segment list, or nil (with a message) on failure.
(defun pf:chain (segs / loop start end found s rest)
  (if (null segs)
    nil
    (progn
      (setq loop  (list (car segs))
            start (car (car segs))
            end   (cadr (car segs))
            segs  (cdr segs))
      (while (and segs
                  (>= (cal:dist end start) *PF-CHAIN-FUZZ*))
        (setq found nil rest nil)
        (foreach s segs
          (cond
            (found (setq rest (cons s rest)))
            ((< (cal:dist end (car s)) *PF-CHAIN-FUZZ*)
             (setq found s))
            ((< (cal:dist end (cadr s)) *PF-CHAIN-FUZZ*)
             ;; reverse the segment: swap ends, negate the bulge
             (setq found (list (cadr s) (car s) (- (caddr s)))))
            (T (setq rest (cons s rest)))))
        (if found
          (setq loop (cons found loop)
                end  (cadr found)
                segs (reverse rest))
          (setq segs nil end nil)))  ; gap -> bail out
      (cond
        ((null end)
         (princ "\nABHD: gap in the POOL perimeter - could not close the loop.")
         nil)
        ((>= (cal:dist end start) *PF-CHAIN-FUZZ*)
         (princ "\nABHD: the POOL perimeter does not close.")
         nil)
        (T
         (if segs
           (princ (strcat "\nABHD: warning - "
                          (itoa (length segs))
                          " POOL segment(s) not part of the closed loop were ignored.")))
         (reverse loop))))))

;; ---- span fitting helpers --------------------------------------------
;; A "span" is one candidate segment from A to B judged against QS, the
;; survey points it is supposed to represent.

;; Worst distance from any of QS to the segment (A B bulge).
(defun pf:span-dev (a b bul qs / seg mx d q)
  (setq seg (list a b bul) mx 0.0)
  (foreach q qs
    (setq d (pf:seg-dist q seg))
    (if (> d mx) (setq mx d)))
  mx)

;; The miss percentage in force for the current run: the command binds
;; pf-miss-pct from the user's answer; Enter keeps the standard value.
(defun pf:misspct ()
  (if pf-miss-pct pf-miss-pct *PF-MISS-PCT*))

;; The "on the shape" threshold in force for the current run.  It
;; scales with the tolerance (a quarter of it, never below
;; *PF-ON-EPS*): if the user accepts 4 inches of error, a point 1 inch
;; off is plainly still ON the shape, and counting it as a miss would
;; burn the whole allowance on the first span and starve the rest of
;; the loop into single-point stubs.  pf-on-eps is bound per run by
;; the command and per pass by pf:fit-pass.
(defun pf:oneps ()
  (if pf-on-eps pf-on-eps *PF-ON-EPS*))

;; How many of QS sit farther than the on-the-shape threshold from the
;; segment - the points that would eat into the miss allowance.
(defun pf:span-misses (a b bul qs / seg c q lim)
  (setq seg (list a b bul) c 0 lim (pf:oneps))
  (foreach q qs
    (if (> (pf:seg-dist q seg) lim) (setq c (1+ c))))
  c)

;; Best single arc from A to B over the points QS: candidate bulges are
;; the exact 3-point fits through a few of the points plus the average
;; of them all; the one with the smallest worst-case deviation wins.
;; Returns (bulge . maxdev).
(defun pf:span-arc (a b qs / bls sum bl m cands best bd d)
  (setq bls (mapcar '(lambda (q) (pf:bulge-3pt a q b)) qs)
        sum 0.0
        m   (length qs))
  (foreach bl bls (setq sum (+ sum bl)))
  (setq cands (list (/ sum m) (nth (/ m 2) bls)))
  (if (>= m 4)
    (setq cands (append cands (list (nth (/ m 4) bls)
                                    (nth (/ (* 3 m) 4) bls)))))
  (setq best nil bd nil)
  (foreach bl cands
    (setq d (pf:span-dev a b bl qs))
    (if (or (null bd) (< d bd)) (setq best bl bd d)))
  (cons best bd))

;; Radius of the arc (A B bulge); nil for a straight segment.
(defun pf:bulge-radius (a b bl / h)
  (if (< (abs bl) 1.0e-9)
    nil
    (progn
      (setq h (/ (cal:dist a b) 2.0))
      (/ (* h (1+ (* bl bl))) (* 2.0 (abs bl))))))

;; Bulge of the arc from A to B with radius R, on the same side and
;; with the same minor/major-arc character as reference bulge BREF.
;; nil when R is too small to span the chord.
(defun pf:radius-bulge (a b r bref / h s bl)
  (setq h (/ (cal:dist a b) 2.0))
  (if (or (< r h) (< h 1.0e-9))
    nil
    (progn
      (setq s  (sqrt (- (* r r) (* h h)))
            bl (if (> (abs bref) 1.0)
                 (/ (+ r s) h)              ; major arc
                 (/ (- r s) h)))            ; minor arc
      (if (< bref 0.0) (- bl) bl))))

;; Try to snap the arc A->B (free-fit bulge BL over points QS) to a
;; "nice" radius - whole feet first, then half feet, then whole inches
;; (*PF-NICE-RADII*) - keeping every point within TOL and at most LEFT
;; of them off by more than *PF-ON-EPS*.  When WIN (a bulge interval)
;; is given the snapped bulge must stay inside it, so snapping never
;; breaks the tangency window.  The nearer multiple on each tier is
;; tried first; the arc's endpoints never move.  Returns
;; (bulge . misses) of the snapped arc, or nil.
(defun pf:snap-arc (a b bl qs tol left win / r0 h best tier lo hi
                                              cands r bl2 mis)
  (setq r0   (pf:bulge-radius a b bl)
        h    (/ (cal:dist a b) 2.0)
        best nil)
  (if (and r0 (< r0 1.0e6))       ; a huge radius is basically straight
    (foreach tier *PF-NICE-RADII*
      (if (null best)
        (progn
          (setq lo    (* tier (fix (/ r0 tier)))
                hi    (+ lo tier)
                cands (if (< (- r0 lo) (- hi r0))
                        (list lo hi)
                        (list hi lo)))
          (foreach r cands
            (if (and (null best) (>= r h) (> r 0.0))
              (progn
                (setq bl2 (pf:radius-bulge a b r bl))
                (if (and bl2
                         (or (null win)
                             (and (>= bl2 (car win)) (<= bl2 (cdr win))))
                         (<= (pf:span-dev a b bl2 qs) tol)
                         (<= (setq mis (pf:span-misses a b bl2 qs))
                             left))
                  (setq best (cons bl2 mis))))))))))
  best)

;; ---- arc segment re-fitting ------------------------------------------
;; Re-fit one curved segment from P1 to P2 (original bulge B) through
;; CANDS, its nearby survey points sorted along the segment.  Returns a
;; list of one or more segments (p1 p2 bulge):
;;   * no candidates          -> the original arc, endpoints updated
;;   * a nice-radius (foot / half-foot / inch) arc holds every point
;;     within TOL and the miss allowance (pf-miss-left, set by the
;;     command) can absorb the off points
;;                            -> that single snapped arc, preferred
;;                               even over an exact free fit
;;   * one arc holds them all -> that single arc
;;   * one free arc keeps every point within TOL and the allowance
;;     covers it              -> that single arc; fewer curves beats
;;                               exactness, by design
;;   * otherwise              -> a tangent-continuous chain of arcs
;;                               passing exactly through every point
(defun pf:cap-bulge (b)
  (cond ((> b 5.0) 5.0) ((< b -5.0) -5.0) (T b)))

(defun pf:fit-arc-seg (p1 p2 b cands tol / ar bavg maxres mis nb q segs
                                            prev tang sn)
  (if (null cands)
    (list (list p1 p2 b))
    (progn
      (setq ar     (pf:span-arc p1 p2 cands)
            bavg   (car ar)
            maxres (cdr ar)
            sn     (pf:snap-arc p1 p2 bavg cands tol pf-miss-left nil))
      (cond
        ;; a nice-radius arc holds every point: take it first
        (sn
         (setq pf-miss-left (- pf-miss-left (cdr sn)))
         (list (list p1 p2 (car sn))))
        ;; a single free arc genuinely holds every point
        ((<= maxres *PF-FIT-EPS*)
         (list (list p1 p2 bavg)))
        ;; a single arc is close enough and the allowance covers it
        ((and (<= maxres tol)
              (<= (setq mis (pf:span-misses p1 p2 bavg cands))
                  pf-miss-left))
         (setq pf-miss-left (- pf-miss-left mis))
         (list (list p1 p2 bavg)))
        ;; subdivide.  First arc runs from P1 through the 1st point to
        ;; the 2nd; every further arc starts tangent to the previous one
        ;; and lands exactly on the next point; the last lands on P2.
        ;; All points are hit exactly and every internal joint is
        ;; tangent-continuous (smooth).
        (T
         (setq nb   (pf:bulge-3pt p1 (car cands) (cadr cands))
               segs (list (list p1 (cadr cands) nb))
               tang (pf:end-tangent p1 (cadr cands) nb)
               prev (cadr cands))
         (foreach q (cddr cands)
           (setq nb   (pf:cap-bulge (pf:tangent-bulge prev tang q))
                 segs (cons (list prev q nb) segs)
                 tang (pf:end-tangent prev q nb)
                 prev q))
         (setq nb (pf:cap-bulge (pf:tangent-bulge prev tang p2)))
         (reverse (cons (list prev p2 nb) segs)))))))

;; ---- points-only / ordering-sketch mode -------------------------------

;; Pure-AutoLISP list helpers (no Visual LISP / vl-* dependency, so the
;; command works even when (vl-load-com) has not been run).

;; Remove every element equal (within fuzz) to VAL from LST.
(defun pf:remove (val lst / out x)
  (foreach x lst
    (if (not (equal x val 1.0e-9)) (setq out (cons x out))))
  (reverse out))

;; Insert (key . val) pair X into the already-sorted list LST, keeping
;; ascending order by the pair's car (key).
(defun pf:ins-car (x lst)
  (cond ((null lst) (list x))
        ((< (car x) (car (car lst))) (cons x lst))
        (T (cons (car lst) (pf:ins-car x (cdr lst))))))

;; Insertion-sort a list of (key . val) pairs ascending by key.
(defun pf:sort-car (lst / out x)
  (foreach x lst (setq out (pf:ins-car x out)))
  out)

;; T when the chained loop contains at least one curved segment
(defun pf:has-arcs (loop / r)
  (foreach s loop (if (>= (abs (caddr s)) 1.0e-9) (setq r T)))
  r)

;; Order points into a closed tour: nearest-neighbour walk from the
;; leftmost point, then 2-opt passes to remove crossings.
(defun pf:order-points (pts / start cur tour rest best bd q d n i j k
                              pass improved ti ti1 tj tj1 delta head midl
                              taill)
  (setq start (car pts))
  (foreach q (cdr pts)
    (if (or (< (car q) (car start))
            (and (= (car q) (car start)) (< (cadr q) (cadr start))))
      (setq start q)))
  (setq cur  start
        rest (pf:remove start pts)
        tour (list start))
  (while rest
    (setq best nil bd nil)
    (foreach q rest
      (setq d (cal:dist cur q))
      (if (or (null bd) (< d bd)) (setq best q bd d)))
    (setq tour (cons best tour)
          cur  best
          rest (pf:remove best rest)))
  (setq tour (reverse tour)
        n    (length tour)
        pass 0
        improved T)
  (while (and improved (< pass 40))
    (setq improved nil pass (1+ pass) i 0)
    (while (< i (1- n))
      (setq j (1+ i))
      (while (< j n)
        (if (not (and (= i 0) (= j (1- n))))
          (progn
            (setq ti    (nth i tour)
                  ti1   (nth (1+ i) tour)
                  tj    (nth j tour)
                  tj1   (nth (rem (1+ j) n) tour)
                  delta (- (+ (cal:dist ti tj) (cal:dist ti1 tj1))
                           (+ (cal:dist ti ti1) (cal:dist tj tj1))))
            (if (< delta -1.0e-9)
              (progn                    ; reverse tour[i+1 .. j]
                (setq head nil midl nil taill nil k 0)
                (foreach q tour
                  (cond ((<= k i) (setq head (cons q head)))
                        ((<= k j) (setq midl (cons q midl)))
                        (T        (setq taill (cons q taill))))
                  (setq k (1+ k)))
                (setq tour     (append (reverse head) midl (reverse taill))
                      improved T)))))
        (setq j (1+ j)))
      (setq i (1+ i))))
  tour)

;; Order points by their position along a user-drawn ordering sketch
;; (the chained loop): each point keys on segment-index + parameter.
(defun pf:loop-order (loop pts / keyed q best bd d i s tp)
  (foreach q pts
    (setq best 0 bd nil i 0)
    (foreach s loop
      (setq d (pf:seg-dist q s))
      (if (or (null bd) (< d bd)) (setq bd d best i))
      (setq i (1+ i)))
    (setq tp (pf:seg-param q (nth best loop)))
    (if (< tp 0.0) (setq tp 0.0))
    (if (> tp 1.0) (setq tp 1.0))
    (setq keyed (cons (cons (+ best tp) q) keyed)))
  (mapcar 'cdr (pf:sort-car keyed)))

;; The surveyed number carried by a point block, read from its
;; *PF-PT-TAG* attribute ("number" on ab_pt).  nil when the block has
;; no such attribute.
;;
;; DELIBERATELY strict: no first-numeric-attribute fallback, unlike
;; ABFIND/BPCALLOUT/LHD/FITABHD and cal:block-number.  The fitter
;; consumes every point it is handed, so a stray numbered block (a
;; detail bubble, a keynote) silently joining the survey would warp the
;; whole fit - a dropped untagged point is the visible, recoverable
;; failure.  Reviewed 2026-08-27 and kept on purpose; CABHD's copy
;; holds the same line for the same reason.
(defun pf:block-number (en / sub ed val)
  (setq sub (entnext en) val nil)
  (while (and sub
              (setq ed (entget sub))
              (= "ATTRIB" (cdr (assoc 0 ed))))
    (if (and (null val)
             (cdr (assoc 2 ed))
             (= (strcase (cdr (assoc 2 ed))) (strcase *PF-PT-TAG*)))
      (setq val (cdr (assoc 1 ed))))
    (setq sub (entnext sub)))
  val)

;; Remember a point and what to call it, so a miss can be reported as
;; "Pt.17" using the number in the drawing rather than a private
;; index.  Points with no number of their own get the next count.
(defun pf:add-point (p nm)
  (setq npt        (1+ npt)
        pts        (cons p pts)
        pf-ptnames (cons (cons p (if (and nm (/= nm "")) nm (itoa npt)))
                         pf-ptnames)))

;; What to call the surveyed point at Q.
(defun pf:pt-name (q / nm p)
  (setq nm nil)
  (foreach p pf-ptnames
    (if (and (null nm) (< (cal:dist (car p) q) *PF-EXACT-EPS*))
      (setq nm (cdr p))))
  (if nm nm "?"))

;; The member of LST nearest to P.
(defun pf:nearest (p lst / best bd q d)
  (setq best nil bd nil)
  (foreach q lst
    (setq d (cal:dist p q))
    (if (or (null bd) (< d bd)) (setq best q bd d)))
  best)

;; Index of point P in TOUR (exact-point fuzz), or nil.
(defun pf:tour-index (p tour / i k q)
  (setq i nil k 0)
  (foreach q tour
    (if (and (null i) (< (cal:dist p q) *PF-EXACT-EPS*)) (setq i k))
    (setq k (1+ k)))
  i)

;; Rotate the closed TOUR so it starts at point P (used so a declared
;; straight wall never straddles the walk's origin).
(defun pf:rotate-to-point (tour p / i)
  (setq i (pf:tour-index p tour))
  (if (and i (> i 0))
    (append (cal:nthcdr i tour) (cal:sublist tour 0 i))
    tour))

;; Rotate the closed TOUR so it starts at its sharpest turn: the fitter
;; walks the loop from there, so the most corner-like point is always a
;; span endpoint and never gets buried inside a span.
(defun pf:rotate-to-corner (tour / n i prev cur next turn best bi)
  (setq n (length tour) i 0 best -1.0 bi 0)
  (repeat n
    (setq prev (nth (rem (+ i n -1) n) tour)
          cur  (nth i tour)
          next (nth (rem (1+ i) n) tour)
          turn (abs (cal:signed-dang (angle prev cur) (angle cur next))))
    (if (> turn best) (setq best turn bi i))
    (setq i (1+ i)))
  (append (cal:nthcdr bi tour) (cal:sublist tour 0 bi)))

;; Number of curved segments in a span list.
(defun pf:arc-count (spans / c sp)
  (setq c 0)
  (foreach sp spans (if (>= (abs (caddr sp)) 1.0e-9) (setq c (1+ c))))
  c)

;; ---- near-tangent span fitting ---------------------------------------
;; Arcs sit ON the survey points: every span runs from tour point to
;; tour point and its interior is fitted through the points with exact
;; 3-point arcs.  Tangency is a WINDOW, not a chain: at each joint the
;; new arc's start tangent may differ from the previous arc's end
;; tangent by at most *PF-TANG-TOL* (8 degrees), so the perimeter
;; stays visually smooth while the points stay in charge.  A bulge
;; window is a cons (lo . hi); nil means unconstrained.

;; Allowed bulge interval for the span A->B whose START tangent must
;; lie within *PF-TANG-TOL* of the incoming tangent TE.  WF stretches
;; that limit (see *PF-TANG-STEPS*).  The window edges are clamped so
;; extreme (U-turn) geometry stays finite.
(defun pf:tang-window (te a b wf / tt phi alo ahi lo hi)
  (setq tt  (* *PF-TANG-TOL* wf)
        phi (cal:signed-dang te (angle a b))
        alo (max (min (/ (- phi tt) 2.0) 1.373) -1.373)
        ahi (max (min (/ (+ phi tt) 2.0) 1.373) -1.373)
        lo  (cal:tan alo)
        hi  (cal:tan ahi))
  (if (<= lo hi) (cons lo hi) (cons hi lo)))

;; Allowed bulge interval for the CLOSING span A->B whose END tangent
;; must lie within *PF-TANG-TOL* (times WF) of the loop's start
;; tangent TS0.
(defun pf:end-window (ts0 a b wf / tt psi alo ahi lo hi)
  (setq tt  (* *PF-TANG-TOL* wf)
        psi (cal:signed-dang (angle a b) ts0)
        alo (max (min (/ (- psi tt) 2.0) 1.373) -1.373)
        ahi (max (min (/ (+ psi tt) 2.0) 1.373) -1.373)
        lo  (cal:tan alo)
        hi  (cal:tan ahi))
  (if (<= lo hi) (cons lo hi) (cons hi lo)))

;; Intersect two bulge windows.  When they don't overlap no bulge can
;; satisfy both joints, so the bulge halfway between them is used and
;; the leftover kink is split evenly across the two joints.
(defun pf:merge-windows (win win2 / lo hi)
  (cond
    ((null win) win2)
    ((null win2) win)
    (T
     (setq lo (max (car win) (car win2))
           hi (min (cdr win) (cdr win2)))
     (if (<= lo hi)
       (cons lo hi)
       (progn
         (setq lo (if (< (cdr win) (car win2))
                    (/ (+ (cdr win) (car win2)) 2.0)
                    (/ (+ (cdr win2) (car win)) 2.0)))
         (cons lo lo))))))

;; Clamp bulge B into window WIN (nil = unconstrained).
(defun pf:clamp-b (b win)
  (cond ((null win) b)
        ((< b (car win)) (car win))
        ((> b (cdr win)) (cdr win))
        (T b)))

;; Closest any of QS comes to the segment (A B bulge) - used to test
;; whether an arc still passes through one of its interior points.
(defun pf:span-min (a b bul qs / seg mn d q)
  (setq seg (list a b bul) mn nil)
  (foreach q qs
    (setq d (pf:seg-dist q seg))
    (if (or (null mn) (< d mn)) (setq mn d)))
  mn)

;; Best bulge for the span A->B over interior points QS, restricted to
;; the tangent window WIN (nil = free).  EXACT 3-POINT ARCS COME
;; FIRST: an unclamped 3-point bulge through one of the actual
;; interior points - so the arc's middle lands ON a survey point - is
;; preferred whenever one holds the span within TOL and LEFT misses.
;; Compromise bulges (average / window-clamped / window edges), which
;; float between the points, are used only when no exact arc works.
;; Returns (bulge dev misses exactflag).
(defun pf:span-fit (a b qs win tol left / bls m sum bl cands best d mis)
  (setq bls  (mapcar '(lambda (q) (pf:bulge-3pt a q b)) qs)
        m    (length qs)
        best nil)
  ;; exact candidates: through an interior point AND inside the window
  (foreach bl bls
    (if (or (null win)
            (and (>= bl (car win)) (<= bl (cdr win))))
      (progn
        (setq d (pf:span-dev a b bl qs))
        (if (and (<= d tol)
                 (or (null best) (< d (cadr best))))
          (progn
            (setq mis (pf:span-misses a b bl qs))
            (if (<= mis left)
              (setq best (list bl d mis T))))))))
  ;; compromise candidates, only when no exact arc holds the span
  (if (null best)
    (progn
      (setq sum 0.0)
      (foreach bl bls (setq sum (+ sum bl)))
      (setq cands (list (/ sum m) (nth (/ m 2) bls)))
      (if (>= m 4)
        (setq cands (append cands (list (nth (/ m 4) bls)
                                        (nth (/ (* 3 m) 4) bls)))))
      (if win
        (setq cands (append (mapcar '(lambda (bl) (pf:clamp-b bl win))
                                    cands)
                            (list (car win) (cdr win)
                                  (/ (+ (car win) (cdr win)) 2.0)))))
      (foreach bl cands
        (setq d (pf:span-dev a b bl qs))
        (if (or (null best) (< d (cadr best)))
          (setq best (list bl d (pf:span-misses a b bl qs) nil))))))
  best)

;; Cover the rotated closed TOUR with arcs whose endpoints sit ON the
;; tour points, every joint within *PF-TANG-TOL* of tangent.  Sharp
;; corners stay free kinks.  TE0 (may be nil) seeds the first span's
;; tangent window - used to close the seam.  LEFT is the miss
;; allowance for this pass; when PRO is true each span may spend only
;; its own fair share of it, so one greedy span cannot exhaust the
;; budget and starve the rest of the loop (the curve cap turns PRO off
;; because there the whole point is to trade accuracy for few curves).
;; Straight walls the user declared (pf-walls, bound by the command as
;; snapped point pairs) are emitted verbatim as LINE spans; ordinary
;; spans may neither swallow nor cross them.  Returns the segment list.
(defun pf:span-loop (tour tol left te0 pro / n sharp i prev cur next
                                             turn strtshp segs pos te
                                             ts0 lim a best bstx len go
                                             bnd win qs fr bl mis sn
                                             dev0 anch steps wf lm
                                             walls w i1 i2 fwd nogrow f
                                             wrec)
  (setq n (length tour))
  ;; flag the sharp corners (intentional kinks, window resets): turns
  ;; sharper than *PF-CORNER-ANG*, plus every point the user declared
  ;; a corner - there the tangency rule is waived on purpose
  (setq sharp nil i 0)
  (repeat n
    (setq prev (nth (rem (+ i n -1) n) tour)
          cur  (nth i tour)
          next (nth (rem (1+ i) n) tour)
          turn (abs (cal:signed-dang (angle prev cur) (angle cur next))))
    (setq sharp (cons (or (> turn *PF-CORNER-ANG*)
                          (pf:memb cur pf-corners))
                      sharp)
          i     (1+ i)))
  (setq sharp (reverse sharp))
  ;; map the declared straight walls onto tour indices, walking the
  ;; short way around; the tour was rotated so none straddles index 0
  (setq walls nil)
  (foreach w pf-walls
    (setq i1 (pf:tour-index (car w) tour)
          i2 (pf:tour-index (cadr w) tour))
    (if (and i1 i2 (/= i1 i2))
      (progn
        (setq fwd (rem (+ (- i2 i1) n) n))
        (if (> (* 2 fwd) n)
          (setq i1 i2 fwd (- n fwd)))
        (if (<= (+ i1 fwd) n)
          (setq walls (cons (list i1 (+ i1 fwd)) walls))))))
  ;; indices ordinary spans may not swallow: sharp corners, every
  ;; index a declared wall covers, and every HELD point - a span may
  ;; end on a held point (landing on it exactly) but never bury it
  (setq nogrow nil i 0)
  (repeat n
    (setq f (nth i sharp))
    (foreach w walls
      (if (and (>= i (car w)) (<= i (cadr w))) (setq f T))
      (if (and (= (cadr w) n) (= i 0)) (setq f T)))
    (if (pf:memb (nth i tour) pf-holds) (setq f T))
    (setq nogrow (cons f nogrow)
          i      (1+ i)))
  (setq nogrow  (reverse nogrow)
        strtshp (car sharp)
        segs    nil
        pos     0
        te      (if strtshp nil te0)
        ts0     nil)
  (while (< pos n)
    (setq a    (nth pos tour)
          wrec (assoc pos walls))
    (if wrec
      ;; ---- a declared straight wall starts here: emit it verbatim --
      (progn
        (setq len  (- (cadr wrec) pos)
              bnd  (nth (rem (cadr wrec) n) tour)
              qs   (cal:sublist tour (1+ pos) (1- len))
              mis  (pf:span-misses a bnd 0.0 qs)
              segs (cons (list a bnd 0.0) segs)
              left (max 0 (- left mis)))
        (if (and (null ts0) (not strtshp))
          (setq ts0 (angle a bnd)))
        (setq pos (cadr wrec)
              te  (if (and (< pos n) (nth (rem pos n) sharp))
                    nil
                    (angle a bnd))))
      ;; ---- an ordinary span --------------------------------------
      (progn
    ;; one span may never swallow the whole loop: the first span stops
    ;; one point short so the result always has at least two real
    ;; segments instead of a single zero-length one
    (setq lim  (if (= pos 0) (1- (- n pos)) (- n pos))
          best nil                   ; longest feasible span of any kind
          bstx nil                   ; longest span through an interior point
          steps *PF-TANG-STEPS*)
    ;; Smoothness is worth more than one extra arc, so the tangent
    ;; window is stretched by degrees rather than thrown away.  Only
    ;; when even the widest step finds nothing does the stub below take
    ;; over, and that continues the previous tangent exactly - so the
    ;; tangency rule is never simply abandoned.
    (while (and (null best) steps)
      (setq wf    (car steps)
            steps (cdr steps)
            len   2
            go    T)
      (while (and go (<= len lim))
        (if (nth (rem (+ pos len -1) n) nogrow)
          (setq go nil)         ; never bury a corner or a wall point
          (progn
            (setq bnd (nth (rem (+ pos len) n) tour)
                  win (if te (pf:tang-window te a bnd wf)))
            ;; the span that closes the loop must also end within the
            ;; tangent window of the loop's start
            (if (and (= (+ pos len) n) (not strtshp) ts0)
              (setq win (pf:merge-windows win
                                          (pf:end-window ts0 a bnd wf))))
            (setq qs (cal:sublist tour (1+ pos) (1- len))
                  lm (if pro
                       (min left (cal:ceil (* (pf:misspct) len)))
                       left)
                  fr (pf:span-fit a bnd qs win tol lm))
            (if (and (<= (cadr fr) tol) (<= (caddr fr) lm))
              (progn
                (setq best (list len (car fr) (caddr fr) win))
                (if (cadddr fr) (setq bstx best))
                (setq len (1+ len)))
              (setq go nil))))))
    ;; an arc that floats between the points has to earn its keep:
    ;; only take it when it covers at least 2 more points than the
    ;; longest arc that passes exactly through a point
    (if (and bstx best (< (car best) (+ (car bstx) 2)))
      (setq best bstx))
    (if (null best)
      ;; stub to the very next point: continue the incoming tangent
      ;; (clamped to a semicircle); with no tangent it stays straight
      (progn
        (setq bnd (nth (rem (1+ pos) n) tour))
        (if te
          (progn
            (setq bl (pf:tangent-bulge a te bnd))
            (if (and (= (1+ pos) n) (not strtshp) ts0)
              ;; closing stub: split the kink between both joints
              (setq bl (/ (+ bl (cal:tan (/ (cal:signed-dang (angle a bnd)
                                                           ts0)
                                           2.0)))
                          2.0)))
            (if (> bl 1.0) (setq bl 1.0))
            (if (< bl -1.0) (setq bl -1.0)))
          (setq bl 0.0))
        (setq best (list 1 bl 0 nil)))
      ;; nice-radius snap inside the same tangent window.  A snap may
      ;; never pull the arc off its points: covered points may only
      ;; move a hair (*PF-SNAP-EPS*) beyond where they already sat,
      ;; and an arc that passed through an interior point must still
      ;; pass through one after snapping.
      (progn
        (setq len  (car best)
              bl   (cadr best)
              win  (cadddr best)
              bnd  (nth (rem (+ pos len) n) tour)
              qs   (cal:sublist tour (1+ pos) (1- len))
              dev0 (pf:span-dev a bnd bl qs)
              anch (<= (pf:span-min a bnd bl qs) (* 2.0 *PF-FIT-EPS*))
              sn   (pf:snap-arc a bnd bl qs
                                (max dev0 *PF-SNAP-EPS*) left win))
        (if (and sn
                 (or (not anch)
                     (<= (pf:span-min a bnd (car sn) qs)
                         (* 2.0 *PF-FIT-EPS*))))
          (setq best (list len (car sn) (cdr sn) win)))))
    (setq len  (car best)
          bl   (cadr best)
          mis  (caddr best)
          bnd  (nth (rem (+ pos len) n) tour)
          segs (cons (list a bnd bl) segs)
          left (- left mis))
    (if (and (null ts0) (not strtshp))
      (setq ts0 (- (angle a bnd) (* 2.0 (atan bl)))))
    (setq pos (+ pos len)
          te  (if (nth (rem pos n) sharp)
                nil
                (+ (angle a bnd) (* 2.0 (atan bl))))))))
  (reverse segs))

;; Tangent mismatch at the loop's closing joint (radians).
(defun pf:seam-kink (segs / sl sf te ts)
  (setq sl (last segs)
        sf (car segs)
        te (+ (angle (car sl) (cadr sl)) (* 2.0 (atan (caddr sl))))
        ts (- (angle (car sf) (cadr sf)) (* 2.0 (atan (caddr sf)))))
  (abs (cal:signed-dang te ts)))

;; One full fit; if the seam closes with more than *PF-TANG-TOL* of
;; kink, refit once seeding the first span's window with the arrival
;; tangent, and keep whichever seam is straighter.  The on-the-shape
;; threshold is bound here so it tracks this pass's tolerance.
(defun pf:fit-pass (tour tol left pro / segs k1 sl te0 segs2 pf-on-eps)
  (setq pf-on-eps (max *PF-ON-EPS* (* 0.25 tol))
        segs      (pf:span-loop tour tol left nil pro)
        k1        (pf:seam-kink segs))
  (if (> k1 (+ *PF-TANG-TOL* 0.001))
    (progn
      (setq sl    (last segs)
            te0   (+ (angle (car sl) (cadr sl))
                     (* 2.0 (atan (caddr sl))))
            segs2 (pf:span-loop tour tol left te0 pro))
      (if (< (pf:seam-kink segs2) k1) (setq segs segs2))))
  segs)

;; Points-only / ordering-sketch fit: arcs on the points, joints
;; within *PF-TANG-TOL* of tangent, nice radii.  LEFT is the miss
;; allowance the walk may spend and PRO whether each span is held to
;; its own fair share of it - lifting both is what buys long arcs at
;; an unchanged tolerance, which is how the "few" candidate trades
;; curves for nothing but slack the user already granted.  MAXARCS,
;; when set, is enforced by refitting the whole loop with a
;; progressively relaxed tolerance, which keeps the tangent windows
;; intact.  The fewest-curves result seen is kept, so an unreachably
;; small cap still returns the smallest fit possible - never the
;; biggest.
(defun pf:coarse-loop (tour tol maxarcs left pro / segs segs2 tol2 tries)
  ;; start the walk at a declared wall or corner when there is one, so
  ;; neither straddles the walk's origin; otherwise at the sharpest turn
  (setq tour (cond
               (pf-walls   (pf:rotate-to-point tour (car (car pf-walls))))
               (pf-corners (pf:rotate-to-point tour (car pf-corners)))
               (T          (pf:rotate-to-corner tour)))
        segs (pf:fit-pass tour tol left pro))
  ;; the cap deliberately buys few curves with accuracy, so the refits
  ;; drop both the miss allowance and the per-span fair share
  (if maxarcs
    (progn
      (setq tol2 tol tries 0)
      (while (and (> (pf:arc-count segs) maxarcs) (< tries 40))
        (setq tol2  (* tol2 1.4)
              tries (1+ tries)
              segs2 (pf:fit-pass tour tol2 1000000 nil))
        (if (< (pf:arc-count segs2) (pf:arc-count segs))
          (setq segs segs2)))))
  segs)

;; ---- self-intersection check -----------------------------------------
;; A loop that crosses itself almost always means the automatic point
;; ordering went around a narrow waist the wrong way.  We cannot fix
;; that from the points alone, but we can spot it and say so.

;; Cross product of (P-O) x (Q-O); its sign says which side Q is on.
(defun pf:cross3 (o p q)
  (- (* (- (car p) (car o)) (- (cadr q) (cadr o)))
     (* (- (cadr p) (cadr o)) (- (car q) (car o)))))

;; T when segments A-B and C-D properly cross.  Touching or shared
;; endpoints give a zero product and do not count.
(defun pf:segs-cross (a b c d / d1 d2 d3 d4)
  (setq d1 (pf:cross3 a b c) d2 (pf:cross3 a b d)
        d3 (pf:cross3 c d a) d4 (pf:cross3 c d b))
  (and (< (* d1 d2) 0.0) (< (* d3 d4) 0.0)))

;; Sample the fitted loop into a point list; arcs get intermediate
;; points so a bulging arc's real path is tested, not just its chord.
(defun pf:loop-pts (segs / out s g c r a1 a2 sweep k j aa)
  (setq out nil)
  (foreach s segs
    (setq out (cons (cal:2d (car s)) out))
    (if (>= (abs (caddr s)) 1.0e-9)
      (progn
        (setq g (pf:arc-geom (car s) (cadr s) (caddr s)))
        (if g
          (progn
            (setq c  (car g)   r  (cadr g)
                  a1 (caddr g) a2 (cadddr g))
            (if (> (caddr s) 0.0)
              (setq sweep (cal:angnorm (- a2 a1)))
              (setq sweep (- (cal:angnorm (- a1 a2)))))
            (setq k 4 j 1)
            (while (< j k)
              (setq aa  (+ a1 (* sweep (/ (float j) (float k))))
                    out (cons (list (+ (car c) (* r (cos aa)))
                                    (+ (cadr c) (* r (sin aa))))
                              out)
                    j   (1+ j))))))))
  (reverse out))

;; T when the fitted loop crosses itself.
(defun pf:self-crosses (segs / p n found ti tj i j a b c d)
  (setq p (pf:loop-pts segs))
  (if (< (length p) 4)
    nil
    (progn
      (setq p     (append p (list (car p)))  ; close the point ring
            n     (1- (length p))            ; number of chords
            found nil
            ti    p
            i     0)
      (while (and (not found) (< i (- n 2)))
        (setq a  (car ti)
              b  (cadr ti)
              tj (cddr ti)
              j  (+ i 2))
        (while (and (not found) (< j n))
          (setq c (car tj) d (cadr tj))
          ;; the first and last chords legitimately share a vertex
          (if (not (and (= i 0) (= j (1- n))))
            (if (pf:segs-cross a b c d) (setq found T)))
          (setq tj (cdr tj) j (1+ j)))
        (setq ti (cdr ti) i (1+ i)))
      found)))

;; How many fitted polylines are already on the output layer (counted
;; before the new one is drawn).
(defun pf:prior-fits (/ ss)
  (setq ss (ssget "_X" (list (cons 8 *PF-OUT-LAYER*)
                             '(0 . "LWPOLYLINE"))))
  (if ss (sslength ss) 0))

;; T when R is a whole multiple of one of the *PF-NICE-RADII* tiers.
(defun pf:nice-radius-p (r / found tier q)
  (setq found nil)
  (if (and r (< r 1.0e6))
    (foreach tier *PF-NICE-RADII*
      (setq q (/ r tier))
      (if (< (abs (- q (fix (+ q 0.5)))) 1.0e-6) (setq found T))))
  found)

;; verts: list of (pt bulge) in order, closed.  COL is an AutoCAD
;; colour index, or nil for BYLAYER.
(defun pf:make-pline (verts layer col / dxf v)
  (setq dxf (list '(0 . "LWPOLYLINE") '(100 . "AcDbEntity")
                  (cons 8 layer)))
  (if col (setq dxf (append dxf (list (cons 62 col)))))
  (setq dxf (append dxf (list '(100 . "AcDbPolyline")
                              (cons 90 (length verts)) '(70 . 1))))
  (foreach v verts
    (setq dxf (append dxf (list (cons 10 (car v)) (cons 42 (cadr v))))))
  (entmakex dxf))

;; The kept fit joins the POOL layer in ByLayer colour: the preview
;; colour and the preview layer both belonged to the comparison - the
;; result belongs with the pool.
(defun pf:set-bylayer (en / ed)
  (cal:ensure-layer *PF-POOL-LAYER* 4)
  (setq ed (entget en)
        ed (subst (cons 8 *PF-POOL-LAYER*) (assoc 8 ed) ed))
  (if (assoc 62 ed) (setq ed (subst '(62 . 256) (assoc 62 ed) ed)))
  (entmod ed))

;; The points SEGS fails to hold within TOL.
(defun pf:unheld (segs pts tol / out q s d dmin)
  (setq out nil)
  (foreach q pts
    (setq dmin nil)
    (foreach s segs
      (setq d (pf:seg-dist q s))
      (if (or (null dmin) (< d dmin)) (setq dmin d)))
    (if (> dmin tol) (setq out (cons q out))))
  (reverse out))

;; List membership by position, within the exact-point fuzz.
(defun pf:memb (q lst / found p)
  (setq found nil)
  (foreach p lst
    (if (< (cal:dist p q) *PF-EXACT-EPS*) (setq found T)))
  found)

(defun pf:isect (a b / out q)
  (setq out nil)
  (foreach q a
    (if (pf:memb q b) (setq out (cons q out))))
  (reverse out))

;; ---- temporary preview geometry --------------------------------------
;; Everything ABHD draws to help you decide - the dashed straight-wall
;; markers, the three candidate outlines, their number labels - is
;; scaffolding, not a result.  Each piece is registered here as it is
;; created and swept away when the command ends, whether that is
;; normally, by ESC, or by an error, so no run leaves litter behind.
;; Whatever the user chooses to keep is dropped from the list first.

(defun pf:temp-add (en)
  (if en (setq pf-temp (cons en pf-temp)))
  en)

(defun pf:temp-drop (en / out x)
  (setq out nil)
  (foreach x pf-temp
    (if (not (eq x en)) (setq out (cons x out))))
  (setq pf-temp (reverse out))
  en)

;; entget returns nil for something already gone, so a piece erased
;; earlier is simply skipped instead of raising an error
(defun pf:temp-clear ( / en)
  (foreach en pf-temp
    (if (and en (entget en)) (entdel en)))
  (setq pf-temp nil))

;; Scaffolding removed early - when a Back re-opens the step that
;; drew it - rather than at command end.
(defun pf:temp-kill (en)
  (if (and en (entget en)) (entdel en))
  (pf:temp-drop en))

;; ---- "this one is mine" stamping -------------------------------------
;; ABHD writes onto layers the drawing may already be using - FGStep in
;; particular - so it must never clear a layer wholesale.  Everything it
;; creates carries a small piece of extended data naming this command,
;; and only stamped objects are ever erased again.

(defun pf:tag-mine (en / ed)
  (if en
    (progn
      (regapp "ABHD")
      (setq ed (entget en))
      (entmod (append ed (list (list -3 (list "ABHD" (cons 1000 "ABHD"))))))))
  en)

;; Erase only ABHD's own objects on a layer; anything the user drew
;; there is left alone.  Returns how many went.
(defun pf:purge-mine (name / ss i n en)
  (setq n 0)
  (if (tblsearch "LAYER" name)
    (progn
      (setq ss (ssget "_X" (list (cons 8 name))))
      (if ss
        (progn
          (setq i 0)
          (repeat (sslength ss)
            (setq en (ssname ss i))
            (if (assoc -3 (entget en '("ABHD")))
              (progn (entdel en) (setq n (1+ n))))
            (setq i (1+ i)))))))
  n)

;; Make sure the DASHED linetype exists (pure entmake, no command
;; calls).  Dash lengths are in drawing units - sized for an inch
;; drawing, so the dashes read at pool scale.
(defun pf:ensure-dashed ()
  (if (not (tblsearch "LTYPE" "DASHED"))
    (entmake (list '(0 . "LTYPE") '(100 . "AcDbSymbolTableRecord")
                   '(100 . "AcDbLinetypeTableRecord")
                   '(2 . "DASHED") '(70 . 0)
                   '(3 . "Dashed __ __ __ __ __")
                   '(72 . 65) '(73 . 2) '(40 . 18.0)
                   '(49 . 12.0) '(74 . 0)
                   '(49 . -6.0) '(74 . 0)))))

;; Draw the dashed ring marking a user-declared sharp corner.
(defun pf:draw-corner-marker (p)
  (pf:ensure-dashed)
  (cal:ensure-layer *PF-WALL-LAYER* 8)
  (entmakex (list '(0 . "CIRCLE") '(100 . "AcDbEntity")
                  (cons 8 *PF-WALL-LAYER*) '(6 . "DASHED")
                  '(100 . "AcDbCircle")
                  (cons 10 (list (car p) (cadr p) 0.0))
                  (cons 40 *PF-MISS-RADIUS*))))

;; Draw the marker for a user-declared HELD point: a dashed ring at
;; half the miss-ring radius, so it reads apart from corner rings.
(defun pf:draw-hold-marker (p)
  (pf:ensure-dashed)
  (cal:ensure-layer *PF-WALL-LAYER* 8)
  (entmakex (list '(0 . "CIRCLE") '(100 . "AcDbEntity")
                  (cons 8 *PF-WALL-LAYER*) '(6 . "DASHED")
                  '(100 . "AcDbCircle")
                  (cons 10 (list (car p) (cadr p) 0.0))
                  (cons 40 (* 0.5 *PF-MISS-RADIUS*)))))

;; Draw the dashed marker for a user-declared straight wall.
(defun pf:draw-wall-marker (p1 p2)
  (pf:ensure-dashed)
  (cal:ensure-layer *PF-WALL-LAYER* 8)
  (entmakex (list '(0 . "LINE") '(100 . "AcDbEntity")
                  (cons 8 *PF-WALL-LAYER*) '(6 . "DASHED")
                  '(100 . "AcDbLine")
                  (cons 10 (list (car p1) (cadr p1) 0.0))
                  (cons 11 (list (car p2) (cadr p2) 0.0)))))

;; Bounding box of a point list, as (minx miny maxx maxy).
(defun pf:bbox (pts / x0 y0 x1 y1 q)
  (foreach q pts
    (if (null x0)
      (setq x0 (car q) x1 (car q) y0 (cadr q) y1 (cadr q))
      (setq x0 (min x0 (car q)) x1 (max x1 (car q))
            y0 (min y0 (cadr q)) y1 (max y1 (cadr q)))))
  (list x0 y0 x1 y1))

;; Draw "1", "2", "3" beside each candidate, in that candidate's own
;; colour, with that fit's numbers spelled out to the right of it - so
;; the whole choice can be made from the drawing without reading the
;; command line at all.  The labels stack down the right-hand side of
;; the shape and are sized to the drawing, so they read at any zoom.
;; Returns the list of entities that make up the label.  The figures
;; go on two lines bracketing the number, so the label stays readable
;; instead of trailing a single very long line across the drawing.
(defun pf:label (num colour bb hgt row top bot / x y out e pr)
  (setq x   (+ (caddr bb) (* 0.6 hgt))
        y   (- (cadddr bb) (* row hgt 2.1))
        out nil)
  ;; the number itself, full height
  (setq e (entmakex (list '(0 . "TEXT") '(100 . "AcDbEntity")
                          (cons 8 *PF-OUT-LAYER*) (cons 62 colour)
                          '(100 . "AcDbText")
                          (cons 10 (list x y 0.0))
                          (cons 40 hgt)
                          (cons 1 num))))
  (if e (setq out (cons e out)))
  ;; its figures, smaller, on two lines to the right of the number
  (foreach pr (list (cons top (* 0.55 hgt)) (cons bot (* -0.05 hgt)))
    (setq e (entmakex (list '(0 . "TEXT") '(100 . "AcDbEntity")
                            (cons 8 *PF-OUT-LAYER*) (cons 62 colour)
                            '(100 . "AcDbText")
                            (cons 10 (list (+ x (* 1.4 hgt))
                                           (+ y (cdr pr))
                                           0.0))
                            (cons 40 (* 0.42 hgt))
                            (cons 1 (car pr)))))
    (if e (setq out (cons e out))))
  (reverse out))

;; Ring every point the chosen fit could not hold, on its own layer,
;; so they are easy to zoom to and judge: a mis-shot, a duplicate, or
;; a real feature the tolerance is too tight for.
;; Also writes the list of them to the side of the shape, worst first,
;; as "Pt.17   off by 1-7/8"" - so the misses can be worked through
;; without hunting for red circles.
(defun pf:mark-unheld (bad segs bb hgt / q d s dmin keyed pair th x y
                                         line)
  ;; markers from an earlier run describe a fit that no longer exists;
  ;; only ABHD's own are removed, never anything else on the layer
  (pf:purge-mine *PF-MISS-LAYER*)
  (if bad
    (progn
      (cal:ensure-layer *PF-MISS-LAYER* 1)
      ;; rings on the points themselves
      (foreach q bad
        (pf:tag-mine
          (entmakex (list '(0 . "CIRCLE") '(100 . "AcDbEntity")
                          (cons 8 *PF-MISS-LAYER*) '(100 . "AcDbCircle")
                          (cons 10 (list (car q) (cadr q) 0.0))
                          (cons 40 *PF-MISS-RADIUS*)))))
      ;; how far off each one is, worst first
      (setq keyed nil)
      (foreach q bad
        (setq dmin nil)
        (foreach s segs
          (setq d (pf:seg-dist q s))
          (if (or (null dmin) (< d dmin)) (setq dmin d)))
        (setq keyed (cons (cons dmin q) keyed)))
      (setq keyed (reverse (pf:sort-car keyed))
            th    (* 0.5 hgt)
            x     (+ (caddr bb) (* 0.6 hgt))
            y     (cadddr bb))
      (pf:tag-mine
        (entmakex (list '(0 . "TEXT") '(100 . "AcDbEntity")
                        (cons 8 *PF-MISS-LAYER*) '(100 . "AcDbText")
                        (cons 10 (list x y 0.0))
                        (cons 40 th)
                        (cons 1 (strcat "POINTS OFF THE LINE ("
                                        (itoa (length bad)) ")")))))
      (foreach pair keyed
        (setq y    (- y (* th 1.6))
              line (strcat "Pt." (pf:pt-name (cdr pair))
                           "   off by " (rtos (car pair) 4 4)))
        (pf:tag-mine
          (entmakex (list '(0 . "TEXT") '(100 . "AcDbEntity")
                          (cons 8 *PF-MISS-LAYER*) '(100 . "AcDbText")
                          (cons 10 (list x y 0.0))
                          (cons 40 th)
                          (cons 1 line)))))))
  keyed)

;; Print the hit report for the fit the user kept.  ALLOW is the run's
;; miss allowance (how many points were permitted to sit between the
;; on-the-shape threshold and the tolerance off the result).
(defun pf:report (newsegs pts tol allow prior / nl na hiton hitok miss
                                                q s s2 d dmin worst sum
                                                sumo no nice onpt inner
                                                ns i te ts kk mk nk
                                                hw hq pf-on-eps)
  ;; report against the same on-the-shape threshold the fit used
  (setq pf-on-eps (max *PF-ON-EPS* (* 0.25 tol)))
  (progn
      ;; -- segment mix, nice radii, arcs anchored on a point --------
      (setq nl 0 na 0 nice 0 onpt 0)
      (foreach s newsegs
        (if (< (abs (caddr s)) 1.0e-9)
          (setq nl (1+ nl))
          (progn
            (setq na (1+ na))
            (if (pf:nice-radius-p
                  (pf:bulge-radius (car s) (cadr s) (caddr s)))
              (setq nice (1+ nice)))
            ;; does this arc pass through a point other than its ends?
            (setq inner nil)
            (foreach q pts
              (if (and (> (cal:dist q (car s)) *PF-EXACT-EPS*)
                       (> (cal:dist q (cadr s)) *PF-EXACT-EPS*)
                       (<= (pf:seg-dist q s) (* 2.0 *PF-FIT-EPS*)))
                (setq inner T)))
            (if inner (setq onpt (1+ onpt))))))
      ;; -- how the survey points landed ------------------------------
      (setq hiton 0 hitok 0 miss 0 worst 0.0 sum 0.0 sumo 0.0 no 0)
      (foreach q pts
        (setq dmin nil)
        (foreach s newsegs
          (setq d (pf:seg-dist q s))
          (if (or (null dmin) (< d dmin)) (setq dmin d)))
        (if (> dmin worst) (setq worst dmin))
        (setq sum (+ sum dmin))
        (if (> dmin (pf:oneps))
          (setq sumo (+ sumo dmin) no (1+ no)))
        (cond
          ((<= dmin (pf:oneps)) (setq hiton (1+ hiton)))
          ((<= dmin tol)        (setq hitok (1+ hitok)))
          (T                    (setq miss  (1+ miss)))))
      ;; -- smoothness: worst kink at a joint that is not a corner ----
      (setq ns (length newsegs) i 0 mk 0.0 nk 0)
      (while (< i ns)
        (setq s  (nth i newsegs)
              s2 (nth (rem (1+ i) ns) newsegs)
              te (+ (angle (car s) (cadr s)) (* 2.0 (atan (caddr s))))
              ts (- (angle (car s2) (cadr s2)) (* 2.0 (atan (caddr s2))))
              kk (abs (cal:signed-dang te ts)))
        (if (<= kk *PF-CORNER-ANG*)     ; bigger = an intentional corner
          (progn
            (if (> kk mk) (setq mk kk))
            (if (> kk (+ *PF-TANG-TOL* 1.0e-6)) (setq nk (1+ nk)))))
        (setq i (1+ i)))
      (princ (strcat "\nABHD: " (itoa ns) " segments ("
                     (itoa nl) " lines + " (itoa na)
                     " curves) written to layer " *PF-POOL-LAYER* "."
                     "\n  Points on the perimeter:      " (itoa hiton)
                     "\n  Points off within tolerance:  " (itoa hitok)
                     "  (allowance " (itoa allow) ")"
                     "\n  Points beyond tolerance:      " (itoa miss)
                     "\n  Worst point deviation:        " (rtos worst 2 3)
                     "\n  Average off, all points:      "
                     (rtos (if (> (length pts) 0)
                             (/ sum (length pts))
                             0.0)
                           2 3)
                     "\n  Average off, off points only: "
                     (if (> no 0)
                       (strcat (rtos (/ sumo no) 2 3)
                               "  (" (itoa no) " point(s))")
                       "-  (every point is on the line)")
                     "\n  Curves through a point:       " (itoa onpt)
                     " of " (itoa na)
                     "\n  Curves on foot/half/inch radii:" (itoa nice)
                     " of " (itoa na)
                     "\n  Largest joint kink:           "
                     (rtos (* 180.0 (/ mk pi)) 2 1) " deg  (limit "
                     (rtos (* 180.0 (/ *PF-TANG-TOL* pi)) 2 1) ")"))
      (if (> nk 0)
        (princ (strcat "\n  (" (itoa nk)
                       " joint(s) needed more than the tangent limit to"
                       " close the loop)")))
      (if pf-walls
        (princ (strcat "\n  (" (itoa (length pf-walls))
                       " declared straight wall(s) kept dead straight)")))
      (if pf-holds
        (progn
          ;; every held point must sit ON the kept fit exactly; one
          ;; that does not means the drawn shape or a declared wall
          ;; overruled it, and that deserves a loud line of its own
          (setq hw 0.0)
          (foreach q pf-holds
            (setq dmin nil)
            (foreach s newsegs
              (setq d (pf:seg-dist q s))
              (if (or (null dmin) (< d dmin)) (setq dmin d)))
            (if (> dmin hw) (setq hw dmin hq q)))
          (if (<= hw *PF-EXACT-EPS*)
            (princ (strcat "\n  (" (itoa (length pf-holds))
                           " held point(s) all landed on the line"
                           " exactly)"))
            (princ (strcat "\n  WARNING: held Pt." (pf:pt-name hq)
                           " is off by " (rtos hw 2 4)
                           " - the drawn shape or a declared wall"
                           " overruled it.")))))
      (if (and *PF-MAX-ARCS* (> na *PF-MAX-ARCS*))
        (princ (strcat "\n  (the curve cap is " (itoa *PF-MAX-ARCS*)
                       " but " (itoa na) " curves was the fewest"
                       " reachable: a closed loop needs at least 2"
                       " segments)")))
      (if (> miss 0)
        (princ "\n  (points beyond tolerance: the curve cap and/or the drawn shape overruled them)"))
      (if (pf:self-crosses newsegs)
        (princ (strcat "\n  WARNING: the result crosses itself - the"
                       " automatic point order is probably wrong."
                       "  Draw a rough lines-only loop on layer "
                       *PF-POOL-LAYER*
                       " through the points in the right order and"
                       " select it too.")))
      (if (> prior 0)
        (princ (strcat "\n  (" (itoa prior)
                       " earlier fit(s) were already on layer "
                       *PF-OUT-LAYER* " - erase them if you only want"
                       " the new one)"))))
  (princ))

;; ---- guided mode ------------------------------------------------------
;; Re-fit the drawn perimeter LOOP through the survey points: every
;; vertex snaps to the nearest point within TOL, every drawn arc is
;; re-fitted through the points lying along it, and drawn straight
;; walls stay straight.  TOL and FTOL are two different jobs one number
;; used to do: TOL is the reach - which point belongs to which vertex
;; and which drawn arc - and is always the distance the user typed, so
;; every candidate reads the drawn shape the same way; FTOL is how
;; exactly the re-fit then has to hold those points, and is what a
;; candidate varies.  If the result needs more curves than MAXARCS, the
;; fit falls back to the points-driven builder - the drawn loop still
;; supplies the point order.
(defun pf:guided-fit (loop pts dpts tol ftol allow maxarcs
                      / verts used n s p1 p2 b cands clean ns newsegs
                        q d)
  ;; -- 1. snap each vertex to its nearest point within tol ----------
  (setq verts (mapcar '(lambda (s) (car s)) loop)
        used  nil)
  (setq verts
    (mapcar
      '(lambda (v / best bd)
         (setq best nil bd tol)
         (foreach q pts
           (setq d (cal:dist v q))
           (if (and (<= d bd) (not (member q used)))
             (setq best q bd d)))
         (if best (progn (setq used (cons best used)) best) v))
      verts))
  ;; -- 2. re-fit every arc segment through the points near it -------
  (setq newsegs nil n 0)
  (repeat (length loop)
    (setq s  (nth n loop)
          p1 (nth n verts)
          p2 (nth (rem (1+ n) (length verts)) verts)
          b  (caddr s))
    (if (< (abs b) 1.0e-9)
      ;; straight wall: trust the user, keep it straight
      (setq newsegs (cons (list p1 p2 0.0) newsegs))
      (progn
        ;; survey points lying near the ORIGINAL arc, excluding the
        ;; ones already consumed as vertices, sorted along the arc and
        ;; de-duplicated
        (setq cands nil)
        (foreach q pts
          (if (and (not (member q used))
                   (<= (pf:seg-dist q s) tol)
                   (> (cal:dist q p1) *PF-EXACT-EPS*)
                   (> (cal:dist q p2) *PF-EXACT-EPS*))
            (setq cands (cons (cons (pf:seg-param q s) q) cands))))
        (setq cands (mapcar 'cdr (pf:sort-car cands)))
        (setq clean nil)
        (foreach q cands
          (if (or (null clean)
                  (> (cal:dist q (car clean)) *PF-EXACT-EPS*))
            (setq clean (cons q clean))))
        (foreach ns (pf:fit-arc-seg p1 p2 b (reverse clean) ftol)
          (setq newsegs (cons ns newsegs)))))
    (setq n (1+ n)))
  (setq newsegs (reverse newsegs))
  ;; -- 3. the drawn shape is trusted, but the curve cap still wins --
  (if (and maxarcs
           (> (pf:arc-count newsegs) maxarcs)
           (>= (length dpts) 3))
    (progn
      (princ (strcat "\n  (the drawn perimeter needs "
                     (itoa (pf:arc-count newsegs))
                     " curves but the cap is " (itoa maxarcs)
                     " - refitting from the points instead)"))
      (setq pf-miss-left allow
            newsegs (pf:coarse-loop (pf:loop-order loop dpts)
                                    ftol maxarcs allow T))))
  newsegs)

;; Build one candidate fit in MODE - "tight", "asked" or "few", the
;; three aims listed against *PF-COMPARE*.  A non-nil TOUR means the
;; points drive the shape (points-only and ordering-sketch modes);
;; otherwise the drawn LOOP is re-fitted (guided mode).  TOL is always
;; the distance the user typed - it is what reads the drawn shape and
;; what the table judges every candidate against - and the mode sets
;; the three knobs that actually differ:
;;
;;   FTOL  how exactly the arcs must hold their points.  "tight" fits
;;         to *PF-TIGHT-TOL* (or to TOL when that is tighter yet),
;;         which is what drives its error towards nothing and its
;;         curve count up; the other two fit to TOL.
;;   LEFT  the miss allowance.  "tight" grants none, so no point is
;;         written off; "few" lifts it (and the per-span fair share
;;         with it), which is the whole trick - the arcs run as long
;;         as TOL permits instead of stopping at the standard share,
;;         and every point is still held to TOL by the span fitter.
;;   CAP   the curve cap.  Only "asked" honours it: capping the other
;;         two would be asking for the most curves, or the fewest,
;;         and then overruling the answer.
;;
;; Each call gets its own miss allowance and on-the-shape threshold.
(defun pf:build (tour loop pts dpts tol allow mode
                 / pf-miss-left pf-on-eps ftol left cap)
  (setq ftol (if (= mode "tight") (min tol *PF-TIGHT-TOL*) tol)
        left (cond ((= mode "tight") 0)
                   ((= mode "few")   1000000)
                   (T                allow))
        cap  (if (= mode "asked") *PF-MAX-ARCS*)
        pf-miss-left left
        pf-on-eps    (max *PF-ON-EPS* (* 0.25 ftol)))
  (if tour
    (pf:coarse-loop tour ftol cap left (not (= mode "few")))
    (pf:guided-fit loop pts dpts tol ftol left cap)))

;; Deviation summary for SEGS against PTS: (worst avg avg-off).
;;   worst   - furthest any point sits from the line
;;   avg     - mean over ALL points, so it counts the ones sitting on
;;             the line as the zeros they are
;;   avg-off - mean over only the points that are actually OFF the
;;             line (further than ON from it), which says how far the
;;             strays really stray; nil when nothing is off
(defun pf:devstats (segs pts on / w q s d dmin sum n sumo no)
  (setq w 0.0 sum 0.0 n 0 sumo 0.0 no 0)
  (foreach q pts
    (setq dmin nil)
    (foreach s segs
      (setq d (pf:seg-dist q s))
      (if (or (null dmin) (< d dmin)) (setq dmin d)))
    (if (> dmin w) (setq w dmin))
    (setq sum (+ sum dmin) n (1+ n))
    (if (> dmin on) (setq sumo (+ sumo dmin) no (1+ no))))
  (list w
        (if (> n 0) (/ sum n) 0.0)
        (if (> no 0) (/ sumo no) nil)))

;; A deviation for a table cell; "-" when there is nothing to average.
(defun pf:fmt-dev (x)
  (if x (rtos x 2 2) "-"))

;; ---- offer three fits and let the user pick ---------------------------
;; Knowing up front how much curve to spend on how much accuracy is the
;; hardest part of the command, so instead of asking the user to
;; imagine it, draw the two ends of that trade and the middle: the
;; most curves for the least error, the settings as typed, and the
;; fewest curves that still hold the distance.  Each goes on in its own
;; colour with what it costs, and the one they point at is kept.
;; Everything is judged against the tolerance the user actually typed,
;; so the columns compare like for like even though the three were not
;; built alike.
(defun pf:compare (tour loop pts dpts tol allow
                   / prior vars v e ent lab st onv segs bad allbad first
                     i pick idx keep ce bb hgt sel picked keyed pr res)
  (setq prior (pf:prior-fits))
  (cal:ensure-layer *PF-OUT-LAYER* 3)
  ;; every candidate is judged against the distance the user typed, so
  ;; "off the line" means the same thing in all three rows
  (setq onv (max *PF-ON-EPS* (* 0.25 tol)))
  ;; label height: a twentieth of the shape, so it reads at any zoom
  (setq bb  (pf:bbox pts)
        hgt (/ (max (- (caddr bb) (car bb))
                    (- (cadddr bb) (cadr bb)))
               20.0))
  (if (<= hgt 0.0) (setq hgt 1.0))
  (setq pf-phase "building the three candidate fits"
        vars     nil
        allbad   nil
        first    T
        i        1)
  (foreach v *PF-COMPARE*
    (setq segs (pf:build tour loop pts dpts tol allow (car v))
          ent  (pf:temp-add
                 (pf:make-pline
                   (mapcar '(lambda (s) (list (car s) (caddr s))) segs)
                   *PF-OUT-LAYER* (cadr v)))
          bad  (pf:unheld segs pts tol)
          st   (pf:devstats segs pts onv)
          ;; the same figures the table prints, spelled out so they
          ;; stand on their own beside the number in the drawing
          lab  (pf:label
                 (itoa i) (cadr v) bb hgt i
                 (strcat (itoa (length segs)) " segs    "
                         (itoa (pf:arc-count segs)) " curves    "
                         (itoa (length bad)) " not held    "
                         (cadddr v))
                 (strcat "worst " (pf:fmt-dev (car st))
                         "    avg all " (pf:fmt-dev (cadr st))
                         "    avg off " (pf:fmt-dev (caddr st))))
          vars (cons (list segs ent bad v lab st) vars)
          i    (1+ i))
    (foreach e lab (pf:temp-add e))
    ;; the note below is about points NO fit could hold, so only the
    ;; fits actually built to the user's distance get a vote.  The
    ;; tight one threads every point by construction - counting it
    ;; would empty the intersection every time and quietly retire the
    ;; warning that catches mis-shots
    (if (not (= (car v) "tight"))
      (if first
        (setq allbad bad first nil)
        (setq allbad (pf:isect allbad bad)))))
  (setq vars (reverse vars))
  (if (null (cadr (car vars)))
    (princ "\nABHD: could not draw the result - is the drawing read-only?")
    (progn
      (princ (strcat "\n\nThree candidate fits are now drawn on layer "
                     *PF-OUT-LAYER*
                     ",\neach numbered on screen in its own colour:\n"))
      (princ "\n   #  segs  curves  worst off  avg all  avg off  not held  ")
      (princ "\n   -  ----  ------  ---------  -------  -------  --------  ")
      (setq i 1)
      (foreach v vars
        (setq segs (car v) bad (caddr v) ce (cadddr v) st (nth 5 v))
        (princ (strcat "\n   " (itoa i) "  "
                       (cal:pad (itoa (length segs)) 6)
                       (cal:pad (itoa (pf:arc-count segs)) 8)
                       (cal:pad (pf:fmt-dev (car st)) 11)
                       (cal:pad (pf:fmt-dev (cadr st)) 9)
                       (cal:pad (pf:fmt-dev (caddr st)) 9)
                       (cal:pad (itoa (length bad)) 10)
                       (cadddr ce)))
        (setq i (1+ i)))
      (princ (strcat "\n\n  \"not held\" = points further than "
                     (rtos tol 2 3) " from that fit."
                     "\n  \"avg all\" averages every point; \"avg off\""
                     " averages only the points that are off the line"
                     "\n  (further than " (rtos onv 2 3) " from it)."))
      (princ (strcat "\n  All three are measured against the "
                     (rtos tol 2 3) " you typed, but only one is built"
                     " to it:"
                     "\n  the tight fit spends curves to drive the error"
                     " towards nothing (it"
                     "\n  ignores that distance"
                     (if *PF-MAX-ARCS* " and the curve cap" "")
                     "), the middle one is your settings exactly,"
                     "\n  and the few fit holds the same distance with"
                     " as few curves as it can."))
      (if allbad
        (princ (strcat "\n  NOTE: " (itoa (length allbad))
                       " point(s) could not be held by ANY fit built to"
                       " that distance - likely a mis-shot, a duplicate,"
                       " or a corner that needs more points around it."
                       "\n  (the tight fit threads every point it can"
                       " reach, so it does not get a vote here.)")))
      ;; -- let the user choose ---------------------------------------
      ;; Clicking the outline you want beats translating a colour into
      ;; a number, so a pick on screen is offered first; typing the
      ;; number still works for anyone who prefers the keyboard.
      (setq pf-phase "waiting for the choice of fit")
      (princ "\n\n  Click the outline you want to keep, or type its number.")
      (princ "\n  Redo refits with new settings, and lets you omit points first.")
      (initget "1 2 3 All None Redo")
      (setq pick (getkword
                   "\n  Keep which fit - click one, or [1/2/3/All/None/Redo] <2>: "))
      (if (null pick)
        ;; no keyword typed: give them a click, and fall back to 2
        (progn
          (setq sel (entsel "\n  Pick the outline to keep (or Enter for 2): "))
          (if sel
            (progn
              (setq picked (car sel) i 1)
              (foreach v vars
                (if (or (eq picked (cadr v))
                        (member picked (nth 4 v)))
                  (setq pick (itoa i)))
                (setq i (1+ i)))
              (if (null pick)
                (progn
                  (princ "\n  (that is not one of the three - keeping 2)")
                  (setq pick "2"))))
            (setq pick "2"))))
      ;; anything not explicitly kept stays registered as scaffolding
      ;; and is swept when the command ends
      (cond
        ((= pick "Redo")
         ;; clear this trio off the screen right away - the caller
         ;; asks its questions and draws a fresh one
         (foreach v vars
           (if (and (cadr v) (entget (cadr v))) (entdel (cadr v)))
           (foreach e (nth 4 v)
             (if (and e (entget e)) (entdel e))))
         (setq res 'REDO))
        ((= pick "All")
         (foreach v vars
           (pf:temp-drop (cadr v))
           (foreach e (nth 4 v) (pf:temp-drop e)))
         (princ "\nKeeping all three, in their preview colours.")
         (princ "\n  (the number labels are kept too - erase them when done)"))
        ((= pick "None")
         (princ "\nAll three erased - nothing was added to the drawing."))
        (T
         (setq idx (atoi pick) i 1)
         (foreach v vars
           (if (= i idx)
             (setq keep v)
             ;; erase the losers now, so the keeper is clear on screen
             ;; while the report is read
             (if (and (cadr v) (entget (cadr v))) (entdel (cadr v))))
           (setq i (1+ i)))
         ;; name the aim that was kept, not just its number - the three
         ;; were built to different ends and the report that follows is
         ;; read against the settings as typed
         (if keep
           (princ (strcat "\n  Keeping fit " pick " - "
                          (cadddr (cadddr keep)) ".")))
         (if (cadr keep)
           (progn
             (pf:temp-drop (cadr keep))
             (pf:set-bylayer (cadr keep))))))
      (if keep
        (progn
          (setq keyed (pf:mark-unheld (caddr keep) (car keep) bb hgt))
          (pf:report (car keep) pts tol allow prior)
          (if keyed
            (progn
              (princ (strcat "\n  " (itoa (length keyed))
                             " point(s) beyond the distance are ringed"
                             " on layer " *PF-MISS-LAYER*
                             " and listed beside the pool, worst first:"))
              (foreach pr keyed
                (princ (strcat "\n    Pt." (pf:pt-name (cdr pr))
                               "   off by " (rtos (car pr) 4 4))))))
          ;; one perimeter was chosen, so the floor can be drawn too
          (pf:bottom (car keep) dpts T)))))
  (princ)
  res)

;; ---- the pool bottom (hopper) ----------------------------------------
;; After a perimeter is kept, the floor can be drawn in the same
;; sitting: the SHALLOW BREAK and DEEP BREAK lines across the pool,
;; and the hopper - the flat deep-end floor - as an inward offset of
;; the perimeter beyond the deep break.  Three offsets shape it,
;; asked by survey point number: one at each deep break point and one
;; at the back of the hopper, blending gradually in between when they
;; differ.  A slope line joins each of the hopper's ends to the
;; shallow break point on its side - straight, guided along the
;; perimeter's curve, or guided through points the user picks at
;; pinned offsets, asked per side.  The hopper and guided slopes are
;; drawn as few long arcs (merged within *PF-BOTTOM-FIT* - curved,
;; not faceted, not heavy).  Lines and dimensions all land on
;; *PF-POOL-LAYER*.

;; Closest point ON segment (p1 p2 bulge) to P - pf:seg-dist's twin,
;; returning the foot of the distance instead of the distance.
(defun pf:seg-near (p seg / p1 p2 b v w len2 t2 g c r a1 a2 ap sweep
                            rel)
  (setq p  (cal:2d p)
        p1 (cal:2d (car seg))
        p2 (cal:2d (cadr seg))
        b  (caddr seg))
  (if (< (abs b) 1.0e-9)
    ;; straight: project onto the segment, clamp to its ends
    (progn
      (setq v    (cal:v- p2 p1)
            w    (cal:v- p p1)
            len2 (cal:dot v v))
      (if (< len2 1.0e-20)
        p1
        (progn
          (setq t2 (/ (cal:dot w v) len2))
          (if (< t2 0.0) (setq t2 0.0))
          (if (> t2 1.0) (setq t2 1.0))
          (cal:v+ p1 (cal:v* v t2)))))
    ;; arc: the radial foot when P falls inside the sweep, else the
    ;; nearer endpoint
    (progn
      (setq g (pf:arc-geom p1 p2 b))
      (if (null g)
        (if (<= (cal:dist p p1) (cal:dist p p2)) p1 p2)
        (progn
          (setq c  (car g)  r (cadr g)
                a1 (caddr g) a2 (cadddr g)
                ap (angle c p))
          (if (> b 0.0)
            (setq sweep (cal:angnorm (- a2 a1)) rel (cal:angnorm (- ap a1)))
            (setq sweep (cal:angnorm (- a1 a2)) rel (cal:angnorm (- ap a2))))
          (if (<= rel sweep)
            (cal:v+ c (cal:v* (list (cos ap) (sin ap)) r))
            (if (<= (cal:dist p p1) (cal:dist p p2)) p1 p2)))))))

;; Closest point on the whole loop to P.
(defun pf:curve-near (p segs / best bd s q d)
  (foreach s segs
    (setq q (pf:seg-near p s)
          d (cal:dist p q))
    (if (or (null bd) (< d bd)) (setq best q bd d)))
  best)

;; The subset of PTS sitting within EPS of the loop SEGS - the
;; perimeter's own survey points, as opposed to depth shots and deck
;; points that only happen to be nearby.
(defun pf:near-loop (pts segs eps / out q s d dmin)
  (foreach q pts
    (setq dmin nil)
    (foreach s segs
      (setq d (pf:seg-dist q s))
      (if (or (null dmin) (< d dmin)) (setq dmin d)))
    (if (and dmin (<= dmin eps)) (setq out (cons q out))))
  (reverse out))

;; Sample the closed loop into points spaced about STEP apart, walking
;; it in order: each segment contributes its start point plus enough
;; interior points that no gap exceeds STEP (its end is the next
;; segment's start, so nothing doubles up).
(defun pf:sample-loop (segs step / out s p1 p2 b g c r a1 a2 sweep
                                   len k j aa)
  (setq out nil)
  (foreach s segs
    (setq p1  (cal:2d (car s))
          p2  (cal:2d (cadr s))
          b   (caddr s)
          out (cons p1 out)
          g   (if (>= (abs b) 1.0e-9) (pf:arc-geom p1 p2 b)))
    (if g
      (progn
        (setq c  (car g)   r  (cadr g)
              a1 (caddr g) a2 (cadddr g))
        (if (> b 0.0)
          (setq sweep (cal:angnorm (- a2 a1)))
          (setq sweep (- (cal:angnorm (- a1 a2)))))
        (setq len (* r (abs sweep))
              k   (max 1 (fix (/ len step)))
              j   1)
        (while (< j k)
          (setq aa  (+ a1 (* sweep (/ (float j) (float k))))
                out (cons (list (+ (car c) (* r (cos aa)))
                                (+ (cadr c) (* r (sin aa))))
                          out)
                j   (1+ j))))
      (progn
        (setq len (cal:dist p1 p2)
              k   (max 1 (fix (/ len step)))
              j   1)
        (while (< j k)
          (setq out (cons (cal:v+ p1 (cal:v* (cal:v- p2 p1)
                                             (/ (float j) (float k))))
                          out)
                j   (1+ j))))))
  (reverse out))

;; Signed shoelace area of a point ring: positive = counter-clockwise.
;; Only the SIGN is used, to orient the inward normals.
(defun pf:loop-area (pts / sum prev q)
  (setq sum 0.0 prev (last pts))
  (foreach q pts
    (setq sum  (+ sum (- (* (car prev) (cadr q))
                         (* (car q) (cadr prev))))
          prev q))
  (/ sum 2.0))

;; Index of the sample nearest P.
(defun pf:near-idx (p pts / k best bd q d)
  (setq k 0 best 0 bd nil)
  (foreach q pts
    (setq d (cal:dist p q))
    (if (or (null bd) (< d bd)) (setq best k bd d))
    (setq k (1+ k)))
  best)

;; Inward unit normal of the sampled loop at index I.  The tangent
;; comes from the neighbouring samples; SGN is +1 for a counter-
;; clockwise ring (interior on the left of travel), -1 for clockwise.
(defun pf:samp-normal (i pts sgn / n u)
  (setq n (length pts)
        u (cal:unit (cal:v- (nth (rem (1+ i) n) pts)
                           (nth (rem (+ i n -1) n) pts))))
  (if (null u)
    (setq u (cal:unit (cal:v- (nth (rem (1+ i) n) pts) (nth i pts)))))
  (if (null u) (setq u '(1.0 0.0)))
  (cal:v* (cal:perp u) sgn))

;; A LINE on LAYER (nil = the pool layer) with linetype LTYP
;; (nil = ByLayer).
(defun pf:make-line (p1 p2 layer ltyp / dxf)
  (setq dxf (list '(0 . "LINE") '(100 . "AcDbEntity")
                  (cons 8 (if layer layer *PF-POOL-LAYER*))))
  (if ltyp (setq dxf (append dxf (list (cons 6 ltyp)))))
  (entmakex (append dxf
                    (list '(100 . "AcDbLine")
                          (cons 10 (list (car p1) (cadr p1) 0.0))
                          (cons 11 (list (car p2) (cadr p2) 0.0))))))

;; Make sure the DASHED2 linetype (the half-size dashes marking the
;; underwater break stubs) exists - pure entmake, like pf:ensure-dashed.
(defun pf:ensure-dashed2 ()
  (if (not (tblsearch "LTYPE" "DASHED2"))
    (entmake (list '(0 . "LTYPE") '(100 . "AcDbSymbolTableRecord")
                   '(100 . "AcDbLinetypeTableRecord")
                   '(2 . "DASHED2") '(70 . 0)
                   '(3 . "Dashed (.5x) _ _ _ _ _")
                   '(72 . 65) '(73 . 2) '(40 . 9.0)
                   '(49 . 6.0) '(74 . 0)
                   '(49 . -3.0) '(74 . 0)))))

;; An OPEN polyline through PTS on the pool layer, with the segment
;; bulges BLS (one per segment, nil = all straight).
(defun pf:make-open-pline (pts bls / dxf q)
  (setq dxf (list '(0 . "LWPOLYLINE") '(100 . "AcDbEntity")
                  (cons 8 *PF-POOL-LAYER*)
                  '(100 . "AcDbPolyline")
                  (cons 90 (length pts)) '(70 . 0)))
  (foreach q pts
    (setq dxf (append dxf (list (cons 10 q)
                                (cons 42 (if bls (car bls) 0.0))))
          bls (cdr bls)))
  (entmakex dxf))

;; One arc from sample I to sample J through their middle sample: its
;; bulge when every sample between them stays within *PF-BOTTOM-FIT*
;; of it, else nil.  (0.0 - a straight stretch - is a valid answer:
;; the offset of a dead-straight wall IS straight.)
(defun pf:arc-fits (pts i j / a b m bl seg k ok)
  (setq a   (nth i pts)
        b   (nth j pts)
        m   (nth (/ (+ i j) 2) pts)
        bl  (pf:bulge-3pt a m b)
        seg (list a b bl)
        ok  T
        k   (1+ i))
  (while (and ok (< k j))
    (if (> (pf:seg-dist (nth k pts) seg) *PF-BOTTOM-FIT*)
      (setq ok nil))
    (setq k (1+ k)))
  (if ok bl))

;; Replace a densely sampled run with as FEW arcs as hold every
;; sample within *PF-BOTTOM-FIT* of the drawn curve: spans grow
;; greedily (longest first), each drawn as the 3-point arc through
;; its middle sample, and every point in KEEP stays a vertex exactly,
;; so the dimension anchors sit ON the line.  Returns (verts bulges)
;; ready for pf:make-open-pline.
(defun pf:merge-arcs (pts keep / n idx q k i j bl verts bls prevk
                                stop rest)
  (setq n   (length pts)
        idx (list 0 (1- n)))
  (foreach q keep
    (setq k (pf:near-idx q pts))
    (if (and (> k 0) (< k (1- n)) (not (member k idx)))
      (setq idx (cons k idx))))
  (setq idx (mapcar 'car
                    (pf:sort-car (mapcar '(lambda (k) (cons k k))
                                         idx))))
  (setq verts (list (car pts))
        bls   nil
        prevk (car idx)
        rest  (cdr idx))
  (while rest
    (setq stop (car rest)
          i    prevk)
    (while (< i stop)
      (setq j stop bl nil)
      (while (and (null bl) (> j (1+ i)))
        (if (null (setq bl (pf:arc-fits pts i j)))
          (setq j (1- j))))
      (if (null bl)
        (setq j  (1+ i)
              bl (pf:arc-fits pts i j)))
      (setq verts (cons (nth j pts) verts)
            bls   (cons bl bls)
            i     j))
    (setq prevk stop
          rest  (cdr rest)))
  (list (reverse verts) (reverse bls)))

;; The dimension style to stamp on a new dim: NAME when the drawing
;; actually has it, else the current style - with a note the first
;; time each missing name comes up (pf-dim-warned is run-scoped).
(defun pf:dim-style (name)
  (if (and name (tblsearch "DIMSTYLE" name))
    name
    (progn
      (if (and name (not (member name pf-dim-warned)))
        (progn
          (setq pf-dim-warned (cons name pf-dim-warned))
          (princ (strcat "\n  (dimension style \"" name
                         "\" is not in this drawing - using the"
                         " current style instead)"))))
      (getvar "DIMSTYLE"))))

;; An aligned dimension measuring PA to PB, in dimension style STY
;; (nil = current), its dimension line through PDL - or right on the
;; measured stretch when PDL is nil.  The empty group 1 makes AutoCAD
;; fill in the measured value (the "auto" dimension text) and build
;; the dimension block; nil comes back when the drawing cannot take a
;; dimension, and the caller says so once.
(defun pf:make-dim (pa pb sty pdl / m)
  (setq m (if pdl pdl (cal:mid pa pb)))
  (entmakex (list '(0 . "DIMENSION") '(100 . "AcDbEntity")
                  (cons 8 *PF-POOL-LAYER*)
                  '(100 . "AcDbDimension")
                  (cons 3 (pf:dim-style sty))
                  (cons 10 (list (car m) (cadr m) 0.0))
                  '(70 . 33)                     ; aligned + block flag
                  '(1 . "")                      ; text = the measurement
                  '(100 . "AcDbAlignedDimension")
                  (cons 13 (list (car pa) (cadr pa) 0.0))
                  (cons 14 (list (car pb) (cadr pb) 0.0)))))

;; Show an offset the way it was typed: architectural when it came in
;; as feet-and-inches, plain inches otherwise.  DEF is (value . ftin).
(defun pf:fmt-off (def)
  (if (cdr def) (rtos (car def) 4 4) (rtos (car def) 2 2)))

;; Read an offset distance, remembering HOW it was typed - as
;; feet-and-inches (3'6) or as plain inches (42) - because that
;; choice picks the dimension style later.  Returns (value . T) for
;; feet-and-inches, (value . nil) for inches; Enter takes DEF, a
;; (value . ftin) pair from the previous entry.  Negative input is
;; refused, zero too unless ALLOWZERO (a waypoint may pin the line
;; to the wall).  With BACK non-nil, typing B (Back; Undo works too)
;; returns the symbol PF-BACK instead.
(defun pf:get-off (msg def allowzero back / s v res)
  (setq res nil)
  (while (null res)
    (setq s (getstring T (strcat msg " <" (pf:fmt-off def) ">"
                                 (if back " [Back]" "") ": ")))
    (cond
      ((= s "") (setq res def))
      ((and back (cal:back-word-p s)) (setq res 'PF-BACK))
      (T
       (setq v (distof s 4))
       (cond
         ((null v)
          (princ "\n  (that is not a distance - type inches like 42, or feet and inches like 3'6)"))
         ((or (< v 0.0) (and (= v 0.0) (not allowzero)))
          (princ (strcat "\n  (the offset must be a positive distance"
                         (if allowzero " or zero" "") ")")))
         (T (setq res (cons v (if (wcmatch s "*'*") T nil))))))))
  res)

;; Snap a picked break point onto the nearest survey point, warning
;; when the pick was nowhere near one (same rule as declared walls).
(defun pf:snap-break (p dpts / q)
  (setq p (cal:2d p)
        q (pf:nearest p dpts))
  (if (null q)
    p
    (progn
      (if (> (cal:dist p q) (* 3.0 *PF-TOL*))
        (princ "\n  (picked well away from any survey point - snapped to the nearest one)"))
      q)))

;; The survey point marking the BACK of the hopper: cast a ray from
;; the middle of the deep break line, perpendicular to it, away from
;; the shallow break, and take the point closest to that ray on that
;; side.  nil when no survey point lies beyond the deep break at all.
(defun pf:hopper-back (dp1 dp2 sp1 sp2 dpts / mid u q t2 lat back bd)
  (setq mid (cal:mid dp1 dp2)
        u   (cal:unit (cal:perp (cal:v- dp2 dp1))))
  (if u
    (progn
      (if (> (cal:dot u (cal:v- (cal:mid sp1 sp2) mid)) 0.0)
        (setq u (cal:v* u -1.0)))
      (setq back nil bd nil)
      (foreach q dpts
        (setq t2  (cal:dot (cal:v- q mid) u)
              lat (abs (cal:dot (cal:v- q mid) (cal:perp u))))
        (if (and (> t2 *PF-EXACT-EPS*)
                 (or (null bd) (< lat bd)))
          (setq back q bd lat)))
      back)))

;; The hopper outline: walk the sampled perimeter from the deep break
;; point at sample I1 to the one at I2, whichever way round passes the
;; back point at IB, pushing every point inward by an offset that
;; blends OFF1 at the start through OFF3 at the back to OFF2 at the
;; end - a straight run over arc length, so differing offsets change
;; gradually.  P1 and P2 are the exact break positions and stand in
;; for their samples, so the hopper's ends land exactly off them.
;; Returns (hopperPts backPos perimeterPts walkDir), or nil when the
;; two deep break points share a sample.
(defun pf:hopper-pts (samps sgn i1 i2 ib p1 p2 off1 off2 off3
                      / n fwdb fwd2 dir cnt kb idxs i k base cum lt lb
                        prev q out j cj offv bl)
  (setq n    (length samps)
        fwdb (rem (+ (- ib i1) n) n)
        fwd2 (rem (+ (- i2 i1) n) n))
  ;; walk whichever way round passes the back of the hopper
  (if (<= fwdb fwd2)
    (setq dir 1  cnt fwd2 kb fwdb)
    (setq dir -1 cnt (rem (+ (- i1 i2) n) n)
          kb  (rem (+ (- i1 ib) n) n)))
  (if (< cnt 2)
    nil
    (progn
      ;; the perimeter points under the hopper, break to break
      (setq idxs nil i i1 k 0)
      (while (<= k cnt)
        (setq idxs (cons i idxs)
              i    (rem (+ i dir n) n)
              k    (1+ k)))
      (setq idxs (reverse idxs)
            base nil)
      (foreach i idxs (setq base (cons (nth i samps) base)))
      (setq base (reverse base)
            base (cons p1 (cdr base))
            base (reverse (cons p2 (cdr (reverse base)))))
      ;; arc length along the walk places the blend
      (setq cum nil lt 0.0 prev nil)
      (foreach q base
        (if prev (setq lt (+ lt (cal:dist prev q))))
        (setq cum (cons lt cum) prev q))
      (setq cum (reverse cum)
            lb  (nth kb cum))
      (if (< lt 1.0e-9)
        nil
        (progn
          (setq out nil j 0)
          (foreach q base
            (setq cj   (nth j cum)
                  offv (if (<= cj lb)
                         (+ off1 (* (- off3 off1)
                                    (if (> lb 1.0e-9) (/ cj lb) 1.0)))
                         (+ off3 (* (- off2 off3)
                                    (if (> (- lt lb) 1.0e-9)
                                      (/ (- cj lb) (- lt lb))
                                      1.0))))
                  out  (cons (cal:v+ q (cal:v*
                                         (pf:samp-normal (nth j idxs)
                                                         samps sgn)
                                         offv))
                             out)
                  j    (1+ j)))
          (setq out (reverse out))
          ;; the hopper's corners sit ON the deep break line itself,
          ;; OFF1 and OFF2 in from its ends - not merely near it
          (setq bl (cal:unit (cal:v- p2 p1)))
          (if bl
            (setq out (cons (cal:v+ p1 (cal:v* bl off1)) (cdr out))
                  out (reverse (cons (cal:v+ p2 (cal:v* bl (- off2)))
                                     (cdr (reverse out))))))
          (list out kb base dir))))))

;; Offset at arc position CJ, read off the piecewise profile ANCHORS
;; ((position . offset) ... sorted ascending, both ends included):
;; the offset runs straight between neighbouring anchors.
(defun pf:off-at (cj anchors / prev a res span)
  (setq prev (car anchors) res nil)
  (foreach a (cdr anchors)
    (if (and (null res) (<= cj (car a)))
      (setq span (- (car a) (car prev))
            res  (if (< span 1.0e-9)
                   (cdr a)
                   (+ (cdr prev)
                      (* (- (cdr a) (cdr prev))
                         (/ (- cj (car prev)) span))))))
    (if (null res) (setq prev a)))
  (if res res (cdr prev)))

;; A guided slope line: walk CNT samples from index IA in direction
;; DIR (the side away from the hopper), following the perimeter with
;; an inward offset that starts at OFFA on the hopper's end and eases
;; to nothing at the shallow break.  WAYPTS - (surveyPt offset ftin)
;; entries the user picked along this side - pin the offset to those
;; values where they sit, measured square off the wall (along the
;; local inward normal); between anchors the offset runs straight
;; over arc length, so the picked points steer the line and the curve
;; carries it the rest of the way.  PA and PB are the exact break
;; positions; the first point lands exactly on the hopper's corner EA
;; (which sits on the deep break line), the last exactly on the
;; shallow break point.
;; Returns (linePts dimTriples) - one (wallPt linePt ftin) per
;; accepted waypoint, so its offset can be dimensioned in the style
;; its format asks for - or nil when the walk is too short to bother
;; (the caller draws a straight line then).
(defun pf:slope-pts (samps sgn ia dir cnt pa pb offa waypts ea
                     / n idxs i k base cum lt prev q out j anchors wp
                       woff wfl bk bd d dims dv fade w cj out2)
  (setq n (length samps))
  (if (< cnt 2)
    nil
    (progn
      (setq idxs nil i ia k 0)
      (while (<= k cnt)
        (setq idxs (cons i idxs)
              i    (rem (+ i dir n) n)
              k    (1+ k)))
      (setq idxs (reverse idxs)
            base nil)
      (foreach i idxs (setq base (cons (nth i samps) base)))
      (setq base (reverse base)
            base (cons pa (cdr base))
            base (reverse (cons pb (cdr (reverse base)))))
      (setq cum nil lt 0.0 prev nil)
      (foreach q base
        (if prev (setq lt (+ lt (cal:dist prev q))))
        (setq cum (cons lt cum) prev q))
      (setq cum (reverse cum))
      (if (< lt 1.0e-9)
        nil
        (progn
          ;; the offset profile: pinned at both ends and at each
          ;; waypoint the user gave along this side
          (setq anchors (list (cons 0.0 offa)) dims nil)
          (foreach wp waypts
            (setq woff (cadr wp) wfl (caddr wp) wp (car wp)
                  bk nil bd nil k 0)
            (foreach q base
              (setq d (cal:dist wp q))
              (if (or (null bd) (< d bd)) (setq bk k bd d))
              (setq k (1+ k)))
            (cond
              ((> bd *PF-BOTTOM-STEP*)
               (princ (strcat "\n  (Pt." (pf:pt-name wp)
                              " is not on this side of the pool - its"
                              " offset is ignored)")))
              ((or (= bk 0) (= bk cnt))
               (princ (strcat "\n  (Pt." (pf:pt-name wp)
                              " sits on a break point - its offset is"
                              " ignored, the breaks rule there)")))
              (T
               (setq anchors (cons (cons (nth bk cum) woff) anchors)
                     dims    (cons (list (nth bk base) bk wfl)
                                   dims)))))
          (setq anchors (pf:sort-car anchors)
                anchors (append anchors (list (cons lt 0.0))))
          (setq out nil j 0)
          (foreach q base
            (setq out (cons (cal:v+ q (cal:v*
                                        (pf:samp-normal (nth j idxs)
                                                        samps sgn)
                                        (pf:off-at (nth j cum)
                                                   anchors)))
                            out)
                  j   (1+ j)))
          (setq out (reverse out))
          ;; the line must DEPART from the hopper's corner EA, not
          ;; merely have its first vertex moved there: pull the early
          ;; stretch by the gap between the corner and the plain
          ;; normal-offset start, fading the pull to nothing by the
          ;; first pinned anchor (or the shallow break when there is
          ;; none), so waypoint offsets stay exact
          (if ea
            (progn
              (setq dv   (cal:v- ea (car out))
                    fade (car (cadr anchors)))
              (if (< fade 1.0e-9) (setq fade lt))
              (setq out2 nil j 0)
              (foreach q out
                (setq cj   (nth j cum)
                      w    (if (< cj fade) (- 1.0 (/ cj fade)) 0.0)
                      out2 (cons (cal:v+ q (cal:v* dv w)) out2)
                      j    (1+ j)))
              (setq out (reverse out2))))
          (list out
                (mapcar '(lambda (pr) (list (car pr)
                                            (nth (cadr pr) out)
                                            (caddr pr)))
                        (reverse dims))))))))

;; Drop consecutive duplicates closer than a hundredth - a tight
;; offset can fold neighbouring samples onto each other.
(defun pf:thin-run (pts / out prev q)
  (foreach q pts
    (if (or (null prev) (> (cal:dist prev q) 0.01))
      (setq out (cons q out) prev q)))
  (reverse out))

;; Draw the rest of the bottom package: the hopper outline, the slope
;; lines, and an aligned dimension on each of the three hopper
;; offsets plus every waypoint offset.  GUIDED holds the user's
;; answer for each side: nil = straight, T = guided along the
;; perimeter's curve, or a list of (surveyPt offset ftin) waypoints =
;; guided through those pinned offsets.  Dims not anchored to a break
;; point (the hopper back, the waypoints) carry the dimension style
;; their typed format asks for: *PF-DIM-FTIN* when the offset came in
;; as feet-and-inches (BFL for the back one), *PF-DIM-IN* for plain
;; inches.  LINES holds the two break lines pf:bottom already drew;
;; everything stays scaffolding until the end, so an error in between
;; sweeps the lot - the bottom only ever lands complete.
(defun pf:bottom-draw (segs sp1 sp2 dp1 dp2 back off1 off2 off3 bfl
                       lines guided
                       / made samps sgn i1 i2 ib hp hpts base kb dir
                         n is1 is2 sl spec wdims desc1 desc2 e1 e2 q e
                         dimfail u)
  (setq pf-phase "building the hopper"
        samps    (pf:sample-loop segs *PF-BOTTOM-STEP*)
        sgn      (if (< (pf:loop-area samps) 0.0) -1.0 1.0)
        i1       (pf:near-idx dp1 samps)
        i2       (pf:near-idx dp2 samps)
        ib       (pf:near-idx (pf:curve-near back segs) samps)
        hp       (pf:hopper-pts samps sgn i1 i2 ib dp1 dp2
                                off1 off2 off3))
  (if (null hp)
    ;; the break lines stay scaffolding and are swept with the rest
    (princ "\n  (the deep break points sit on top of each other on the perimeter - the pool bottom was not added)")
    (progn
      (setq hpts (car hp)  kb  (cadr hp)
            base (caddr hp) dir (cadddr hp)
            e1   (car hpts) e2  (last hpts)
            made lines)
      (if (<= (cal:dist dp1 dp2) (+ off1 off2))
        (princ "\n  (warning: the two deep end offsets meet or overlap across the pool)"))
      ;; the deep break becomes THREE lines on the pool layer: dashed
      ;; stubs from each wall in to the hopper's corners, and a solid
      ;; (ByLayer) run across the hopper between them - the single
      ;; placeholder line drawn during the questions goes away
      (if (and (cadr lines) (entget (cadr lines)))
        (entdel (cadr lines)))
      (pf:ensure-dashed2)
      (cal:ensure-layer *PF-POOL-LAYER* 4)
      (setq made (cons (pf:temp-add (pf:tag-mine
                         (pf:make-line dp1 e1 nil "DASHED2")))
                       made)
            made (cons (pf:temp-add (pf:tag-mine
                         (pf:make-line e1 e2 nil nil)))
                       made)
            made (cons (pf:temp-add (pf:tag-mine
                         (pf:make-line e2 dp2 nil "DASHED2")))
                       made))
      ;; the hopper outline: the dense samples merge into as few long
      ;; arcs as hold the shape, the back anchor kept as a vertex so
      ;; its dimension sits on the line
      (setq sl   (pf:merge-arcs (pf:thin-run hpts)
                                (list (nth kb hpts)))
            made (cons (pf:temp-add (pf:tag-mine
                         (pf:make-open-pline (car sl) (cadr sl))))
                       made))
      ;; the slope lines: each hopper end joins the shallow break
      ;; point on its own side of the loop, so the two never cross -
      ;; walking away from the hopper from each deep break end, the
      ;; shallow projection met first is that side's partner
      (setq n   (length samps)
            is1 (pf:near-idx sp1 samps)
            is2 (pf:near-idx sp2 samps))
      (if (< (rem (+ (* dir (- i1 is2)) n n) n)
             (rem (+ (* dir (- i1 is1)) n n) n))
        (setq q sp1 sp1 sp2 sp2 q
              q is1 is1 is2 is2 q))
      ;; straight, eased in along the perimeter's own curve, or eased
      ;; through the offsets the user pinned at picked points
      (setq wdims nil
            spec  (car guided)
            sl    (if spec
                    (pf:slope-pts samps sgn i1 (- dir)
                                  (rem (+ (* dir (- i1 is1)) n n) n)
                                  dp1 sp1 off1
                                  (if (eq spec T) nil spec) e1)))
      (setq q     (if sl (pf:merge-arcs (pf:thin-run (car sl))
                                        (mapcar 'cadr (cadr sl)))))
      (setq made  (cons (pf:temp-add (pf:tag-mine
                          (if sl
                            (pf:make-open-pline (car q) (cadr q))
                            (pf:make-line e1 sp1 nil nil))))
                        made)
            wdims (if sl (append wdims (cadr sl)))
            desc1 (cond ((null sl) "straight")
                        ((cadr sl) (strcat "guided through "
                                           (itoa (length (cadr sl)))
                                           " point(s)"))
                        (T "guided")))
      (setq spec (cadr guided)
            sl   (if spec
                   (pf:slope-pts samps sgn i2 dir
                                 (rem (+ (* dir (- is2 i2)) n n) n)
                                 dp2 sp2 off2
                                 (if (eq spec T) nil spec) e2)))
      (setq q     (if sl (pf:merge-arcs (pf:thin-run (car sl))
                                        (mapcar 'cadr (cadr sl)))))
      (setq made  (cons (pf:temp-add (pf:tag-mine
                          (if sl
                            (pf:make-open-pline (car q) (cadr q))
                            (pf:make-line e2 sp2 nil nil))))
                        made)
            wdims (if sl (append wdims (cadr sl)) wdims)
            desc2 (cond ((null sl) "straight")
                        ((cadr sl) (strcat "guided through "
                                           (itoa (length (cadr sl)))
                                           " point(s)"))
                        (T "guided")))
      ;; dimension each offset right where it applies.  The deep end
      ;; gets the K/L/M-style string: wall-to-hopper, hopper width,
      ;; hopper-to-wall, all chained on one line a foot off the deep
      ;; break on the shallow-end side - the string reads from the
      ;; shallow end, not from over the deep end it measures.  Break-
      ;; point dims keep the current style; the back and waypoint dims
      ;; get the style their typed format asks for, on the measured
      ;; stretch itself
      (setq u (cal:unit (cal:perp (cal:v- dp2 dp1))))
      (if (and u
               (< (cal:dot u (cal:v- (cal:mid sp1 sp2) (cal:mid dp1 dp2)))
                  0.0))
        (setq u (cal:v* u -1.0)))       ; u points to the shallow side
      (setq dimfail nil)
      (foreach q (append
                   (list (list dp1 e1 nil
                               (if u (cal:v+ (cal:mid dp1 e1)
                                             (cal:v* u *PF-DIM-OFF*))))
                         (list e1 e2 nil
                               (if u (cal:v+ (cal:mid e1 e2)
                                             (cal:v* u *PF-DIM-OFF*))))
                         (list e2 dp2 nil
                               (if u (cal:v+ (cal:mid e2 dp2)
                                             (cal:v* u *PF-DIM-OFF*))))
                         (list (nth kb base) (nth kb hpts)
                               (if bfl *PF-DIM-FTIN* *PF-DIM-IN*)
                               nil))
                   (mapcar '(lambda (pr) (list (car pr) (cadr pr)
                                               (if (caddr pr)
                                                 *PF-DIM-FTIN*
                                                 *PF-DIM-IN*)
                                               nil))
                           wdims))
        (setq e (pf:make-dim (car q) (cadr q) (caddr q) (cadddr q)))
        (if e
          (setq made (cons (pf:temp-add e) made))
          (setq dimfail T)))
      (if dimfail
        (princ (strcat "\n  (a dimension could not be created - the"
                       " offsets are " (rtos off1 2 2) ", "
                       (rtos off2 2 2) " and " (rtos off3 2 2) ")")))
      ;; the flow finished: promote it all from scaffolding to result
      (foreach e made (if e (pf:temp-drop e)))
      (princ (strcat "\nPool bottom added on layer " *PF-POOL-LAYER*
                     ": the shallow break, the three-piece deep break"
                     " (dashed stubs, solid middle), the curved hopper"
                     " (offsets " (rtos off1 2 2) " / "
                     (rtos off3 2 2) " / " (rtos off2 2 2)
                     "), the slope lines (" desc1 " / " desc2
                     "), and every dimension - the deep-end string a"
                     " foot off the break, on the shallow side."))))
  (princ))

;; Ask how one slope line should run.  NM names the deep break point
;; whose side is being asked about; DPTS are the survey points and
;; DEFO - a (value . ftin) pair - seeds the offset default.  Returns
;; nil for straight, T for guided, or a list of (surveyPt offset
;; ftin) waypoints for a guided line that passes through picked
;; points at pinned offsets.
(defun pf:ask-slope (nm dpts defo / ans wp spec o seed marks mk done)
  (initget "Straight Guided Points Back Undo")
  (setq ans (getkword (strcat
              "\n  Slope line from the offset at Pt." nm
              " [Straight/Guided/Points/Back] <Straight>: ")))
  (setq slopemarks nil)     ; the caller's register of this side's rings
  (cond
    ((member ans '("Back" "Undo")) 'PF-BACK)
    ((= ans "Guided") T)
    ((/= ans "Points") nil)
    (T
     (princ "\n  Pick survey points along this side, between the breaks; each")
     (princ "\n  gets its own offset, measured square off the wall.  The line")
     (princ "\n  follows the curve through them and eases to the shallow break.")
     (setq spec     nil
           marks    nil
           seed     defo
           done     nil
           pf-phase "picking slope waypoints")
     (while (not done)
       (initget "Back Undo")
       (setq wp (getpoint (strcat
                  "\n  Point on the Pt." nm
                  " side (Enter when done) [Back]: ")))
       (cond
         ((null wp) (setq done T))
         ((= (type wp) 'STR)             ; Back: un-pick the last waypoint
          (if spec
            (progn
              (pf:temp-kill (car marks))
              (setq marks (cdr marks)
                    spec  (cdr spec)
                    seed  (if spec
                            (cons (cadr (car spec)) (caddr (car spec)))
                            defo))
              (princ "\n  Stepping back one point."))
            (setq done 'PF-BACK)))       ; none yet: back to the choice
         (T
          (setq wp (pf:snap-break wp dpts))
          ;; the dashed ring is scaffolding: it confirms the pick and
          ;; clears itself when the command ends (or on a Back)
          (setq mk (pf:temp-add (pf:tag-mine (pf:draw-corner-marker wp))))
          (setq pf-phase "reading a slope waypoint offset")
          (setq o (pf:get-off (strcat "\n  What is the offset at Pt."
                                      (pf:pt-name wp) "?")
                              seed T T))
          (if (eq o 'PF-BACK)
            (progn                       ; un-pick this waypoint, re-ask
              (pf:temp-kill mk)
              (princ "\n  Stepping back one point."))
            (setq spec  (cons (list wp (car o) (cdr o)) spec)
                  marks (cons mk marks)
                  seed  o))
          (setq pf-phase "picking slope waypoints"))))
     (cond
       ((eq done 'PF-BACK)               ; re-ask Straight/Guided/Points
        (pf:ask-slope nm dpts defo))
       (spec
        (setq slopemarks marks)
        (reverse spec))
       (T
        (princ "\n  (no points picked - guiding along the curve instead)")
        T)))))

;; The interactive flow, run once a perimeter is in hand.  SEGS is
;; the closed loop, DPTS the survey points.  With ASK the user is
;; first offered the bottom (Enter or No skips it - the ABHD ending);
;; without, the flow starts straight away (the ADAB command, which
;; exists only for this).
(defun pf:bottom (segs dpts ask / ans s1 s2 d1 d2 sp1 sp2 dp1 dp2
                                   back off1 off2 off3 o1 o2 o3 bfl
                                   lines nm1 nm2 g1 g2 g1m g2m
                                   slopemarks stage go quit v e)
  ;; Staged so every prompt after the first offers Back - [Back] at
  ;; the point picks, B typed at the offsets - re-opening the previous
  ;; question and removing the scaffolding it drew.  Enter at a pick
  ;; still cancels the whole bottom, as before.  A break line whose
  ;; ends land wrong re-opens its own pick instead of aborting.
  (setq stage (if ask 0 1) go T quit nil)
  (while (and go (not quit))
    (cond
      ;; -- offer the bottom (the ABHD ending; ADAB starts at 1)
      ((= stage 0)
       (setq pf-phase "asking about the pool bottom")
       (cond
         ;; cover mode: a cover sheet records the perimeter and nothing
         ;; below it, so this is answered No without being asked --
         ;; ABHDCOVER sets the flag and c:ABHD clears it again
         (abhd:*nobottom*
          (princ "\n\n  Cover sheet - skipping the bottom of the pool.")
          (setq go nil))
         (t
          (initget "Yes No")
          (setq ans (getkword
                      "\n\n  Add the bottom of the pool (breaks and hopper)? [Yes/No] <No>: "))
          (if (= ans "Yes") (setq stage 1) (setq go nil)))))

      ;; -- the shallow break, one end per stage
      ((= stage 1)
       (princ "\n\n  SHALLOW BREAK - where the flat shallow floor starts sloping down.")
       (princ "\n  Pick its two ends (snap to the survey points).")
       (setq pf-phase "picking the shallow break")
       (if ask (initget "Back Undo") (initget ""))
       (setq v (getpoint (strcat "\n  First shallow break point"
                                 (if ask " [Back]" "") ": ")))
       (cond
         ((null v)
          (princ "\n  (point pick cancelled - the pool bottom was not added)")
          (setq quit T))
         ((= (type v) 'STR) (setq stage 0))
         (T (setq s1 v stage 2))))
      ((= stage 2)
       (initget "Back Undo")
       (setq v (getpoint s1 "\n  Second shallow break point [Back]: "))
       (cond
         ((null v)
          (princ "\n  (point pick cancelled - the pool bottom was not added)")
          (setq quit T))
         ((= (type v) 'STR) (setq stage 1))
         (T (setq s2 v stage 3))))

      ;; -- the deep break
      ((= stage 3)
       (princ "\n  DEEP BREAK - where the slope levels out into the hopper.")
       (setq pf-phase "picking the deep break")
       (initget "Back Undo")
       (setq v (getpoint "\n  First deep break point [Back]: "))
       (cond
         ((null v)
          (princ "\n  (point pick cancelled - the pool bottom was not added)")
          (setq quit T))
         ((= (type v) 'STR) (setq stage 2))
         (T (setq d1 v stage 4))))
      ((= stage 4)
       (initget "Back Undo")
       (setq v (getpoint d1 "\n  Second deep break point [Back]: "))
       (cond
         ((null v)
          (princ "\n  (point pick cancelled - the pool bottom was not added)")
          (setq quit T))
         ((= (type v) 'STR) (setq stage 3))
         (T
          (setq d2 v)
          ;; break ends snap to survey points, like declared walls do
          (setq s1 (pf:snap-break s1 dpts) s2 (pf:snap-break s2 dpts)
                d1 (pf:snap-break d1 dpts) d2 (pf:snap-break d2 dpts))
          (cond
            ((< (cal:dist s1 s2) *PF-EXACT-EPS*)
             (princ "\n  (both ends of the shallow break landed on the same survey point - pick it again)")
             (setq stage 1))
            ((< (cal:dist d1 d2) *PF-EXACT-EPS*)
             (princ "\n  (both ends of the deep break landed on the same survey point - pick it again)")
             (setq stage 3))
            (T
             ;; the break ends land exactly on the kept perimeter
             (setq sp1  (pf:curve-near s1 segs)
                   sp2  (pf:curve-near s2 segs)
                   dp1  (pf:curve-near d1 segs)
                   dp2  (pf:curve-near d2 segs)
                   back (pf:hopper-back dp1 dp2 sp1 sp2 dpts))
             (cond
               ((null back)
                (princ (strcat "\n  (no survey point lies beyond the"
                               " deep break - are the two break lines"
                               " swapped?  Pick the deep break again)"))
                (setq stage 3))
               (T
                ;; both break lines go down now, solid, so what was
                ;; declared is visible while the offsets are typed;
                ;; they stay scaffolding until the whole flow lands.
                ;; A re-commit (after a Back) sweeps the old pair first.
                (foreach e lines (pf:temp-kill e))
                (cal:ensure-layer *PF-POOL-LAYER* 4)
                (setq lines (list (pf:temp-add (pf:tag-mine
                                    (pf:make-line sp1 sp2 nil nil)))
                                  (pf:temp-add (pf:tag-mine
                                    (pf:make-line dp1 dp2 nil nil)))))
                (princ (strcat "\n  Back of the hopper: Pt."
                               (pf:pt-name back)
                               " (the survey point straight out from"
                               " the deep break)."))
                (setq nm1 (pf:pt-name d1)
                      nm2 (pf:pt-name d2))
                (princ "\n  Three offsets pull the hopper in from the perimeter;")
                (princ "\n  they blend gradually where they differ.  Type inches (42)")
                (princ "\n  or feet and inches (3'6).")
                (setq stage 5))))))))

      ;; -- the three hopper offsets
      ((= stage 5)
       (setq pf-phase "reading the hopper offsets")
       (setq o1 (pf:get-off (strcat "\n  What is the deep end offset at Pt."
                                    nm1 "?")
                            (cons *PF-HOP-OFF* nil) nil T))
       (if (eq o1 'PF-BACK)
         (setq stage 4)
         (setq off1 (car o1) stage 6)))
      ((= stage 6)
       (setq o2 (pf:get-off (strcat "\n  What is the deep end offset at Pt."
                                    nm2 "?")
                            o1 nil T))
       (if (eq o2 'PF-BACK)
         (setq stage 5)
         (setq off2 (car o2) stage 7)))
      ((= stage 7)
       (setq o3 (pf:get-off (strcat "\n  What is the offset at the back of the"
                                    " hopper (Pt." (pf:pt-name back) ")?")
                            o1 nil T))
       (if (eq o3 'PF-BACK)
         (setq stage 6)
         (progn
           (setq off3 (car o3)
                 bfl  (cdr o3))
           (setq *PF-HOP-OFF* off1)
           ;; each slope line can run straight to the shallow break,
           ;; follow the perimeter's curve gently in, or pass through
           ;; picked points at pinned offsets
           (setq pf-phase "asking about the slope lines")
           (princ "\n  Each slope line can run STRAIGHT to the shallow break, be GUIDED")
           (princ "\n  by the perimeter - easing in along its curve - or pass through")
           (princ "\n  POINTS you pick along that side, each with its own offset.")
           (setq stage 8))))

      ;; -- one slope choice per side; Back at a choice re-opens the
      ;; -- previous question, sweeping that side's waypoint rings
      ((= stage 8)
       (foreach e g1m (pf:temp-kill e))
       (setq g1m nil
             v   (pf:ask-slope nm1 dpts o1))
       (if (eq v 'PF-BACK)
         (setq stage 7)
         (setq g1 v g1m slopemarks stage 9)))
      ((= stage 9)
       (foreach e g2m (pf:temp-kill e))
       (setq g2m nil
             v   (pf:ask-slope nm2 dpts o2))
       (if (eq v 'PF-BACK)
         (setq stage 8)
         (setq g2 v g2m slopemarks stage 10)))

      ;; -- everything is in hand: draw the bottom
      (T
       (pf:bottom-draw segs sp1 sp2 dp1 dp2 back
                       off1 off2 off3 bfl lines
                       (list g1 g2))
       (setq go nil))))
  (princ))

;; ---- the numeric parameters ------------------------------------------
;; Asked identically at the start of a run and again on a Redo -
;; Enter keeps the shown value each time.

;; Maximum distance from a point; remembered in *PF-TOL*.
(defun pf:ask-tol (/ tol)
  (initget 6)
  (setq tol (getdist (strcat "\n  Maximum distance from a point <"
                             (rtos *PF-TOL* 2 3) ">: ")))
  (if (null tol) (setq tol *PF-TOL*))
  (if (> tol *PF-TOL-MAX*)
    (progn
      (princ (strcat "\n  (more than " (rtos *PF-TOL-MAX* 2 1)
                     " and the line is no longer a trace of the points"
                     " - using " (rtos *PF-TOL-MAX* 2 1) ")"))
      (setq tol *PF-TOL-MAX*)))
  (setq *PF-TOL* tol)
  tol)

;; Share of the points allowed off the line, returned as a fraction;
;; DEF is the fraction Enter keeps.
(defun pf:ask-pct (def / pct)
  (initget 4)
  (setq pct (getint (strcat "\n  Percent of points allowed off <"
                            (itoa (fix (+ 0.5 (* 100.0 def))))
                            ">: ")))
  (cond
    ((null pct) def)
    ((> pct 100)
     (princ "\n  (more than 100 makes no sense - using 100)")
     1.0)
    (T (/ pct 100.0))))

;; Curve cap; remembered in *PF-MAX-ARCS* (nil = no cap).
(defun pf:ask-cap (/ mx)
  (initget 4 "None")
  (setq mx (getint (strcat "\n  Maximum curves <"
                           (if *PF-MAX-ARCS* (itoa *PF-MAX-ARCS*) "None")
                           ">: ")))
  (cond ((null mx) nil)                            ; Enter: keep as-is
        ((eq 'STR (type mx)) (setq *PF-MAX-ARCS* nil))
        (T (setq *PF-MAX-ARCS* mx)))
  *PF-MAX-ARCS*)

;; ---- redo-time editing of walls and corners --------------------------
;; A Redo may change more than the numbers: straight walls and sharp
;; corners can be added or removed before the refit.  Both editors
;; work on the run-scoped pf-walls / pf-corners lists and keep the
;; dashed markers in step with them.

;; Erase this run's scaffolding markers of one entity type on the
;; marker layer (walls are the LINEs, rings the CIRCLEs), so the set
;; can be redrawn to match an edited declaration list.
(defun pf:sweep-marks (etype / keep en ed)
  (setq keep nil)
  (foreach en pf-temp
    (setq ed (if (and en (entget en)) (entget en)))
    (if (and ed
             (= etype (cdr (assoc 0 ed)))
             (= (strcase *PF-WALL-LAYER*)
                (strcase (cdr (assoc 8 ed)))))
      (entdel en)
      (setq keep (cons en keep))))
  (setq pf-temp (reverse keep)))

;; Add or remove declared straight walls.  Ends snap to the survey
;; points; each change is confirmed by name and the dashed markers
;; follow.
(defun pf:edit-walls (dpts / ans wp1 wp2 w1 w2 best bd w d)
  (setq ans T)
  (while ans
    (initget "Add Remove Keep")
    (setq ans (getkword (strcat
                "\n  Straight walls (" (itoa (length pf-walls))
                " declared) - [Add/Remove/Keep] <Keep>: ")))
    (cond
      ((= ans "Add")
       (setq pf-phase "picking a straight wall"
             wp1      (getpoint "\n  First end of the straight wall: ")
             wp2      (if wp1 (getpoint wp1 "\n  Second end: ")))
       (if wp2
         (progn
           (setq w1 (pf:snap-break wp1 dpts)
                 w2 (pf:snap-break wp2 dpts))
           (if (< (cal:dist w1 w2) *PF-EXACT-EPS*)
             (princ "\n  (both ends landed on the same survey point - ignored)")
             (progn
               (setq pf-walls (append pf-walls (list (list w1 w2))))
               (pf:temp-add (pf:tag-mine (pf:draw-wall-marker w1 w2)))
               (princ (strcat "\n  wall Pt." (pf:pt-name w1)
                              " - Pt." (pf:pt-name w2) " added")))))))
      ((= ans "Remove")
       (if (null pf-walls)
         (princ "\n  (no straight walls to remove)")
         (progn
           (setq pf-phase "removing a straight wall"
                 wp1      (getpoint "\n  Pick near the straight wall to remove: "))
           (if wp1
             (progn
               (setq wp1 (cal:2d wp1) best nil bd nil)
               (foreach w pf-walls
                 (setq d (pf:seg-dist wp1 (list (car w) (cadr w) 0.0)))
                 (if (or (null bd) (< d bd)) (setq best w bd d)))
               (setq pf-walls (pf:remove best pf-walls))
               ;; redraw the wall markers to match what is left
               (pf:sweep-marks "LINE")
               (foreach w pf-walls
                 (pf:temp-add (pf:tag-mine
                   (pf:draw-wall-marker (car w) (cadr w)))))
               (princ (strcat "\n  wall Pt." (pf:pt-name (car best))
                              " - Pt." (pf:pt-name (cadr best))
                              " removed")))))))
      (T (setq ans nil)))))

;; Add or remove declared sharp corners the same way.  (The corners
;; the fitter finds by itself - turns over *PF-CORNER-ANG* - are not
;; declarations and cannot be removed here.)
(defun pf:edit-corners (dpts / ans wp1 w1 best bd w)
  (setq ans T)
  (while ans
    (initget "Add Remove Keep")
    (setq ans (getkword (strcat
                "\n  Sharp corners (" (itoa (length pf-corners))
                " declared) - [Add/Remove/Keep] <Keep>: ")))
    (cond
      ((= ans "Add")
       (setq pf-phase "picking a sharp corner"
             wp1      (getpoint "\n  Corner point: "))
       (if wp1
         (progn
           (setq w1 (pf:snap-break wp1 dpts))
           (if (pf:memb w1 pf-corners)
             (princ "\n  (that corner is already declared)")
             (progn
               (setq pf-corners (append pf-corners (list w1)))
               (pf:temp-add (pf:tag-mine (pf:draw-corner-marker w1)))
               (princ (strcat "\n  corner Pt." (pf:pt-name w1)
                              " added")))))))
      ((= ans "Remove")
       (if (null pf-corners)
         (princ "\n  (no declared corners to remove)")
         (progn
           (setq pf-phase "removing a sharp corner"
                 wp1      (getpoint "\n  Pick the declared corner to remove: "))
           (if wp1
             (progn
               (setq wp1 (cal:2d wp1) best nil bd nil)
               (foreach w pf-corners
                 (if (or (null bd) (< (cal:dist wp1 w) bd))
                   (setq best w bd (cal:dist wp1 w))))
               (setq pf-corners (pf:remove best pf-corners))
               ;; the rings share their look with the omit markers;
               ;; redraw the corner and hold rings (spent omit rings
               ;; go quietly - the omissions already happened)
               (pf:sweep-marks "CIRCLE")
               (foreach w pf-corners
                 (pf:temp-add (pf:tag-mine (pf:draw-corner-marker w))))
               (foreach w pf-holds
                 (pf:temp-add (pf:tag-mine (pf:draw-hold-marker w))))
               (princ (strcat "\n  corner Pt." (pf:pt-name best)
                              " removed")))))))
      (T (setq ans nil)))))

;; Add or remove HELD points the same way.
(defun pf:edit-holds (dpts / ans wp1 w1 best bd w)
  (setq ans T)
  (while ans
    (initget "Add Remove Keep")
    (setq ans (getkword (strcat
                "\n  Held points (" (itoa (length pf-holds))
                " declared) - [Add/Remove/Keep] <Keep>: ")))
    (cond
      ((= ans "Add")
       (setq pf-phase "picking a held point"
             wp1      (getpoint "\n  Point to hold exactly: "))
       (if wp1
         (progn
           (setq w1 (pf:snap-break wp1 dpts))
           (if (pf:memb w1 pf-holds)
             (princ "\n  (that point is already held)")
             (progn
               (setq pf-holds (append pf-holds (list w1)))
               (pf:temp-add (pf:tag-mine (pf:draw-hold-marker w1)))
               (princ (strcat "\n  held Pt." (pf:pt-name w1)
                              " added")))))))
      ((= ans "Remove")
       (if (null pf-holds)
         (princ "\n  (no held points to remove)")
         (progn
           (setq pf-phase "removing a held point"
                 wp1      (getpoint "\n  Pick the held point to release: "))
           (if wp1
             (progn
               (setq wp1 (cal:2d wp1) best nil bd nil)
               (foreach w pf-holds
                 (if (or (null bd) (< (cal:dist wp1 w) bd))
                   (setq best w bd (cal:dist wp1 w))))
               (setq pf-holds (pf:remove best pf-holds))
               ;; redraw the rings to match what is left
               (pf:sweep-marks "CIRCLE")
               (foreach w pf-corners
                 (pf:temp-add (pf:tag-mine (pf:draw-corner-marker w))))
               (foreach w pf-holds
                 (pf:temp-add (pf:tag-mine (pf:draw-hold-marker w))))
               (princ (strcat "\n  held Pt." (pf:pt-name best)
                              " released")))))))
      (T (setq ans nil)))))

;; ---- the command -----------------------------------------------------
(defun c:ABHD ( / tol ans go wp1 wp2 rawwalls rawcnrs rawholds w w1 w2
                    ss i en ed lay typ ext nunsup nocs
                    segs pts dpts allow loop tour ok stale npt
                    again omits pts2 ent ring pf-omitted
                    pf-miss-pct pf-walls pf-corners pf-holds
                    pf-temp pf-ptnames
                    pf-dim-warned *error* pf-old-err pf-phase)
  ;; report which step failed if anything goes wrong, sweep away any
  ;; preview geometry drawn so far, then restore the old handler - a
  ;; cancelled run must not leave dashed markers or candidate outlines
  ;; lying around
  (setq pf-temp   nil
        pf-old-err *error*
        *error*
          (lambda (m)
            (if (and m (not (wcmatch (strcase m)
                     "*BREAK*,*CANCEL*,*QUIT*,*EXIT*")))
              (princ (strcat "\nABHD stopped while "
                             (if pf-phase pf-phase "starting up")
                             " -- " m)))
            (pf:temp-clear)
            (setq *error* pf-old-err)
            ;; cover mode must not outlive the run that asked for it,
            ;; or the next ABHD would skip its bottom without a word
            (setq abhd:*nobottom* nil)
            (princ)))

  ;; sweep leftovers from a run that was interrupted before it could
  ;; tidy up after itself
  (setq stale (pf:purge-mine *PF-WALL-LAYER*))
  (if (> stale 0)
    (princ (strcat "\nABHD: cleared " (itoa stale)
                   " leftover marker(s) from layer " *PF-WALL-LAYER*
                   ".")))

  (princ "\n\nABHD - fit a pool perimeter through the surveyed points.")

  ;; -- step 1: how close must the line stay to the points? ----------
  ;; This is the one prompt people misread, so it says in plain words
  ;; what the number means and which way it moves the result.
  ;; initget 6 refuses zero and negative values - a zero tolerance
  ;; would silently collapse the fit into single-point stubs.
  (setq pf-phase "reading the tolerance")
  (princ "\n\n  Step 1 of 7 - how far may the fitted line sit from a survey point?")
  (princ "\n  Type a distance in drawing units (1 = one inch, 2 at most), or")
  (princ "\n  pick two points in the drawing to measure one.")
  (princ "\n  Smaller = hugs the points.  Bigger = smoother, with fewer curves.")
  (setq tol (pf:ask-tol))

  ;; -- step 2: how many of the points may sit off the line? ---------
  ;; Enter means the standard share; the answer is per run, on purpose.
  (setq pf-phase "reading the miss percentage")
  (princ "\n\n  Step 2 of 7 - what percent of the points may sit OFF the line")
  (princ "\n  (off, but still within the distance above)?")
  (princ (strcat "\n  Press Enter for the standard "
                 (itoa (fix (+ 0.5 (* 100.0 *PF-MISS-PCT*))))
                 " percent."))
  (setq pf-miss-pct (pf:ask-pct *PF-MISS-PCT*))

  ;; -- step 3: optional cap on how many curves the result may use ---
  (setq pf-phase "reading the curve limit")
  (princ "\n\n  Step 3 of 7 - limit how many curves the result may use?")
  (princ "\n  Type a whole number, or None for no limit.")
  (pf:ask-cap)

  ;; -- step 4: any dead-straight walls to declare? ------------------
  ;; Each declared wall is marked with a dashed line right away and
  ;; comes out of the fit as a straight LINE between those two survey
  ;; points, no matter what the arcs around it are doing.
  (setq pf-phase "asking about straight lines")
  (princ "\n\n  Step 4 of 7 - does the pool edge have any dead-straight walls?")
  (princ "\n  If Yes you will pick the two end points of each (snap to the")
  (princ "\n  survey points); a dashed line marks each declared wall.")
  (initget "Yes No")
  (setq ans      (getkword "\n  Any straight lines? [Yes/No] <No>: ")
        rawwalls nil)
  (if (= ans "Yes")
    (progn
      (setq go T)
      (while go
        (setq pf-phase "picking a straight wall"
              wp1      (getpoint "\n  First end of the straight wall: "))
        (if wp1
          (progn
            (setq wp2 (getpoint wp1 "\n  Second end: "))
            (if wp2
              (progn
                (setq wp1 (cal:2d wp1) wp2 (cal:2d wp2))
                ;; the dashed marker is scaffolding: it confirms what
                ;; you declared, and goes when the command ends
                (pf:temp-add (pf:tag-mine (pf:draw-wall-marker wp1 wp2)))
                (setq rawwalls (cons (list wp1 wp2) rawwalls))
                (initget "Yes No")
                (if (/= (getkword "\n  Another straight line? [Yes/No] <No>: ")
                        "Yes")
                  (setq go nil)))
              (setq go nil)))
          (setq go nil)))
      (setq rawwalls (reverse rawwalls))
      (if rawwalls
        (princ (strcat "\n  " (itoa (length rawwalls))
                       " straight wall(s) noted - the dashed markers on "
                       *PF-WALL-LAYER*
                       " clear themselves when the command finishes.")))))

  ;; -- step 5: any sharp corners to declare? ------------------------
  ;; The fitter finds obvious corners itself (turns over
  ;; *PF-CORNER-ANG*), but a gentler one still reads as a corner on
  ;; site.  A declared point is exempt from the tangency rule: the fit
  ;; breaks there instead of rounding it off.
  (setq pf-phase "asking about sharp corners")
  (princ "\n\n  Step 5 of 7 - are there any sharp corners the fit must not round off?")
  (princ "\n  Obvious ones are found automatically; declare the gentler ones here.")
  (princ "\n  If Yes you will pick each corner point (snap to the survey points).")
  (initget "Yes No")
  (setq ans     (getkword "\n  Any sharp corners? [Yes/No] <No>: ")
        rawcnrs nil)
  (if (= ans "Yes")
    (progn
      (setq go T)
      (while go
        (setq pf-phase "picking a sharp corner"
              wp1      (getpoint "\n  Corner point (Enter when done): "))
        (if wp1
          (progn
            (setq wp1     (cal:2d wp1)
                  rawcnrs (cons wp1 rawcnrs))
            (pf:temp-add (pf:tag-mine (pf:draw-corner-marker wp1))))
          (setq go nil)))
      (setq rawcnrs (reverse rawcnrs))
      (if rawcnrs
        (princ (strcat "\n  " (itoa (length rawcnrs))
                       " corner(s) noted - the markers clear themselves"
                       " when the command finishes.")))))

  ;; -- step 6: any points that must be held absolutely? -------------
  ;; Control shots and tie-ins are surveyed as exact positions: a held
  ;; point always ends a span, so the fit passes through it exactly
  ;; and the miss allowance can never write it off.
  (setq pf-phase "asking about held points")
  (princ "\n\n  Step 6 of 7 - any points that must be held ABSOLUTELY?")
  (princ "\n  A held point can never be fudged: the line passes through it")
  (princ "\n  exactly, in every candidate.  If Yes you will pick each one")
  (princ "\n  (snap to the survey points); a small dashed ring marks it.")
  (initget "Yes No")
  (setq ans      (getkword "\n  Any held points? [Yes/No] <No>: ")
        rawholds nil)
  (if (= ans "Yes")
    (progn
      (setq go T)
      (while go
        (setq pf-phase "picking a held point"
              wp1      (getpoint "\n  Point to hold exactly (Enter when done): "))
        (if wp1
          (progn
            (setq wp1      (cal:2d wp1)
                  rawholds (cons wp1 rawholds))
            (pf:temp-add (pf:tag-mine (pf:draw-hold-marker wp1))))
          (setq go nil)))
      (setq rawholds (reverse rawholds))
      (if rawholds
        (princ (strcat "\n  " (itoa (length rawholds))
                       " held point(s) noted - the markers clear"
                       " themselves when the command finishes.")))))

  ;; -- step 7: the selection ----------------------------------------
  (princ "\n\n  Step 7 of 7 - select the survey points (POINTS layer or ab_pt")
  (princ "\n  blocks) and, if you have one, the POOL perimeter or ordering sketch.")
  (princ "\n  Select objects: ")
  (setq pf-phase "waiting for the selection")
  ;; only entity types this command can actually read, so a sloppy
  ;; crossing window over dimensions, hatches or text is harmless.
  ;; SPLINE and ELLIPSE are let in ON PURPOSE - not to fit them, but
  ;; so the classifier below can name them in a useful message.
  (setq ss (ssget '((0 . "POINT,INSERT,LINE,ARC,CIRCLE,LWPOLYLINE,POLYLINE,SPLINE,ELLIPSE"))))
  (if (null ss)
    (princ "\nNothing usable selected (points, and optionally POOL lines/arcs/polylines).")
    (progn
      ;; -- sort the selection into perimeter segments and points -----
      (setq pf-phase "reading the selected entities")
      (setq segs nil pts nil i 0 nunsup 0 nocs 0
            npt 0 pf-ptnames nil)
      (while (< i (sslength ss))
        (setq en  (ssname ss i)
              ed  (entget en)
              lay (strcase (cdr (assoc 8 ed)))
              typ (cdr (assoc 0 ed))
              ext (cdr (assoc 210 ed))
              i   (1+ i))
        ;; geometry drawn in a tilted UCS reads back in its own plane,
        ;; so a flat 2D fit of it would be wrong - count and warn
        (if (and ext (< (abs (caddr ext)) 0.999)) (setq nocs (1+ nocs)))
        (cond
          ;; survey points stored as block references (e.g. "ab_pt"):
          ;; a block with this name is ALWAYS a point, on any layer, and
          ;; its insertion point is taken as the location (the blocks are
          ;; never exploded - non-destructive).  Checked first so such
          ;; blocks are never mistaken for perimeter geometry.
          ((and (= typ "INSERT")
                (= (strcase (cdr (assoc 2 ed))) (strcase *PF-POINT-BLOCK*)))
           (pf:add-point (cal:2d (cdr (assoc 10 ed)))
                         (pf:block-number en)))
          ;; curve types we cannot fit, sitting on the POOL layer: count
          ;; them so the user gets told what to do, instead of a
          ;; mystifying "the perimeter does not close" later on
          ((and (= lay (strcase *PF-POOL-LAYER*))
                (member typ '("SPLINE" "ELLIPSE")))
           (setq nunsup (1+ nunsup)))
          ;; ABHD's own pool-bottom geometry lives on the POOL layer
          ;; too (stamped) - never read it back as a guide
          ((and (= lay (strcase *PF-POOL-LAYER*))
                (assoc -3 (entget en '("ABHD"))))
           nil)
          ;; perimeter / ordering sketch on the POOL layer
          ((= lay (strcase *PF-POOL-LAYER*))
           (setq segs (append segs (pf:ent-segs en))))
          ;; plain POINT entities on the POINTS layer
          ((and (= lay (strcase *PF-POINT-LAYER*)) (= typ "POINT"))
           (pf:add-point (cal:2d (cdr (assoc 10 ed))) nil))
          ;; any other block dropped on the POINTS layer -> a point too
          ((and (= typ "INSERT") (= lay (strcase *PF-POINT-LAYER*)))
           (pf:add-point (cal:2d (cdr (assoc 10 ed)))
                         (pf:block-number en)))))
      (if (> nunsup 0)
        (princ (strcat "\nABHD: warning - " (itoa nunsup)
                       " SPLINE/ELLIPSE object(s) on layer "
                       *PF-POOL-LAYER*
                       " were ignored (only lines, arcs, circles and"
                       " polylines can be read - explode or convert"
                       " them first).")))
      (if (> nocs 0)
        (princ (strcat "\nABHD: warning - " (itoa nocs)
                       " selected object(s) are not drawn in the world"
                       " plane; the fit is flat (XY) and may be wrong."
                       "  Set UCS to World and flatten them first.")))
      ;; the miss allowance: this share of the points (the answer to
      ;; step 2, rounded UP to a whole point) may sit off the result
      ;; by up to TOL
      (setq dpts  (if pts (cal:dedupe pts *PF-EXACT-EPS*))
            allow (cal:ceil (* (pf:misspct) (length dpts))))
      ;; snap the declared straight-wall ends onto actual survey
      ;; points - arc and wall endpoints always sit ON points
      (setq pf-walls nil)
      (foreach w rawwalls
        (setq w1 (pf:nearest (car w) dpts)
              w2 (pf:nearest (cadr w) dpts))
        (cond
          ((or (null w1) (null w2)) nil)
          ((< (cal:dist w1 w2) *PF-EXACT-EPS*)
           (princ "\n  (both ends of a declared wall landed on the same survey point - that wall is ignored)"))
          (T
           (if (or (> (cal:dist (car w) w1) (* 3.0 tol))
                   (> (cal:dist (cadr w) w2) (* 3.0 tol)))
             (princ "\n  (a declared wall end was picked well away from any survey point - snapped to the nearest one)"))
           (setq pf-walls (cons (list w1 w2) pf-walls)))))
      (setq pf-walls (reverse pf-walls))
      ;; declared corners snap onto survey points the same way
      (setq pf-corners nil)
      (foreach w rawcnrs
        (setq w1 (pf:nearest w dpts))
        (if w1
          (progn
            (if (> (cal:dist w w1) (* 3.0 tol))
              (princ "\n  (a declared corner was picked well away from any survey point - snapped to the nearest one)"))
            (setq pf-corners (cons w1 pf-corners)))))
      (setq pf-corners (reverse pf-corners))
      ;; held points snap onto survey points the same way; duplicates
      ;; collapse to one
      (setq pf-holds nil)
      (foreach w rawholds
        (setq w1 (pf:nearest w dpts))
        (if w1
          (progn
            (if (> (cal:dist w w1) (* 3.0 tol))
              (princ "\n  (a held point was picked well away from any survey point - snapped to the nearest one)"))
            (if (not (pf:memb w1 pf-holds))
              (setq pf-holds (cons w1 pf-holds))))))
      (setq pf-holds (reverse pf-holds))
      (if (> (length dpts) 150)
        (princ (strcat "\nABHD: " (itoa (length dpts))
                       " points - ordering and fitting will take a"
                       " little while, please wait...")))
      (cond
        ((null pts)
         (princ (strcat "\nNo survey points found (looked for POINT entities on layer "
                        *PF-POINT-LAYER* " and \"" *PF-POINT-BLOCK*
                        "\" block insertions).")))
        ((and (null segs) (< (length dpts) 3))
         (princ "\nPoints-only mode needs at least 3 distinct points."))
        (T
         ;; work out the mode, then hand all three modes to the same
         ;; compare-and-choose step
         (setq tour nil loop nil ok T)
         (cond
           ((null segs)
            ;; ---- POINTS-ONLY: order the points ourselves ----------
            (princ "\nNo POOL geometry selected - ordering the points automatically.")
            (setq pf-phase "ordering the points"
                  tour     (pf:order-points dpts)))
           ((null (setq loop (pf:chain segs)))
            (setq ok nil))                     ; pf:chain said why
           ((not (pf:has-arcs loop))
            ;; ---- ORDERING SKETCH: the drawn loop is all straight
            ;; lines, so it only tells us the ORDER of the points;
            ;; the shape itself comes from the points
            (if (< (length dpts) 3)
              (progn
                (princ (strcat "\nThe lines-only POOL sketch only orders"
                               " the points, and at least 3 distinct"
                               " points are needed to build a shape."))
                (setq ok nil))
              (progn
                (princ "\nPOOL sketch is lines only - using it just to order the points.")
                (setq pf-phase "following the sketch order"
                      tour     (pf:loop-order loop dpts)))))
           (T
            (princ "\nUsing the drawn POOL perimeter as the guide.")
            (if pf-walls
              (princ (strcat "\n  (declared straight walls only steer"
                             " the points-built fit; here your drawn"
                             " straight segments are already kept)")))
            (if pf-holds
              (princ (strcat "\n  (held points only bind the"
                             " points-built fit; the drawn shape wins"
                             " here - the report flags any held point"
                             " the kept fit missed)")))))
         (if ok
           (progn
             (setq again T)
             (while again
               (setq again nil)
               (if (eq 'REDO (pf:compare tour loop pts dpts tol allow))
                 (progn
                   ;; -- redo: maybe omit points, then re-ask the
                   ;; numbers and draw a fresh trio -----------------
                   (setq pf-phase "picking points to omit"
                         omits    nil)
                   (princ "\n\nRedoing the fit.  Any points to leave out this time?")
                   (princ "\n  Pick each one (Enter for none) - mis-shots, duplicates, or")
                   (princ "\n  anything the line should not chase; each gets a dashed ring.")
                   (if pf-omitted
                     (princ (strcat "\n  " (itoa (length pf-omitted))
                                    " point(s) are already out -"
                                    " picking one of those puts it"
                                    " BACK IN.")))
                   (while (setq wp1 (getpoint
                                      "\n  Point to omit - or a ringed one to restore (Enter when done): "))
                     (setq wp1 (cal:2d wp1)
                           w1  (pf:nearest wp1 dpts)
                           w2  (pf:nearest wp1 (mapcar 'car pf-omitted)))
                     (cond
                       ;; nearer to an already-omitted point: this
                       ;; click un-omits it - the saved entries (its
                       ;; duplicates too) rejoin the fit, its ring goes
                       ((and w2 (or (null w1)
                                    (<= (cal:dist wp1 w2)
                                        (cal:dist wp1 w1))))
                        (setq ent        (assoc w2 pf-omitted)
                              pts        (append pts (cadr ent))
                              dpts       (cal:dedupe pts *PF-EXACT-EPS*)
                              pf-omitted (pf:remove ent pf-omitted)
                              omits      (pf:remove w2 omits))
                        (if (and (caddr ent) (entget (caddr ent)))
                          (progn
                            (pf:temp-drop (caddr ent))
                            (entdel (caddr ent))))
                        (princ (strcat "  - Pt." (pf:pt-name w2)
                                       " back in")))
                       ;; otherwise omit: pull it - and its duplicates
                       ;; - out of the fit, the stats and the miss
                       ;; allowance alike, and remember how to undo it
                       (w1
                        (setq pts2 nil ent nil)
                        (foreach w pts
                          (if (< (cal:dist w w1) *PF-EXACT-EPS*)
                            (setq ent (cons w ent))
                            (setq pts2 (cons w pts2))))
                        (setq pts  (reverse pts2)
                              dpts (cal:dedupe pts *PF-EXACT-EPS*)
                              ring (pf:temp-add (pf:tag-mine
                                     (pf:draw-corner-marker w1)))
                              pf-omitted (cons (list w1 ent ring)
                                               pf-omitted)
                              omits      (cons w1 omits))
                        (princ (strcat "  - omitting Pt."
                                       (pf:pt-name w1))))))
                   (if omits
                     (progn
                       ;; declared walls and corners anchored on a
                       ;; point omitted this round make no sense any
                       ;; more (a restored point keeps nothing - the
                       ;; wall went when it went out)
                       (setq pts2 nil)
                       (foreach w pf-walls
                         (if (not (or (pf:memb (car w) omits)
                                      (pf:memb (cadr w) omits)))
                           (setq pts2 (cons w pts2))))
                       (if (< (length pts2) (length pf-walls))
                         (princ "\n  (a declared wall lost an end and was dropped)"))
                       (setq pf-walls (reverse pts2)
                             pts2     nil)
                       (foreach w pf-corners
                         (if (not (pf:memb w omits))
                           (setq pts2 (cons w pts2))))
                       (setq pf-corners (reverse pts2)
                             pts2       nil)
                       ;; a held point that was just omitted is out of
                       ;; the fit entirely - nothing left to hold
                       (foreach w pf-holds
                         (if (not (pf:memb w omits))
                           (setq pts2 (cons w pts2))))
                       (if (< (length pts2) (length pf-holds))
                         (princ "\n  (an omitted point was held - its hold went with it)"))
                       (setq pf-holds (reverse pts2))))
                   (if pf-omitted
                     (princ (strcat "\n  " (itoa (length pf-omitted))
                                    " point(s) omitted in total - "
                                    (itoa (length dpts))
                                    " in the fit.")))
                   (if (< (length dpts) 3)
                     (princ "\nToo few points remain for a fit - nothing redone.")
                     (progn
                       ;; walls and corners may change for the retry
                       (princ "\n\n  Straight walls and sharp corners can change too -")
                       (princ "\n  Enter keeps each list as it is.")
                       (setq pf-phase "editing straight walls")
                       (pf:edit-walls dpts)
                       (setq pf-phase "editing sharp corners")
                       (pf:edit-corners dpts)
                       (setq pf-phase "editing held points")
                       (pf:edit-holds dpts)
                       (princ "\n\n  New settings - Enter keeps each one as it is.")
                       (setq pf-phase "reading the tolerance"
                             tol      (pf:ask-tol))
                       (setq pf-phase "reading the miss percentage"
                             pf-miss-pct (pf:ask-pct pf-miss-pct))
                       (setq pf-phase "reading the curve limit")
                       (pf:ask-cap)
                       (setq allow (cal:ceil (* (pf:misspct)
                                               (length dpts))))
                       ;; the point order must forget the omitted ones
                       (cond
                         ((null loop)
                          (setq pf-phase "ordering the points"
                                tour     (pf:order-points dpts)))
                         ((not (pf:has-arcs loop))
                          (setq tour (pf:loop-order loop dpts))))
                       (setq again T))))))))))))
  ;; sweep the dashed wall markers and any candidate the user did not
  ;; keep - the command tidies up after itself
  (pf:temp-clear)
  (setq *error* pf-old-err)   ; restore the previous error handler
  (setq abhd:*nobottom* nil)  ; cover mode lasts one run only
  (princ))

;; ABHD for a cover sheet: the same fit, with the pool-bottom question
;; answered No before it is asked.  A cover records the perimeter and
;; nothing below it, so the breaks, the hopper offsets and the slope
;; lines are work the sheet has no room for.
;;
;; A command of its own rather than a mode, so that a button runs
;; exactly the command named on it; the flag is cleared by c:ABHD on
;; both its exits, so it cannot leak into the next run.
(defun c:ABHDCOVER ()
  (setq abhd:*nobottom* t)
  (princ "\nABHDCOVER: cover sheet - the pool bottom will be skipped.")
  (c:ABHD)
  (princ))

;; ---- ADAB: the pool bottom on its own --------------------------------
;; The end of the ABHD flow as a command of its own: select an
;; existing perimeter - one closed polyline, or the exploded
;; lines/arcs that form one - and go straight to the breaks, the
;; hopper offsets and the slope lines.  The survey points do not have
;; to be selected: with none in the selection, every ab_pt block and
;; POINTS-layer point in the drawing is gathered and only those
;; sitting ON the loop (within *PF-PICKUP-EPS*) are used, so stray
;; depth shots and deck points stay out of it.  Points that ARE
;; selected are trimmed by the same rule.  For when the perimeter was
;; fitted (or drawn) some other day and only the floor is needed.
(defun c:ADAB ( / ss i en ed typ ext lay segs pts dpts loop nocs nskip
                    nall npt stale pf-temp pf-ptnames pf-dim-warned
                    *error* pf-old-err pf-phase)
  (setq pf-temp   nil
        pf-old-err *error*
        *error*
          (lambda (m)
            (if (and m (not (wcmatch (strcase m)
                     "*BREAK*,*CANCEL*,*QUIT*,*EXIT*")))
              (princ (strcat "\nADAB stopped while "
                             (if pf-phase pf-phase "starting up")
                             " -- " m)))
            (pf:temp-clear)
            (setq *error* pf-old-err)
            (princ)))
  ;; sweep leftovers from a run interrupted before it could tidy up
  (setq stale (pf:purge-mine *PF-WALL-LAYER*))
  (if (> stale 0)
    (princ (strcat "\nADAB: cleared " (itoa stale)
                   " leftover marker(s) from layer " *PF-WALL-LAYER*
                   ".")))
  (princ "\n\nADAB - draw the pool bottom over an existing perimeter.")
  (princ "\n\n  Select the pool perimeter - one closed polyline, or its exploded")
  (princ "\n  lines/arcs.  The survey points sitting on it are found by")
  (princ "\n  themselves; select them too only if they live somewhere unusual.")
  (princ "\n  Select objects: ")
  (setq pf-phase "waiting for the selection")
  (setq ss (ssget '((0 . "POINT,INSERT,LINE,ARC,CIRCLE,LWPOLYLINE,POLYLINE"))))
  (if (null ss)
    (princ "\nNothing usable selected (survey points and the perimeter geometry).")
    (progn
      (setq pf-phase "reading the selected entities")
      (setq segs nil pts nil i 0 nocs 0 nskip 0
            npt 0 pf-ptnames nil)
      (while (< i (sslength ss))
        (setq en  (ssname ss i)
              ed  (entget en)
              typ (cdr (assoc 0 ed))
              lay (strcase (cdr (assoc 8 ed)))
              ext (cdr (assoc 210 ed))
              i   (1+ i))
        (if (and ext (< (abs (caddr ext)) 0.999)) (setq nocs (1+ nocs)))
        (cond
          ;; ab_pt blocks are survey points wherever they sit
          ((and (= typ "INSERT")
                (= (strcase (cdr (assoc 2 ed))) (strcase *PF-POINT-BLOCK*)))
           (pf:add-point (cal:2d (cdr (assoc 10 ed)))
                         (pf:block-number en)))
          ;; a plain POINT counts on any layer here - the selection
          ;; is explicit, so there is no guessing involved
          ((= typ "POINT")
           (pf:add-point (cal:2d (cdr (assoc 10 ed))) nil))
          ;; other blocks only count as points on the points layer
          ((= typ "INSERT")
           (if (= lay (strcase *PF-POINT-LAYER*))
             (pf:add-point (cal:2d (cdr (assoc 10 ed)))
                           (pf:block-number en))))
          ;; ABHD's own scaffolding and results must never be read
          ;; back as perimeter: miss rings, dashed markers, and an
          ;; earlier bottom all live on known layers or carry the
          ;; ABHD stamp
          ((or (= lay (strcase *PF-MISS-LAYER*))
               (= lay (strcase *PF-WALL-LAYER*))
               (= lay (strcase *PF-BOTTOM-LAYER*))
               (assoc -3 (entget en '("ABHD"))))
           (setq nskip (1+ nskip)))
          (T
           (setq segs (append segs (pf:ent-segs en))))))
      (if (> nocs 0)
        (princ (strcat "\nADAB: warning - " (itoa nocs)
                       " selected object(s) are not drawn in the world"
                       " plane; the bottom is built flat (XY) and may"
                       " be wrong.  Set UCS to World and flatten them"
                       " first.")))
      (if (> nskip 0)
        (princ (strcat "\n  (" (itoa nskip)
                       " marker/bottom object(s) in the selection were"
                       " ignored)")))
      (setq dpts (if pts (cal:dedupe pts *PF-EXACT-EPS*)))
      (cond
        ((null segs)
         (princ "\nNo perimeter found in the selection - include the closed polyline or its exploded lines/arcs."))
        ((null (setq loop (pf:chain segs))) nil)   ; pf:chain said why
        (T
         (if (null dpts)
           ;; no points in the selection: the perimeter knows its own.
           ;; Gather every survey point in the drawing and keep the
           ;; ones sitting on the loop.
           (progn
             (setq pf-phase "gathering the perimeter's points"
                   ss (ssget "_X"
                        (list '(-4 . "<OR")
                              '(-4 . "<AND") '(0 . "INSERT")
                              (cons 2 *PF-POINT-BLOCK*) '(-4 . "AND>")
                              '(-4 . "<AND") '(0 . "POINT")
                              (cons 8 *PF-POINT-LAYER*) '(-4 . "AND>")
                              '(-4 . "<AND") '(0 . "INSERT")
                              (cons 8 *PF-POINT-LAYER*) '(-4 . "AND>")
                              '(-4 . "OR>"))))
             (if ss
               (progn
                 (setq i 0)
                 (while (< i (sslength ss))
                   (setq en  (ssname ss i)
                         ed  (entget en)
                         typ (cdr (assoc 0 ed))
                         i   (1+ i))
                   (pf:add-point (cal:2d (cdr (assoc 10 ed)))
                                 (if (= typ "INSERT")
                                   (pf:block-number en))))))
             (setq dpts (if pts (cal:dedupe pts *PF-EXACT-EPS*))
                   dpts (pf:near-loop dpts loop *PF-PICKUP-EPS*))
             (if dpts
               (princ (strcat "\n  " (itoa (length dpts))
                              " survey point(s) sitting on the"
                              " perimeter picked up automatically."))))
           ;; points WERE selected: trim them to the perimeter's own,
           ;; so depth shots and deck points caught by the window do
           ;; not get in the way of the break and waypoint snapping
           (progn
             (setq nall (length dpts)
                   dpts (pf:near-loop dpts loop *PF-PICKUP-EPS*))
             (if (< (length dpts) nall)
               (princ (strcat "\n  (" (itoa (- nall (length dpts)))
                              " selected point(s) well off the"
                              " perimeter were set aside)")))))
         (if (null dpts)
           (princ (strcat "\nNo survey points sit on this perimeter"
                          " (within " (rtos *PF-PICKUP-EPS* 2 1)
                          ") - looked for \"" *PF-POINT-BLOCK*
                          "\" blocks anywhere and points on layer "
                          *PF-POINT-LAYER*
                          ".  Select the points explicitly if they"
                          " live elsewhere."))
           (pf:bottom loop dpts nil))))))
  (pf:temp-clear)
  (setq *error* pf-old-err)
  (princ))

;; ---- TUTORIALABHD ----------------------------------------------------
;; A guided introduction for new users, two ways: Checks lists every
;; rule and safeguard the commands apply, for readers; Demo draws a
;; practice pool and walks it through the whole flow on screen, stage
;; by stage, for lookers - then cleans up after itself.

(defun pf:tut-pause ()
  (getstring "\n  --- press Enter to continue ---")
  (princ))

;; The stage caption above the demo, replaced at each stage.
(defun pf:tut-cap (p txt hgt / e)
  (setq e (entmakex (list '(0 . "TEXT") '(100 . "AcDbEntity")
                          (cons 8 *PF-OUT-LAYER*) '(62 . 2)
                          '(100 . "AcDbText")
                          (cons 10 (list (car p) (cadr p) 0.0))
                          (cons 40 hgt)
                          (cons 1 txt))))
  (if e (pf:temp-add (pf:tag-mine e)))
  e)

;; The practice survey: a kidney-shaped pool about 30 x 16 ft around
;; CP, drawn as POINTs on the points layer and numbered like ab_pt
;; blocks would be.  Returns the points in walking order.
(defun pf:tut-survey (cp / n i tt r p out)
  (cal:ensure-layer *PF-POINT-LAYER* 7)
  (setq n 44 i 0 out nil)
  (while (< i n)
    (setq tt  (* 2.0 pi (/ (float i) n))
          r   (+ 150.0 (* 45.0 (cos tt)) (* 22.0 (sin (* 2.0 tt)))
                 (* -14.0 (cos (* 3.0 tt))))
          p   (list (+ (car cp) (* r (cos tt) 1.15))
                    (+ (cadr cp) (* r (sin tt) 0.75)))
          i   (1+ i)
          out (cons p out))
    (pf:add-point p nil)
    (pf:temp-add (pf:tag-mine
      (entmakex (list '(0 . "POINT") '(100 . "AcDbEntity")
                      (cons 8 *PF-POINT-LAYER*)
                      '(100 . "AcDbPoint")
                      (cons 10 (list (car p) (cadr p) 0.0)))))))
  (reverse out))

;; The reading tour: every rule and safeguard, in the order the
;; commands apply them.
(defun pf:tut-checks ()
  (princ "\n\nWHAT ABHD NEEDS")
  (princ "\n  * Survey points: ab_pt block inserts (any layer, their number")
  (princ "\n    attribute names them) or POINT entities on layer POINTS.")
  (princ "\n  * Optionally on layer POOL: a drawn perimeter (guided mode) or a")
  (princ "\n    lines-only connect-the-dots sketch (sets the point order).")
  (princ "\n    With neither, the points are ordered automatically.")
  (pf:tut-pause)
  (princ "\nTHE SEVEN QUESTIONS")
  (princ "\n  1. Max distance a point may sit from the line (2 inch ceiling).")
  (princ "\n  2. Percent of points allowed off the line (Enter = 15, rounded")
  (princ "\n     UP to whole points - the slack that buys longer arcs).")
  (princ "\n  3. Curve cap (None = unlimited; binds in every mode).")
  (princ "\n  4. Dead-straight walls: pick both ends, dashed marker, comes out")
  (princ "\n     as a straight LINE no arc may swallow or cross.")
  (princ "\n  5. Sharp corners: pick points where tangency is waived.")
  (princ "\n  6. Held points: pick points the line must pass through EXACTLY -")
  (princ "\n     never fudged, never spent from the miss allowance; tangency")
  (princ "\n     still applies at them (they are not corners).")
  (princ "\n  7. Select the points (and the POOL guide if you have one).")
  (pf:tut-pause)
  (princ "\nWHAT THE FITTER GUARANTEES")
  (princ "\n  * Arc endpoints sit ON survey points; arc middles pass through a")
  (princ "\n    point too (3-point arcs) whenever such an arc holds the span;")
  (princ "\n    floating arcs are a rare last resort.")
  (princ "\n  * Joints meet within 8 degrees of tangent; when nothing fits the")
  (princ "\n    window it stretches 1.25x then 1.5x rather than being dropped.")
  (princ "\n  * Radii snap to whole feet, half feet, then inches - only when")
  (princ "\n    the points allow it; the points always outrank pretty radii.")
  (princ "\n  * Turns over 45 degrees are corners and are never buried inside")
  (princ "\n    an arc; the loop is checked for crossing itself.")
  (pf:tut-pause)
  (princ "\nCHOOSING A FIT")
  (princ "\n  Three candidates draw at once, the two ends of the curves-against-")
  (princ "\n  accuracy trade and the middle: red spends the most curves to get")
  (princ "\n  the error near nothing (it ignores your distance and the curve")
  (princ "\n  cap), yellow is your settings exactly, cyan holds that same")
  (princ "\n  distance with the fewest curves it can.  Each is numbered on")
  (princ "\n  screen with its figures, plus a table: segs, curves, worst off,")
  (princ "\n  avg all, avg off, not held - all measured against the distance")
  (princ "\n  you typed.  Click the one to keep, or type 1/2/3;")
  (princ "\n  All keeps the trio, None erases everything.")
  (princ "\n  The kept fit moves onto the POOL layer in ByLayer colour.")
  (pf:tut-pause)
  (princ "\nWHAT GETS FLAGGED")
  (princ "\n  Points no fit built to your distance can hold are called out")
  (princ "\n  before you choose (the tight fit threads every point it can")
  (princ "\n  reach, so it abstains from that count).  The kept fit rings its")
  (princ "\n  unheld points (4 inch circles on FGStep) and")
  (princ "\n  lists them beside the pool, worst first, by point number.  Only")
  (princ "\n  ABHD's own stamped objects on FGStep are ever replaced.")
  (pf:tut-pause)
  (princ "\nREDO")
  (princ "\n  Redo at the choose prompt refits without leaving the command:")
  (princ "\n  omit points by clicking them (clicking a ringed one restores")
  (princ "\n  it - omissions carry across redos), add/remove straight walls,")
  (princ "\n  sharp corners and held points, then the three numbers are asked")
  (princ "\n  again with Enter keeping each.  Repeat until a fit is kept.")
  (pf:tut-pause)
  (princ "\nTHE POOL BOTTOM")
  (princ "\n  After keeping one fit (or via ADAB over any existing perimeter):")
  (princ "\n  pick the SHALLOW BREAK ends, then the DEEP BREAK ends.  The back")
  (princ "\n  of the hopper is found automatically - the survey point nearest")
  (princ "\n  a ray cast from the deep break's middle, away from the shallow.")
  (princ "\n  Three offsets are asked by point number (type 42 or 3'6 - the")
  (princ "\n  format picks the dim style on the back/waypoint dims: SIDE")
  (princ "\n  DIMENSION for feet-inches, STANDARD INCHES for inches).")
  (pf:tut-pause)
  (princ "\n  The hopper's corners land ON the deep break line, which is drawn")
  (princ "\n  as three lines: DASHED2 stubs wall-to-corner, solid across.  Its")
  (princ "\n  dims form the K/L/M string a foot off the line on the shallow")
  (princ "\n  side.  Each slope line to the shallow break is asked Straight,")
  (princ "\n  Guided (follows the perimeter, easing to nothing), or Points")
  (princ "\n  (pick points with pinned offsets, square off the wall, each")
  (princ "\n  dimensioned).  Offsets draw as few merged arcs, not facets, and")
  (princ "\n  every line and dim lands on the POOL layer.")
  (pf:tut-pause)
  (princ "\nHOUSEKEEPING")
  (princ "\n  ADAB needs only the perimeter selected - the survey points on it")
  (princ "\n  are picked up automatically (strays are set aside).  Scaffolding")
  (princ "\n  - markers, previews, labels - sweeps itself on any exit, ESC")
  (princ "\n  included, and a run interrupted mid-flight is tidied by the next.")
  (princ (strcat "\n  This is ABHD " pf:*version*
                 " - the versioned twin file carries the same name."))
  (princ))

;; The watching tour: draw it, fit it, choose it, floor it, clean up.
(defun pf:tut-demo ( / cp tour dpts allow bb hgt cap v segs ent cand
                       kept d1 d2 s1 s2 sp1 sp2 dp1 dp2 back lines q
                       pts npt pf-ptnames pf-miss-pct pf-walls
                       pf-corners pf-holds pf-dim-warned)
  (setq pf-phase "picking a spot for the demo")
  (princ "\n\n  The demo draws a practice pool about 30 ft wide, walks it")
  (princ "\n  through the whole flow, and cleans up after itself.")
  (setq cp (getpoint "\n  Pick a clear spot for it: "))
  (if (null cp)
    (princ "\n  (no spot picked - tutorial ended, nothing drawn)")
    (progn
      (setq cp   (cal:2d cp)
            npt  0
            tour (pf:tut-survey cp)
            dpts (cal:dedupe pts *PF-EXACT-EPS*)
            bb   (pf:bbox dpts)
            hgt  (/ (- (caddr bb) (car bb)) 24.0)
            allow (cal:ceil (* (pf:misspct) (length dpts))))
      (setq cap (pf:tut-cap (list (car bb) (+ (cadddr bb) hgt))
                  "1. The survey: ab_pt blocks or POINTs on POINTS"
                  hgt))
      (princ "\n\n  1. A surveyor shot these points along the pool edge.")
      (pf:tut-pause)
      ;; the walking order
      (if (and cap (entget cap)) (entdel cap))
      (setq cap (pf:tut-cap (list (car bb) (+ (cadddr bb) hgt))
                  "2. The points are ordered into a loop" hgt)
            ent (pf:temp-add (pf:tag-mine
                  (pf:make-pline
                    (mapcar '(lambda (p) (list p 0.0)) tour)
                    *PF-OUT-LAYER* 8))))
      (princ "\n  2. ABHD orders them into a closed loop (a lines-only sketch")
      (princ "\n     on POOL can dictate this order instead).")
      (pf:tut-pause)
      (if (and ent (entget ent)) (entdel ent))
      ;; the three candidates
      (if (and cap (entget cap)) (entdel cap))
      (setq cap (pf:tut-cap (list (car bb) (+ (cadddr bb) hgt))
                  "3. Three candidates: red tight, yellow asked, cyan few"
                  hgt)
            cand nil)
      (foreach v *PF-COMPARE*
        (setq segs (pf:build tour nil pts dpts 1.0 allow (car v))
              ent  (pf:temp-add (pf:tag-mine
                     (pf:make-pline
                       (mapcar '(lambda (s) (list (car s) (caddr s)))
                               segs)
                       *PF-OUT-LAYER* (cadr v))))
              cand (cons (list segs ent) cand)))
      (setq cand (reverse cand))
      (princ "\n  3. Three fits draw at once - the most curves for the least")
      (princ "\n     error, your settings exactly, and the fewest curves that")
      (princ "\n     still hold your distance - each numbered with its figures,")
      (princ "\n     plus a table at the command line.  Every arc runs point to")
      (princ "\n     point, joints within 8 degrees of tangent, radii on feet")
      (princ "\n     and inches where the points allow.")
      (pf:tut-pause)
      ;; keep the middle one
      (if (and cap (entget cap)) (entdel cap))
      (setq cap (pf:tut-cap (list (car bb) (+ (cadddr bb) hgt))
                  "4. Click one to keep - Redo refits, omits points"
                  hgt))
      (setq q (cadr (car cand)))
      (if (and q (entget q)) (entdel q))
      (setq q (cadr (caddr cand)))
      (if (and q (entget q)) (entdel q))
      (setq kept (car (cadr cand)))
      (pf:set-bylayer (cadr (cadr cand)))
      (princ "\n  4. Click the outline you like (or type its number) - the")
      (princ "\n     rest are swept.  Unheld points would be ringed on FGStep")
      (princ "\n     and listed by number.  Redo refits with new settings,")
      (princ "\n     omitted points, and edited walls or corners.")
      (pf:tut-pause)
      ;; the bottom
      (if (and cap (entget cap)) (entdel cap))
      (setq cap (pf:tut-cap (list (car bb) (+ (cadddr bb) hgt))
                  "5. The bottom: breaks, hopper, K/L/M dims, slopes"
                  hgt))
      (setq d1  (nth 4 tour)  d2 (nth 40 tour)
            s1  (nth 18 tour) s2 (nth 26 tour)
            sp1 (pf:curve-near s1 kept) sp2 (pf:curve-near s2 kept)
            dp1 (pf:curve-near d1 kept) dp2 (pf:curve-near d2 kept)
            back (pf:hopper-back dp1 dp2 sp1 sp2 dpts))
      (cal:ensure-layer *PF-POOL-LAYER* 4)
      (setq lines (list (pf:temp-add (pf:tag-mine
                          (pf:make-line sp1 sp2 nil nil)))
                        (pf:temp-add (pf:tag-mine
                          (pf:make-line dp1 dp2 nil nil)))))
      (setq q (entlast))
      (pf:bottom-draw kept sp1 sp2 dp1 dp2 back 12.0 12.0 18.0 nil
                      lines (list T nil))
      ;; bottom-draw promotes its output out of the scaffolding
      ;; registry; a tutorial must still clean it, so re-register
      ;; everything it just made
      (while (setq q (entnext q)) (pf:temp-add q))
      (princ "\n\n  5. ADAB (or the offer after keeping a fit) added the")
      (princ "\n     breaks, found the back point by itself, pulled the")
      (princ "\n     hopper in at your three offsets (asked by point number),")
      (princ "\n     dimensioned them a foot off the deep break on the")
      (princ "\n     shallow side, and ran one")
      (princ "\n     slope guided along the curve, the other straight.")
      (pf:tut-pause)
      (if (and cap (entget cap)) (entdel cap))
      (princ "\n\n  That is the whole flow.  TUTORIALABHD Checks lists every")
      (princ "\n  rule; ABHD runs it on your survey; ADAB does just the")
      (princ "\n  bottom over any perimeter.")
      (initget "Yes No")
      (if (= "Yes" (getkword
                     "\n  Keep the demo drawing to poke at? [Yes/No] <No>: "))
        (progn
          (setq pf-temp nil)
          (princ "\n  Kept - erase it whenever; every piece is stamped ABHD."))
        (princ "\n  Swept - the drawing is as it was.")))))

(defun c:TUTORIALABHD ( / mode pf-temp pf-phase *error* pf-old-err)
  (setq pf-temp   nil
        pf-old-err *error*
        *error*
          (lambda (m)
            (if (and m (not (wcmatch (strcase m)
                     "*BREAK*,*CANCEL*,*QUIT*,*EXIT*")))
              (princ (strcat "\nTUTORIALABHD stopped -- " m)))
            (pf:temp-clear)
            (setq *error* pf-old-err)
            (princ)))
  (princ (strcat "\n\nTUTORIALABHD - how the ABHD pool fitter works ("
                 pf:*version* ")."))
  ;; one bracket, exactly the keyword list (STANDARDS section 1 rule
  ;; 1), and the standard tutorial selector with Both
  (initget "Checks Demo Both")
  (setq mode (getkword
               "\n  Read the checks it applies, watch a drawn demo, or both? [Checks/Demo/Both] <Both>: "))
  (cond ((= mode "Checks") (pf:tut-checks))
        ((= mode "Demo")   (pf:tut-demo))
        (t (pf:tut-checks) (pf:tut-demo)))
  (pf:temp-clear)
  (setq *error* pf-old-err)
  (princ))

;; The same tutorial under the bottom command's name, for whoever
;; goes looking for it there.
(defun c:TUTORIALADAB () (c:TUTORIALABHD))

(princ (strcat "\nABHD " pf:*version*
               " loaded.  ABHD fits the pool perimeter through its"
               " points;"))
(princ "\nADAB draws the pool bottom over an existing perimeter;")
(princ "\nTUTORIALABHD (or TUTORIALADAB) walks new users through everything.")
(princ)


;;; ======================================================================
;;; >>> ABCURCHECK.lsp
;;; ======================================================================

;;; ======================================================================
;;; ABCURCHECK.lsp  --  grade how continuous a drawn pool perimeter is
;;; ----------------------------------------------------------------------
;;; For AutoCAD 2018 and later (plain AutoLISP, no external libraries).
;;;
;;; Commands:  ABCURCHECK        measure a perimeter, mark it, report
;;;            ABCURCHECKSCAN    the same measurement, nothing drawn
;;;            ABCURCHECKRESCUE  erase the marks ABCURCHECK made
;;;            ABCURCHECKVER     print the loaded version
;;;
;;; SHARED BUILD: requires CALOFIN-LIB.lsp (load via CALOFIN-LOADER.lsp).
;;; Generic helpers live there under cal: - see STANDARDS.md.
;;;
;;; A fork of ABHD's geometry reader.  ABHD BUILDS a smooth perimeter
;;; through surveyed points; this measures one that already exists and
;;; says how continuous it is - as a word a drafter can act on, not a
;;; pile of numbers.
;;;
;;; THE INPUT is the same either way: one closed LWPOLYLINE / POLYLINE,
;;; or that same shape exploded into LINEs and ARCs (a CIRCLE counts as
;;; a round spa perimeter).  Exploded input is walked back into a ring
;;; nearest-end first; unlike ABHD's pf:chain this never bails on a
;;; gap, because measuring the gap IS the job.
;;;
;;; CONTINUITY IS A LADDER, and each rung catches a different kind of
;;; bad drawing:
;;;
;;;   G0 - does it close?  Endpoint gaps between segments, zero-length
;;;        segments, duplicated segments, and chords that cross.  A
;;;        trace exploded and rejoined by hand is riddled with
;;;        sub-1/16" gaps that look perfect on screen and break every
;;;        tool downstream.  Any of these caps the grade at Broken.
;;;
;;;   G1 - tangent breaks.  At every joint, the signed angle between
;;;        the arriving tangent and the leaving one.  The bands are
;;;        ABHD's own numbers, so the two commands agree on what
;;;        "smooth" means:
;;;
;;;          <= acc:*tangent-eps*  (0.5 deg)  tangent - clean
;;;          <= acc:*kink-tol*     (8 deg)    soft break - reads smooth
;;;          <= acc:*corner-ang*   (45 deg)   VISIBLE KINK - the problem
;;;           > acc:*corner-ang*              corner - meant, if declared
;;;
;;;        That 8-45 band is the whole point of the command: too big to
;;;        look smooth, too small to read as an intentional corner.  It
;;;        is the kink a fabricator finds in the bead and nobody meant
;;;        to draw.
;;;
;;;   NOISE - the metrics that catch a TRACED perimeter, which is
;;;        tangent everywhere and still wrong.  Micro-segments (shorter
;;;        than acc:*micro-len*) and their share of the perimeter;
;;;        curvature sign changes (inflections); and the turning
;;;        excess.  For any simple closed loop the SIGNED turning is
;;;        exactly 360 deg, while the ABSOLUTE turning - every arc
;;;        sweep and every kink added up regardless of direction - is
;;;        at least that, and equal only for a convex shape.  So
;;;
;;;            excess = (total absolute turning / 360 deg) - 1
;;;
;;;        is one scale-free number folding kinks and wiggle together:
;;;        0 for an oval, a few tenths for a kidney's concave run, well
;;;        over 1 for a noisy trace.  The signed total is reported too,
;;;        because a value that is not 360 deg means the loop doubles
;;;        back or crosses itself.
;;;
;;; DECLARED DISCONTINUITIES.  The user picks the breaks that are meant
;;; to be there - a step corner, a spa dam wall, a beach entry.  One
;;; pick does three jobs:
;;;   * it snaps to the nearest joint within acc:*snap-dist* and takes
;;;     that joint out of the grade, listing it separately with its
;;;     measured angle, so a 90 deg corner stops dragging the score
;;;     down;
;;;   * a pick that lands nowhere near a joint is reported the other
;;;     way round - "declared here, but the geometry is continuous";
;;;   * everything left over is the real output: the UNDECLARED
;;;     discontinuities, which is the list to go and fix.
;;; Declarations are dashed rings on acc:*mark-layer*, stamped as this
;;; command's own, so a second run remembers what the first was told.
;;;
;;; THE VERDICT is two numbers on purpose.  The GRADE - Broken, Rough,
;;; Fair or Smooth - is set by the single worst thing found and names
;;; it, because a drafter has to know why.  The INDEX (0-100) is a
;;; weighted blend of integrity, tangency and noise; it settles nothing
;;; on its own and exists to compare two candidate perimeters.
;;;
;;; THE CURVATURE COMB is the qualitative answer in a form nobody needs
;;; a table to read: a tooth at every sample, its length proportional
;;; to curvature and its side set by which way the curve turns, with
;;; the tips strung into one envelope.  Every tangent break is a step
;;; in that envelope, every noisy stretch a fuzzy one, and every
;;; inflection a crossing.  Lines and arcs are never truly curvature-
;;; continuous, so the steps at a line-to-arc joint are expected - the
;;; comb shows their SIZE, which is the part that matters.
;;;
;;; WHAT IS NOT MEASURED: curvature jumps are drawn, not scored - a
;;; polyline of lines and arcs can never be G2-continuous, so grading
;;; it on that would fail every honest drawing.  Crossings are tested
;;; on segment CHORDS, so a bulged pair that overlaps only through its
;;; arcs is caught by the signed-turning total instead.
;;; ======================================================================

(setq *abcurcheck-version* "v1.0")   ; announced on load; release_lisp.py
                                     ; reads this banner and stamps the
                                     ; dated twin in releases/ from it

;; ---- configuration ---------------------------------------------------

(setq acc:*mark-layer*   "POOL-CONT")  ; findings and declarations go here
(setq acc:*comb-layer*   "POOL-COMB")  ; the curvature comb goes here
(setq acc:*fuzz*         1.0e-4)       ; endpoint-matching fuzz, as ABHD's
                                       ; *PF-CHAIN-FUZZ*: closer than this
                                       ; and two ends are the same point
(setq acc:*tangent-eps*  0.5)          ; deg - at or under this a joint is
                                       ; tangent
(setq acc:*kink-tol*     8.0)          ; deg - ABHD's *PF-TANG-TOL*: the
                                       ; most a joint may turn and still
                                       ; read as smooth
(setq acc:*corner-ang*   45.0)         ; deg - ABHD's *PF-CORNER-ANG*:
                                       ; over this it is a corner, not a
                                       ; kink
(setq acc:*micro-len*    3.0)          ; a segment shorter than this (3
                                       ; inches) is a micro-segment: the
                                       ; signature of a traced outline
(setq acc:*micro-share*  0.10)         ; share of the perimeter sitting in
                                       ; micro-segments that costs the
                                       ; whole noise score
(setq acc:*close-tol*    5.0)          ; deg - how far the signed turning
                                       ; total may sit off 360 before the
                                       ; loop is called self-crossing
(setq acc:*snap-dist*    6.0)          ; how near a declaration pick must
                                       ; land to a joint to claim it
(setq acc:*mark-radius*  4.0)          ; radius of the finding rings
(setq acc:*cross-max*    300)          ; skip the O(n^2) crossing scan
                                       ; above this many segments, and say
                                       ; so rather than pretend it ran
(setq acc:*comb-step*    12.0)         ; one comb tooth per foot of run
(setq acc:*comb-max*     24.0)         ; length of the tooth at the
                                       ; tightest curvature in the loop
(setq acc:*excess-free*  0.35)         ; turning excess a freeform pool is
                                       ; allowed before the noise score
                                       ; starts to fall...
(setq acc:*excess-cap*   1.00)         ; ...and where it reaches zero
(setq acc:*w-integrity*  40.0)         ; index weights: G0 is pass/fail,
(setq acc:*w-tangency*   35.0)         ; tangency scales with the total
(setq acc:*w-noise*      25.0)         ; undeclared kink, noise with the
                                       ; micro share and turning excess

(setq acc:*sysvars* '("OSMODE" "CMDECHO" "CLAYER"))  ; saved and put back

;; ---- small 2D vector helpers -----------------------------------------
;; Local copies of the generic library helpers, as the standalone tier
;; requires (STANDARDS section 6): same bodies, this file's prefix.

(defun acc:deg (r) (* 180.0 (/ r pi)))
(defun acc:rad (d) (* pi (/ d 180.0)))

;; drop the first structurally equal member of LST
(defun acc:remove (val lst / out hit x)
  (setq out nil hit nil)
  (foreach x lst
    (if (and (not hit) (equal x val))
      (setq hit T)
      (setq out (cons x out))))
  (reverse out))

;; Circumcenter of three points, nil when (nearly) collinear.
(defun acc:circumcenter (pa pb pc / x1 y1 x2 y2 x3 y3 d s1 s2 s3)
  (setq x1 (car pa) y1 (cadr pa)
        x2 (car pb) y2 (cadr pb)
        x3 (car pc) y3 (cadr pc)
        d  (* 2.0 (+ (* x1 (- y2 y3)) (* x2 (- y3 y1)) (* x3 (- y1 y2)))))
  (if (< (abs d) 1.0e-10)
    nil
    (progn
      (setq s1 (+ (* x1 x1) (* y1 y1))
            s2 (+ (* x2 x2) (* y2 y2))
            s3 (+ (* x3 x3) (* y3 y3)))
      (list (/ (+ (* s1 (- y2 y3)) (* s2 (- y3 y1)) (* s3 (- y1 y2))) d)
            (/ (+ (* s1 (- x3 x2)) (* s2 (- x1 x3)) (* s3 (- x2 x1))) d)))))

;; ---- segment geometry ------------------------------------------------
;; A segment is (startPt endPt bulge), 2D points - ABHD's shape exactly,
;; so the two commands read a drawing the same way.

;; signed sweep of a bulged segment: bulge = tan(sweep/4), positive CCW
(defun acc:sweep (b) (* 4.0 (atan b)))

;; Radius of the arc (A B bulge); nil for a straight segment.
(defun acc:bulge-radius (a b bl / h)
  (if (< (abs bl) 1.0e-9)
    nil
    (progn
      (setq h (/ (cal:dist a b) 2.0))
      (/ (* h (1+ (* bl bl))) (* 2.0 (abs bl))))))

;; Signed curvature of a segment: 0.0 straight, +ve turning left (CCW).
;; The sign is what makes an inflection countable and what puts a comb
;; tooth on the correct side.
(defun acc:seg-curv (s / r)
  (setq r (acc:bulge-radius (car s) (cadr s) (caddr s)))
  (cond ((null r) 0.0)
        ((< r 1.0e-9) 0.0)
        ((< (caddr s) 0.0) (- (/ 1.0 r)))
        (T (/ 1.0 r))))

;; Length along a segment - the chord when straight, the arc otherwise.
(defun acc:seg-len (s / r)
  (setq r (acc:bulge-radius (car s) (cadr s) (caddr s)))
  (if r
    (* r (abs (acc:sweep (caddr s))))
    (cal:dist (car s) (cadr s))))

;; Tangent direction at the start of a segment: the chord direction
;; turned back by half the sweep.
(defun acc:seg-t0 (s)
  (- (angle (cal:2d (car s)) (cal:2d (cadr s)))
     (* 2.0 (atan (caddr s)))))

;; ...and at its end: the chord direction turned on by half the sweep.
(defun acc:seg-t1 (s)
  (+ (angle (cal:2d (car s)) (cal:2d (cadr s)))
     (* 2.0 (atan (caddr s)))))

;; Arc geometry of a bulged segment: (center radius angStart), nil when
;; the segment is straight.
(defun acc:arc-geom (s / p1 p2 b ch dir apex c)
  (setq p1 (cal:2d (car s))
        p2 (cal:2d (cadr s))
        b  (caddr s))
  (if (< (abs b) 1.0e-9)
    nil
    (progn
      (setq ch   (cal:dist p1 p2)
            dir  (cal:v* (cal:v- p2 p1) (/ 1.0 ch))
            ;; sagitta = (chord/2)*bulge; a positive (CCW) bulge apex
            ;; lies to the RIGHT of the p1->p2 chord direction
            apex (cal:v+ (cal:v* (cal:v+ p1 p2) 0.5)
                          (cal:v* (list (- (cadr dir)) (car dir))
                                   (* -0.5 ch b)))
            c    (acc:circumcenter p1 apex p2))
      (if (null c)
        nil
        (list c (cal:dist c p1) (angle c p1))))))

;; The point at parameter U (0..1) along a segment.
(defun acc:seg-pt (s u / g)
  (setq g (acc:arc-geom s))
  (if (null g)
    (cal:v+ (cal:2d (car s))
             (cal:v* (cal:v- (cadr s) (car s)) u))
    (polar (car g) (+ (caddr g) (* u (acc:sweep (caddr s)))) (cadr g))))

;; The tangent direction at parameter U: it rotates uniformly along an
;; arc, so this is the start tangent plus U of the sweep.
(defun acc:seg-tan (s u)
  (+ (acc:seg-t0 s) (* u (acc:sweep (caddr s)))))

;; ---- entity -> segment extraction ------------------------------------

(defun acc:lw-segs (ed / pts bls item segs n closed)
  ;; collect (10) vertices and their (42) bulges, in order
  (setq pts nil bls nil)
  (foreach item ed
    (cond
      ((= (car item) 10)
       (setq pts (cons (cal:2d (cdr item)) pts)
             bls (cons 0.0 bls)))
      ((and (= (car item) 42) bls)
       (setq bls (cons (cdr item) (cdr bls))))))
  (setq pts    (reverse pts)
        bls    (reverse bls)
        closed (= 1 (logand 1 (cdr (assoc 70 ed))))
        segs   nil
        n      0)
  (while (< n (1- (length pts)))
    (setq segs (cons (list (nth n pts) (nth (1+ n) pts) (nth n bls)) segs)
          n    (1+ n)))
  ;; The closing span of a CLOSED polyline is real geometry and carries
  ;; the last vertex's bulge.  An OPEN one is left open on purpose: the
  ;; ring is closed later with a recorded gap, which is the finding.
  ;; TWO vertices is enough here, where ABHD wants three: a round spa
  ;; is drawn as two bulged vertices, and dropping its closing span
  ;; would turn the smoothest shape in the drawing into a 180 deg kink.
  (if (and closed (> (length pts) 1)
           (>= (cal:dist (last pts) (car pts)) acc:*fuzz*))
    (setq segs (cons (list (last pts) (car pts) (last bls)) segs)))
  (reverse segs))

(defun acc:pl-segs (en / ed sub pts bls segs n closed)
  ;; heavy (old-style) 2D POLYLINE: walk its VERTEX sub-entities
  (setq ed     (entget en)
        closed (= 1 (logand 1 (cdr (assoc 70 ed))))
        pts    nil
        bls    nil
        sub    (entnext en))
  (while (and sub (= "VERTEX" (cdr (assoc 0 (setq ed (entget sub))))))
    ;; skip spline/fit control vertices (flag bits 1 and 16)
    (if (= 0 (logand 17 (cond ((cdr (assoc 70 ed))) (0))))
      (setq pts (cons (cal:2d (cdr (assoc 10 ed))) pts)
            bls (cons (cond ((cdr (assoc 42 ed))) (0.0)) bls)))
    (setq sub (entnext sub)))
  (setq pts (reverse pts) bls (reverse bls) segs nil n 0)
  (while (< n (1- (length pts)))
    (setq segs (cons (list (nth n pts) (nth (1+ n) pts) (nth n bls)) segs)
          n    (1+ n)))
  (if (and closed (> (length pts) 1))
    (setq segs (cons (list (last pts) (car pts) (last bls)) segs)))
  (reverse segs))

(defun acc:ent-segs (en / ed typ c r a1 a2 delta)
  (setq ed  (entget en)
        typ (cdr (assoc 0 ed)))
  (cond
    ((= typ "LINE")
     (list (list (cal:2d (cdr (assoc 10 ed)))
                 (cal:2d (cdr (assoc 11 ed)))
                 0.0)))
    ((= typ "ARC")
     (setq c     (cal:2d (cdr (assoc 10 ed)))
           r     (cdr (assoc 40 ed))
           a1    (cdr (assoc 50 ed))
           a2    (cdr (assoc 51 ed))
           delta (cal:angnorm (- a2 a1)))
     (if (< delta 1.0e-10) (setq delta (* 2.0 pi)))
     ;; a full-circle arc cannot be one bulged segment (its bulge is
     ;; infinite): hand back two semicircles instead
     (if (> delta (- (* 2.0 pi) 1.0e-9))
       (list (list (polar c a1 r) (polar c (+ a1 pi) r) 1.0)
             (list (polar c (+ a1 pi) r) (polar c a1 r) 1.0))
       (list (list (polar c a1 r) (polar c a2 r) (cal:tan (/ delta 4.0))))))
    ;; a CIRCLE is a legitimate perimeter (round spa): two semicircles,
    ;; so the ring walk sees a normal closed loop instead of a gap
    ((= typ "CIRCLE")
     (setq c (cal:2d (cdr (assoc 10 ed)))
           r (cdr (assoc 40 ed)))
     (list (list (polar c 0.0 r) (polar c pi r) 1.0)
           (list (polar c pi r) (polar c 0.0 r) 1.0)))
    ((= typ "LWPOLYLINE") (acc:lw-segs ed))
    ((= typ "POLYLINE") (acc:pl-segs en))
    (T nil)))

;; ---- ordering loose segments into a ring -----------------------------
;; ABHD's pf:chain stops at the first gap because a gap means it cannot
;; fit.  Here the gap is the finding, so the walk always carries on:
;; take whichever remaining segment has an end nearest to where we are,
;; reversing it when it is its far end that is nearer, and let the jump
;; distance be recorded as the joint's gap.

(defun acc:chain (segs / loop cur rest best orig bd s d dr)
  (if (null segs)
    nil
    (progn
      (setq loop (list (car segs))
            cur  (cadr (car segs))
            rest (cdr segs))
      (while rest
        (setq best nil orig nil bd nil)
        (foreach s rest
          (setq d  (cal:dist cur (car s))
                dr (cal:dist cur (cadr s)))
          (if (or (null bd) (< d bd))
            (setq bd d best s orig s))
          (if (< dr bd)
            (setq bd   dr
                  best (list (cadr s) (car s) (- (caddr s)))
                  orig s)))
        (setq loop (cons best loop)
              cur  (cadr best)
              rest (acc:remove orig rest)))
      (reverse loop))))

;; ---- the joints ------------------------------------------------------
;; One record per joint of the ring, joint I sitting between segment I
;; and segment I+1 (the last one wrapping round to the first):
;;
;;   (index  position-along  gap  kink-angle  point  band
;;    declared-p)
;;
;; POSITION-ALONG is measured from the start of the first segment, so a
;; finding can be walked to.  BAND is the tangent classification, and
;; DECLARED-P says the user has already accounted for it.

(defun acc:j-idx  (j) (nth 0 j))
(defun acc:j-pos  (j) (nth 1 j))
(defun acc:j-gap  (j) (nth 2 j))
(defun acc:j-ang  (j) (nth 3 j))
(defun acc:j-pt   (j) (nth 4 j))
(defun acc:j-band (j) (nth 5 j))
(defun acc:j-decl (j) (nth 6 j))

;; Which band a turn of A radians (absolute) falls in.
(defun acc:band (a)
  (cond ((<= a (acc:rad acc:*tangent-eps*)) "tangent")
        ((<= a (acc:rad acc:*kink-tol*))    "soft")
        ((<= a (acc:rad acc:*corner-ang*))  "kink")
        (T                                  "corner")))

;; T when P is close enough to one of the declared picks to be claimed.
(defun acc:declared-p (p declared / hit q)
  (setq hit nil)
  (foreach q declared
    (if (<= (cal:dist p q) acc:*snap-dist*) (setq hit T)))
  hit)

(defun acc:joints (segs declared / n i k out this next pos gap ang p)
  (setq n   (length segs)
        i   0
        pos 0.0
        out nil)
  (while (< i n)
    (setq this (nth i segs)
          k    (if (= (1+ i) n) 0 (1+ i))
          next (nth k segs)
          pos  (+ pos (acc:seg-len this))
          gap  (cal:dist (cadr this) (car next))
          ang  (cal:signed-dang (acc:seg-t1 this) (acc:seg-t0 next))
          p    (cal:2d (cadr this))
          out  (cons (list (1+ i) pos gap ang p
                           (acc:band (abs ang))
                           (acc:declared-p p declared))
                     out)
          i    (1+ i)))
  (reverse out))

;; ---- G0: the defects that make a grade Broken ------------------------

;; Segments with no length left in them.  They carry no tangent of
;; their own, so every joint either side of one is reported against a
;; direction that means nothing - which is exactly why they matter.
(defun acc:zero-segs (segs / i out s)
  (setq i 0 out nil)
  (foreach s segs
    (setq i (1+ i))
    (if (< (acc:seg-len s) acc:*fuzz*) (setq out (cons i out))))
  (reverse out))

;; Segments drawn twice, either way round - the classic result of a
;; copy that landed back on its original.
(defun acc:dupe-segs (segs / n i k a b out)
  (setq n (length segs) i 0 out nil)
  (while (< i n)
    (setq a (nth i segs) k (1+ i))
    (while (< k n)
      (setq b (nth k segs))
      ;; The bulge has to agree as well as the ends, and reversing a
      ;; segment negates it.  Endpoints alone would call the two halves
      ;; of a round spa - one chord, two opposite arcs - a doubled
      ;; segment, and grade the smoothest shape in the drawing Broken.
      (if (or (and (< (cal:dist (car a) (car b)) acc:*fuzz*)
                   (< (cal:dist (cadr a) (cadr b)) acc:*fuzz*)
                   (< (abs (- (caddr a) (caddr b))) 1.0e-6))
              (and (< (cal:dist (car a) (cadr b)) acc:*fuzz*)
                   (< (cal:dist (cadr a) (car b)) acc:*fuzz*)
                   (< (abs (+ (caddr a) (caddr b))) 1.0e-6)))
        (setq out (cons (list (1+ i) (1+ k)) out)))
      (setq k (1+ k)))
    (setq i (1+ i)))
  (reverse out))

;; Do the open chords A-B and C-D properly cross?  Shared endpoints are
;; excluded by the strict bounds, so neighbours never register.
(defun acc:chords-cross-p (a b c d / r s den t1 u ac)
  (setq r   (cal:v- b a)
        s   (cal:v- d c)
        den (cal:cross r s))
  (if (< (abs den) 1.0e-12)
    nil
    (progn
      (setq ac (cal:v- c a)
            t1 (/ (cal:cross ac s) den)
            u  (/ (cal:cross ac r) den))
      (and (> t1 1.0e-9) (< t1 (- 1.0 1.0e-9))
           (> u  1.0e-9) (< u  (- 1.0 1.0e-9))))))

;; Every crossing pair of segment chords.  Adjacent segments are
;; skipped (they share a point by design) and the scan is quadratic, so
;; it stands down above acc:*cross-max* segments rather than hang - the
;; report says when it did.
(defun acc:crossings (segs / n i k a b out)
  (setq n (length segs) i 0 out nil)
  (while (< i n)
    (setq a (nth i segs) k (+ i 2))
    (while (< k n)
      (setq b (nth k segs))
      (if (not (and (= i 0) (= k (1- n))))   ; first and last are neighbours
        (if (acc:chords-cross-p (car a) (cadr a) (car b) (cadr b))
          (setq out (cons (list (1+ i) (1+ k)) out))))
      (setq k (1+ k)))
    (setq i (1+ i)))
  (reverse out))

;; ---- noise -----------------------------------------------------------

;; Curvature sign changes around the ring.  Straight segments carry no
;; sign, so they neither make nor mask an inflection; the walk is
;; cyclic, so the seam counts like any other.
(defun acc:inflections (segs / signs k n i out s)
  (setq signs nil)
  (foreach s segs
    (setq k (acc:seg-curv s))
    (if (> (abs k) 1.0e-12)
      (setq signs (cons (if (> k 0.0) 1 -1) signs))))
  (setq signs (reverse signs)
        n     (length signs)
        i     0
        out   0)
  (if (> n 1)
    (while (< i n)
      (if (/= (nth i signs) (nth (if (= (1+ i) n) 0 (1+ i)) signs))
        (setq out (1+ out)))
      (setq i (1+ i))))
  out)

;; ---- the measurement -------------------------------------------------
;; Everything the report, the grade and the marks are built from, as one
;; alist so a test can read any single number out of a run.

(defun acc:val (key res) (cdr (assoc key res)))

(defun acc:measure (segs declared / joints n perim gaps zeros dupes
                                    crosses crossrun tsign tabs excess
                                    micron microlen share inflect
                                    tangn softn kinkn cornn decln
                                    declj orphans worst und q hit j s)
  (setq joints (acc:joints segs declared)
        n      (length segs)
        perim  0.0
        tsign  0.0
        tabs   0.0
        micron 0
        microlen 0.0)
  (foreach s segs
    (setq perim (+ perim (acc:seg-len s))
          tsign (+ tsign (acc:sweep (caddr s)))
          tabs  (+ tabs (abs (acc:sweep (caddr s)))))
    (if (< (acc:seg-len s) acc:*micro-len*)
      (setq micron   (1+ micron)
            microlen (+ microlen (acc:seg-len s)))))
  (setq gaps nil tangn 0 softn 0 kinkn 0 cornn 0 decln 0
        declj nil und nil worst nil)
  (foreach j joints
    (setq tsign (+ tsign (acc:j-ang j))
          tabs  (+ tabs (abs (acc:j-ang j))))
    (if (>= (acc:j-gap j) acc:*fuzz*) (setq gaps (cons j gaps)))
    (if (acc:j-decl j)
      (setq decln (1+ decln) declj (cons j declj))
      (progn
        (setq und (cons j und))
        (cond ((= (acc:j-band j) "tangent") (setq tangn (1+ tangn)))
              ((= (acc:j-band j) "soft")    (setq softn (1+ softn)))
              ((= (acc:j-band j) "kink")    (setq kinkn (1+ kinkn)))
              (T                            (setq cornn (1+ cornn))))
        (if (or (null worst) (> (abs (acc:j-ang j)) (abs (acc:j-ang worst))))
          (setq worst j)))))
  ;; a pick that claimed no joint at all: the user says there is a break
  ;; here and the geometry disagrees, which is worth saying out loud
  (setq orphans nil)
  (foreach q declared
    (setq hit nil)
    (foreach j joints
      (if (<= (cal:dist q (acc:j-pt j)) acc:*snap-dist*) (setq hit T)))
    (if (not hit) (setq orphans (cons q orphans))))
  (setq zeros    (acc:zero-segs segs)
        dupes    (acc:dupe-segs segs)
        crossrun (<= n acc:*cross-max*)
        crosses  (if crossrun (acc:crossings segs) nil)
        excess   (- (/ tabs (* 2.0 pi)) 1.0)
        share    (if (> perim 0.0) (/ microlen perim) 0.0)
        inflect  (acc:inflections segs))
  (list (cons "segs" segs)          (cons "joints" joints)
        (cons "n" n)                (cons "perim" perim)
        (cons "gaps" (reverse gaps)) (cons "zeros" zeros)
        (cons "dupes" dupes)        (cons "crosses" crosses)
        (cons "crossrun" crossrun)
        (cons "turn-signed" tsign)  (cons "turn-abs" tabs)
        (cons "excess" excess)
        (cons "micro-n" micron)     (cons "micro-len" microlen)
        (cons "micro-share" share)  (cons "inflect" inflect)
        (cons "tangent-n" tangn)    (cons "soft-n" softn)
        (cons "kink-n" kinkn)       (cons "corner-n" cornn)
        (cons "decl-n" decln)       (cons "decl-joints" (reverse declj))
        (cons "undeclared" (reverse und))
        (cons "orphans" (reverse orphans))
        (cons "worst" worst)))

;; ---- the offenders ---------------------------------------------------
;; The joints the user has not accounted for and that break a
;; threshold: the list the report prints and the marks ring, gathered
;; in one place so the two can never disagree about what counts.

;; How badly one joint offends.  A gap outranks any kink outright - a
;; loop that is not joined up is a different order of problem from one
;; that is joined up roughly.
(defun acc:severity (j)
  (if (>= (acc:j-gap j) acc:*fuzz*)
    (+ 1000.0 (acc:j-gap j))
    (acc:deg (abs (acc:j-ang j)))))

(defun acc:ins (j lst / out done x)
  (setq out nil done nil)
  (foreach x lst
    (if (and (not done) (> (acc:severity j) (acc:severity x)))
      (setq out (cons x (cons j out)) done T)
      (setq out (cons x out))))
  (if done (reverse out) (reverse (cons j out))))

(defun acc:offenders (res / out j)
  (setq out nil)
  (foreach j (acc:val "undeclared" res)
    (if (or (>= (acc:j-gap j) acc:*fuzz*)
            (member (acc:j-band j) '("kink" "corner")))
      (setq out (acc:ins j out))))
  out)

;; ---- the verdict -----------------------------------------------------

;; T when the ring fails at the positional level: a gap, a dead
;; segment, a doubled one, a crossing, or a signed turning total that
;; is not one full revolution (which means it doubles back on itself
;; whether or not two chords happen to cross).
(defun acc:turn-ok-p (res)
  (< (abs (- (abs (acc:val "turn-signed" res)) (* 2.0 pi)))
     (acc:rad acc:*close-tol*)))

(defun acc:g0-fault (res)
  (cond
    ((acc:val "gaps" res)
     (strcat (itoa (length (acc:val "gaps" res)))
             " gap(s) in the loop"))
    ((acc:val "zeros" res)
     (strcat (itoa (length (acc:val "zeros" res)))
             " zero-length segment(s)"))
    ((acc:val "dupes" res)
     (strcat (itoa (length (acc:val "dupes" res)))
             " doubled segment(s)"))
    ((acc:val "crosses" res)
     (strcat (itoa (length (acc:val "crosses" res)))
             " crossing segment(s)"))
    ((not (acc:turn-ok-p res))
     (strcat "the loop turns "
             (rtos (acc:deg (acc:val "turn-signed" res)) 2 1)
             " deg, not 360 - it doubles back on itself"))
    (T nil)))

;; The grade is the worst thing found, and it names that thing.  A
;; weighted blend would be easier to compute and impossible to argue
;; with, which is the wrong way round for a drawing check.
(defun acc:grade (res / f)
  (cond
    ((setq f (acc:g0-fault res)) (list "Broken" f))
    ((> (acc:val "kink-n" res) 0)
     (list "Rough" (strcat (itoa (acc:val "kink-n" res))
                           " undeclared kink(s) over "
                           (rtos acc:*kink-tol* 2 1) " deg")))
    ((> (acc:val "corner-n" res) 0)
     (list "Rough" (strcat (itoa (acc:val "corner-n" res))
                           " undeclared corner(s) over "
                           (rtos acc:*corner-ang* 2 1) " deg")))
    ((> (acc:val "micro-share" res) acc:*micro-share*)
     (list "Rough" (strcat (rtos (* 100.0 (acc:val "micro-share" res)) 2 1)
                           "% of the perimeter is in micro-segments")))
    ((> (acc:val "soft-n" res) 0)
     (list "Fair" (strcat (itoa (acc:val "soft-n" res))
                          " soft break(s) - smooth to the eye, not tangent")))
    ((> (acc:val "excess" res) acc:*excess-free*)
     (list "Fair" (strcat "turning excess " (rtos (acc:val "excess" res) 2 2)
                          " - the outline wanders")))
    ((> (acc:val "micro-n" res) 0)
     (list "Fair" (strcat (itoa (acc:val "micro-n" res))
                          " micro-segment(s)")))
    (T (list "Smooth" "tangent at every joint, no defects"))))

;; The index exists to compare two candidate perimeters, not to settle
;; anything on its own: integrity is pass or fail, tangency falls with
;; the total undeclared turn (a whole revolution of kink scores zero -
;; that outline is a polygon), and noise splits between the micro-
;; segment share and the turning excess above what a freeform shape is
;; owed.
(defun acc:index (res / integ tang noise sum j nm nx)
  (setq integ (if (acc:g0-fault res) 0.0 acc:*w-integrity*)
        sum   0.0)
  (foreach j (acc:val "undeclared" res)
    (if (not (= (acc:j-band j) "tangent"))
      (setq sum (+ sum (abs (acc:j-ang j))))))
  (setq tang (* acc:*w-tangency*
                (- 1.0 (min 1.0 (/ sum (* 2.0 pi)))))
        nm   (- 1.0 (min 1.0 (/ (acc:val "micro-share" res)
                                acc:*micro-share*)))
        nx   (- 1.0 (min 1.0 (/ (max 0.0 (- (acc:val "excess" res)
                                            acc:*excess-free*))
                                (- acc:*excess-cap* acc:*excess-free*))))
        noise (* acc:*w-noise* 0.5 (+ nm nx)))
  (list (fix (+ 0.5 (+ integ tang noise)))
        (fix (+ 0.5 integ)) (fix (+ 0.5 tang)) (fix (+ 0.5 noise))))

;; ---- the report ------------------------------------------------------

;; A count and its label, or "none" - a row of zeroes reads as noise in
;; a report someone has to scan.
(defun acc:count-str (n word)
  (if (= n 0) "none" (strcat (itoa n) " " word)))

(defun acc:row (label value)
  (princ (strcat "\n  " (cal:pad label 18) value)))

(defun acc:report (res / g ix j n)
  (princ "\n\n=== ABCURCHECK - perimeter continuity ===")
  (acc:row "Perimeter"
           (strcat (rtos (acc:val "perim" res) 4 4) "  over "
                   (itoa (acc:val "n" res)) " segment(s)"))
  (acc:row "Joints"
           (strcat (itoa (acc:val "n" res)) "  ("
                   (itoa (acc:val "decl-n" res)) " declared, "
                   (itoa (- (acc:val "n" res) (acc:val "decl-n" res)))
                   " measured)"))
  (princ "\n\n  -- the loop itself --")
  (acc:row "Gaps"
           (if (acc:val "gaps" res)
             (strcat (itoa (length (acc:val "gaps" res)))
                     ", worst " (rtos (apply 'max (mapcar 'acc:j-gap
                                                          (acc:val "gaps" res)))
                                      2 4))
             "none"))
  (acc:row "Zero-length" (acc:count-str (length (acc:val "zeros" res))
                                        "segment(s)"))
  (acc:row "Doubled" (acc:count-str (length (acc:val "dupes" res))
                                    "pair(s)"))
  (acc:row "Crossings"
           (if (acc:val "crossrun" res)
             (acc:count-str (length (acc:val "crosses" res)) "pair(s)")
             (strcat "not scanned - over " (itoa acc:*cross-max*)
                     " segments")))
  (acc:row "Turning total"
           (strcat (rtos (acc:deg (acc:val "turn-signed" res)) 2 1)
                   " deg"
                   (if (acc:turn-ok-p res)
                     "  (a simple closed loop turns 360)"
                     "  <-- not one revolution")))
  (princ "\n\n  -- tangency at the joints --")
  (acc:row "Tangent" (strcat (itoa (acc:val "tangent-n" res))
                             "   (within " (rtos acc:*tangent-eps* 2 1)
                             " deg)"))
  (acc:row "Soft breaks" (strcat (itoa (acc:val "soft-n" res))
                                 "   (" (rtos acc:*tangent-eps* 2 1) " - "
                                 (rtos acc:*kink-tol* 2 1) " deg)"))
  (acc:row "Visible kinks"
           (strcat (itoa (acc:val "kink-n" res))
                   "   (" (rtos acc:*kink-tol* 2 1) " - "
                   (rtos acc:*corner-ang* 2 1) " deg)"
                   (if (> (acc:val "kink-n" res) 0)
                     "  <-- these are the problem" "")))
  (acc:row "Corners" (strcat (itoa (acc:val "corner-n" res))
                             "   (over " (rtos acc:*corner-ang* 2 1)
                             " deg, undeclared)"))
  (if (setq j (acc:val "worst" res))
    (acc:row "Worst joint"
             (strcat (rtos (acc:deg (abs (acc:j-ang j))) 2 1)
                     " deg at joint " (itoa (acc:j-idx j))
                     ", " (rtos (acc:j-pos j) 4 4) " along")))
  (princ "\n\n  -- noise --")
  (acc:row "Micro-segments"
           (strcat (itoa (acc:val "micro-n" res)) "   under "
                   (rtos acc:*micro-len* 2 1) "\"  ("
                   (rtos (* 100.0 (acc:val "micro-share" res)) 2 1)
                   "% of the perimeter)"))
  (acc:row "Inflections" (itoa (acc:val "inflect" res)))
  (acc:row "Turning excess" (rtos (acc:val "excess" res) 2 2))
  ;; the offenders, worst first - the list to go and fix
  (setq n 0)
  (foreach j (acc:offenders res)
    (if (= n 0) (princ "\n\n  -- undeclared, worst first --"))
    (setq n (1+ n))
    (princ (strcat "\n    joint " (cal:pad (itoa (acc:j-idx j)) 5)
                   (if (>= (acc:j-gap j) acc:*fuzz*)
                     (strcat "gap " (rtos (acc:j-gap j) 2 4) "  ")
                     "")
                   "kink " (rtos (acc:deg (abs (acc:j-ang j))) 2 1)
                   " deg   at " (rtos (car (acc:j-pt j)) 2 2) ","
                   (rtos (cadr (acc:j-pt j)) 2 2))))
  (foreach j (acc:val "orphans" res)
    (princ (strcat "\n    declared at " (rtos (car j) 2 2) ","
                   (rtos (cadr j) 2 2)
                   " - but the geometry is continuous there")))
  (setq g  (acc:grade res)
        ix (acc:index res))
  (princ (strcat "\n\n  GRADE  " (cal:pad (car g) 10)
                 "set by: " (cadr g)))
  (princ (strcat "\n  Index  " (cal:pad (strcat (itoa (car ix)) " / 100") 10)
                 "(integrity " (itoa (cadr ix))
                 ", tangency " (itoa (caddr ix))
                 ", noise " (itoa (cadddr ix)) ")"))
  (princ)
  g)

;; ---- layers, stamping and marks --------------------------------------

;; Make sure the DASHED linetype exists (pure entmake, no command
;; calls).  Dash lengths are in drawing units - sized for an inch
;; drawing, so the dashes read at pool scale.
(defun acc:ensure-dashed ()
  (if (not (tblsearch "LTYPE" "DASHED"))
    (entmake (list '(0 . "LTYPE") '(100 . "AcDbSymbolTableRecord")
                   '(100 . "AcDbLinetypeTableRecord")
                   '(2 . "DASHED") '(70 . 0)
                   '(3 . "Dashed __ __ __ __ __")
                   '(72 . 65) '(73 . 2) '(40 . 18.0)
                   '(49 . 12.0) '(74 . 0)
                   '(49 . -6.0) '(74 . 0)))))

;; ---- "this one is mine" stamping -------------------------------------
;; ABCURCHECK draws onto layers the drawing may already be using, so it
;; must never clear one wholesale.  Everything it makes carries a piece
;; of extended data naming this command and saying which KIND it is -
;; "MARK" for a finding, which a rescue sweeps away, and "DECL" for a
;; declared discontinuity, which survives so the next run remembers it.

(defun acc:tag (en kind / ed)
  (if en
    (progn
      (regapp "ABCURCHECK")
      (setq ed (entget en))
      (entmod (append ed (list (list -3 (list "ABCURCHECK"
                                              (cons 1000 kind))))))))
  en)

(defun acc:kind (en / x)
  (setq x (assoc -3 (entget en '("ABCURCHECK"))))
  (if x (cdr (assoc 1000 (cdr (assoc "ABCURCHECK" (cdr x)))))))

;; Erase this command's own objects of one KIND on a layer, leaving
;; anything the user drew there alone.  Returns how many went.
(defun acc:purge (name kind / ss i n en)
  (setq n 0)
  (if (tblsearch "LAYER" name)
    (progn
      (setq ss (ssget "_X" (list (cons 8 name))))
      (if ss
        (progn
          (setq i 0)
          (repeat (sslength ss)
            (setq en (ssname ss i))
            (if (or (null kind) (= kind (acc:kind en)))
              (progn (entdel en) (setq n (1+ n))))
            (setq i (1+ i)))))))
  n)

;; The declarations a previous run was told about, read back off the
;; drawing so the user is never asked the same question twice.
(defun acc:read-declared ( / ss i en out ed)
  (setq out nil)
  (if (tblsearch "LAYER" acc:*mark-layer*)
    (progn
      (setq ss (ssget "_X" (list (cons 8 acc:*mark-layer*)))
            i  0)
      (if ss
        (repeat (sslength ss)
          (setq en (ssname ss i)
                ed (entget en))
          (if (and (= "CIRCLE" (cdr (assoc 0 ed)))
                   (= "DECL" (acc:kind en)))
            (setq out (cons (cal:2d (cdr (assoc 10 ed))) out)))
          (setq i (1+ i))))))
  (reverse out))

(defun acc:text (p h str col)
  (entmakex (list '(0 . "TEXT") '(100 . "AcDbEntity")
                  (cons 8 acc:*mark-layer*) (cons 62 col)
                  '(100 . "AcDbText")
                  (cons 10 (list (car p) (cadr p) 0.0))
                  (cons 40 h) (cons 1 str))))

(defun acc:ring (p r col dashed)
  (entmakex (append (list '(0 . "CIRCLE") '(100 . "AcDbEntity")
                          (cons 8 acc:*mark-layer*) (cons 62 col))
                    (if dashed (list '(6 . "DASHED")) nil)
                    (list '(100 . "AcDbCircle")
                          (cons 10 (list (car p) (cadr p) 0.0))
                          (cons 40 r)))))

;; Draw the dashed green ring that says "this break is meant to be
;; here".  Declarations are redrawn from scratch every run, so the
;; drawing and the answer list can never disagree.
(defun acc:draw-declared (declared / p)
  (acc:ensure-dashed)
  (cal:ensure-layer acc:*mark-layer* 3)
  (acc:purge acc:*mark-layer* "DECL")
  (foreach p declared
    (acc:tag (acc:ring p acc:*mark-radius* 3 T) "DECL")))

;; Ring and label every undeclared finding.  Only what fails is marked:
;; a ring on all 47 joints of a normal polyline says nothing, and a
;; drawing nobody can read is a check nobody runs.
(defun acc:draw-marks (res / h col lab n j)
  (cal:ensure-layer acc:*mark-layer* 3)
  (acc:purge acc:*mark-layer* "MARK")
  (setq h (max 4.0 (/ (acc:val "perim" res) 200.0))
        n 0)
  (foreach j (acc:offenders res)
    (setq col (if (or (>= (acc:j-gap j) acc:*fuzz*)
                      (= (acc:j-band j) "kink"))
                1     ; red - a gap, or the 8-45 deg band that hurts
                2)    ; yellow - a corner nobody declared
          lab (if (>= (acc:j-gap j) acc:*fuzz*)
                (strcat "gap " (rtos (acc:j-gap j) 2 3))
                (strcat (rtos (acc:deg (abs (acc:j-ang j))) 2 1) "%%d"))
          n   (1+ n))
    (acc:tag (acc:ring (acc:j-pt j) acc:*mark-radius* col nil) "MARK")
    (acc:tag (acc:text (polar (acc:j-pt j) (acc:rad 45.0)
                              (* 1.4 acc:*mark-radius*))
                       h lab col)
             "MARK"))
  n)

;; ---- the curvature comb ----------------------------------------------
;; A tooth every acc:*comb-step* of run, its length proportional to
;; curvature and its side set by which way the curve turns, with the
;; tips strung into one envelope.  Every tangent break shows as a step
;; in that envelope, every noisy stretch as a fuzzy one, and every
;; inflection as a crossing - the whole judgement in a picture, with no
;; table to read.

(defun acc:comb-tips (segs scale / out s k n i u p len)
  (setq out nil)
  (foreach s segs
    (setq k   (acc:seg-curv s)
          n   (max 1 (cal:ceil (/ (acc:seg-len s) acc:*comb-step*)))
          i   0)
    ;; both ends of every segment are sampled, so a joint contributes
    ;; two tips - and where the curvature jumps, they differ.  That
    ;; visible step is the finding, not an artefact.
    (while (<= i n)
      (setq u   (/ (float i) (float n))
            p   (acc:seg-pt s u)
            len (* k scale)
            out (cons (list p (polar p (+ (acc:seg-tan s u) (/ pi 2.0)) len))
                      out)
            i   (1+ i))))
  (reverse out))

(defun acc:draw-comb (res / segs kmax scale tips pts pr)
  (setq segs (acc:val "segs" res)
        kmax 0.0)
  (foreach pr segs
    (setq kmax (max kmax (abs (acc:seg-curv pr)))))
  (if (< kmax 1.0e-12)
    (progn
      (princ "\n  The comb was not drawn: this perimeter is all straight"
             )
      (princ "\n  lines, so every tooth would have zero length.")
      0)
    (progn
      (cal:ensure-layer acc:*comb-layer* 4)
      (acc:purge acc:*comb-layer* "MARK")
      (setq scale (/ acc:*comb-max* kmax)
            tips  (acc:comb-tips segs scale)
            pts   nil)
      (foreach pr tips
        (setq pts (cons (cadr pr) pts))
        ;; a zero-length tooth on a straight run would be a degenerate
        ;; line, so only real teeth are drawn - the envelope still runs
        ;; through the curve there, which is what flat should look like
        (if (> (cal:dist (car pr) (cadr pr)) 1.0e-6)
          (acc:tag
            (entmakex (list '(0 . "LINE") '(100 . "AcDbEntity")
                            (cons 8 acc:*comb-layer*) '(100 . "AcDbLine")
                            (cons 10 (list (car (car pr)) (cadr (car pr)) 0.0))
                            (cons 11 (list (car (cadr pr))
                                           (cadr (cadr pr)) 0.0))))
            "MARK")))
      (setq pts (reverse pts))
      (acc:tag
        (entmakex (append (list '(0 . "LWPOLYLINE") '(100 . "AcDbEntity")
                                (cons 8 acc:*comb-layer*)
                                '(100 . "AcDbPolyline")
                                (cons 90 (length pts)) '(70 . 1))
                          (mapcar '(lambda (q) (cons 10 q)) pts)))
        "MARK")
      (length pts))))

;; ---- asking ----------------------------------------------------------
;; The bracket is built from the initget string, never written a second
;; time: a click on a bracketed option sends that exact text, so the two
;; can never be allowed to drift (STANDARDS section 1).

;; The bracket is the initget keyword list, built from it and never
;; written a second time: a click on a bracketed option sends that exact
;; text, so any difference between the two makes the click fail
;; (STANDARDS section 1).
(defun acc:ask (msg kws dflt back)
  (cal:askkw msg kws (vl-string-translate " " "/" kws) dflt back))

;; ---- declared discontinuities ----------------------------------------
;; One pick does three jobs: it excuses the joint it lands on, it is
;; checked back against the geometry when it lands on nothing, and what
;; it leaves behind is the undeclared list the report is really about.

(defun acc:declare-loop (declared / done ans p best bd q d)
  (setq done nil)
  (while (not done)
    (princ (strcat "\n  " (itoa (length declared))
                   " discontinuity(ies) declared - breaks that are"
                   " meant to be there."))
    (setq ans (acc:ask "Declared discontinuities" "Add Remove Keep" "Keep" nil))
    (cond
      ((= ans "Add")
       (setq p T)
       (while p
         (setq p (getpoint "\n  Pick a discontinuity (Enter = done): "))
         (if p (setq declared (cons (cal:2d p) declared)))))
      ((= ans "Remove")
       (setq p T)
       (while p
         (setq p (getpoint "\n  Pick the declaration to drop (Enter = done): "))
         (if p
           (progn
             (setq p (cal:2d p) best nil bd nil)
             (foreach q declared
               (setq d (cal:dist p q))
               (if (or (null bd) (< d bd)) (setq bd d best q)))
             (if best
               (setq declared (acc:remove best declared))
               (princ "\n  Nothing declared to drop."))))))
      (T (setq done T))))
  declared)

;; ---- reading the selection -------------------------------------------
;; One polyline carries its own vertex order and is trusted; anything
;; else is loose geometry and gets walked into a ring, gaps and all.

(defun acc:collect (ss / i en all)
  (setq i 0 all nil)
  (repeat (sslength ss)
    (setq en  (ssname ss i)
          all (append all (acc:ent-segs en))
          i   (1+ i)))
  (if (and (= 1 (sslength ss)) (> (length all) 1))
    all
    (acc:chain all)))

(defun acc:select ( / ss)
  (princ "\n\nSelect the closed perimeter - one polyline, or the same")
  (princ "\nshape exploded into lines and arcs.")
  (setq ss (ssget '((0 . "LWPOLYLINE,POLYLINE,LINE,ARC,CIRCLE"))))
  (if (null ss)
    (progn (princ "\nABCURCHECK: nothing selected.") nil)
    ss))

;; ---- housekeeping ----------------------------------------------------

;; ---- the commands ----------------------------------------------------

;; The measurement both commands share: select, read, ask what is meant
;; to be broken, measure, report.  DRAWP nil is the read-only scan -
;; the declarations already in the drawing still count, they just
;; cannot be edited and nothing new is drawn.
(defun acc:run (drawp / ss segs declared res ans again n)
  (if (setq ss (acc:select))
    (progn
      (setq segs (acc:collect ss))
      (if (< (length segs) 2)
        (princ "\nABCURCHECK: that is one segment - there is no joint to measure.")
        (progn
          (setq declared (acc:read-declared)
                again    T)
          (while again
            (setq again nil)
            (if drawp
              (progn
                (setq declared (acc:declare-loop declared))
                (acc:draw-declared declared)))
            (setq res (acc:measure segs declared))
            (acc:report res)
            (if drawp
              (progn
                (setq n (acc:draw-marks res))
                (princ (strcat "\n\n  " (itoa n) " finding(s) ringed on "
                               acc:*mark-layer* "."))
                (setq ans (acc:ask "Draw the curvature comb?"
                                   "Yes No" "Yes" T))
                (cond
                  ((eq ans 'CAL-BACK) (setq again T))
                  ((= ans "Yes")
                   (setq n (acc:draw-comb res))
                   (if (> n 0)
                     (princ (strcat "\n  Comb drawn on " acc:*comb-layer*
                                    " - " (itoa n)
                                    " teeth; the envelope steps where the"
                                    " curve breaks."))))))))))))
  (princ))

(defun c:ABCURCHECK ( / *error* undo-open)
  (defun *error* (msg)
    ;; user settings come back FIRST so nothing below can skip them
    (cal:sysrestore)
    (if undo-open (command "_.UNDO" "_End"))
    (if (and msg (not (wcmatch (strcase msg)
                               "*BREAK*,*CANCEL*,*QUIT*,*EXIT*")))
      (princ (strcat "\nABCURCHECK error: " msg)))
    (princ))
  (cal:syssave acc:*sysvars*)
  (setvar "CMDECHO" 0)
  (command "_.UNDO" "_Begin")
  (setq undo-open T)
  (acc:run T)
  (command "_.UNDO" "_End")
  (setq undo-open nil)
  (cal:sysrestore)
  (princ))

(defun c:ABCURCHECKSCAN ( / *error* undo-open)
  (defun *error* (msg)
    (cal:sysrestore)
    (if undo-open (command "_.UNDO" "_End"))
    (if (and msg (not (wcmatch (strcase msg)
                               "*BREAK*,*CANCEL*,*QUIT*,*EXIT*")))
      (princ (strcat "\nABCURCHECKSCAN error: " msg)))
    (princ))
  (cal:syssave acc:*sysvars*)
  (setvar "CMDECHO" 0)
  (command "_.UNDO" "_Begin")
  (setq undo-open T)
  (acc:run nil)
  (command "_.UNDO" "_End")
  (setq undo-open nil)
  (cal:sysrestore)
  (princ))

;; Sweep the marks away again.  Findings and the comb go; the
;; declarations stay unless asked for by name, because they are the
;; user's answers and re-picking them is the one thing this command
;; should never make anyone do twice.
(defun c:ABCURCHECKRESCUE ( / *error* undo-open ans n)
  (defun *error* (msg)
    (cal:sysrestore)
    (if undo-open (command "_.UNDO" "_End"))
    (if (and msg (not (wcmatch (strcase msg)
                               "*BREAK*,*CANCEL*,*QUIT*,*EXIT*")))
      (princ (strcat "\nABCURCHECKRESCUE error: " msg)))
    (princ))
  (cal:syssave acc:*sysvars*)
  (setvar "CMDECHO" 0)
  (command "_.UNDO" "_Begin")
  (setq undo-open T)
  (setq ans (acc:ask "Erase which of ABCURCHECK's objects?"
                     "Marks All" "Marks" nil)
        n   (+ (acc:purge acc:*mark-layer* "MARK")
               (acc:purge acc:*comb-layer* "MARK")))
  (if (= ans "All")
    (setq n (+ n (acc:purge acc:*mark-layer* "DECL"))))
  (princ (strcat "\nABCURCHECKRESCUE: " (itoa n)
                 " of this command's own object(s) erased"
                 (if (= ans "All") "" ", declarations kept") "."))
  (command "_.UNDO" "_End")
  (setq undo-open nil)
  (cal:sysrestore)
  (princ))

(defun c:ABCURCHECKVER ()
  (princ (strcat "\nABCURCHECK " *abcurcheck-version* " loaded."))
  (princ))

(princ (strcat "\nABCURCHECK " *abcurcheck-version*
               " loaded.  Type ABCURCHECK to run."))
(princ)


;;; ======================================================================
;;; >>> CABHD.lsp
;;; ======================================================================

;;; ===================================================================
;;; CABHD.LSP  --  Fit a pool perimeter through PART of a survey
;;; -------------------------------------------------------------------
;;; For AutoCAD 2018 and later (plain AutoLISP, no external libraries).
;;;
;;; Command:  CABHD - fit the perimeter, and only the perimeter
;;;
;;; SHARED BUILD: requires CALOFIN-LIB.lsp (load via CALOFIN-LOADER.lsp).
;;; Generic helpers live there under cal: - see STANDARDS.md.
;;;
;;; CABHD is ABHD's perimeter half, with one rule added and one whole
;;; half left out.
;;;
;;;   ADDED - THE POINT CUTOFF.  A survey run rarely stops where the
;;;     pool edge does.  The shots that trace the edge come first, and
;;;     the rest - steps, benches, deck, depth shots, the neighbour's
;;;     fence - carry on in the same numbering, so a 137-point survey
;;;     may hold a 20-point perimeter.  After the selection CABHD asks
;;;     how far up the numbers the edge runs, and everything past that
;;;     answer is out of the perimeter ENTIRELY: not ordered into the
;;;     loop, not fitted, not counted against the miss allowance, and
;;;     never reported as a point the line failed to hold.  Select the
;;;     whole survey and say where the pool stops.
;;;
;;;   LEFT OUT - THE POOL BOTTOM.  ABHD offers to draw the floor once a
;;;     perimeter is kept: shallow and deep breaks, the hopper, the
;;;     slope lines and their dimensions.  CABHD does none of it and
;;;     never asks.  It ends with the kept perimeter and its hit
;;;     report.  For the floor, run ABHD or ADAB.
;;;
;;; Everything else is ABHD's, rule for rule, so a fit from either
;;; command is the same fit.  What follows describes those rules.
;;;
;;; The user window-selects an area containing:
;;;   * On layer "POOL"   : (optional) a closed perimeter drawn as ONE
;;;                         closed polyline OR an exploded set of
;;;                         LINEs/ARCs.
;;;   * On layer "POINTS" : POINT entities surveyed on the real pool
;;;                         edge.  Survey points saved as "ab_pt" block
;;;                         inserts count on any layer, and the number
;;;                         attribute they carry is what the cutoff
;;;                         reads.
;;;
;;; THE CUTOFF, EXACTLY: the prompt takes the LAST point number that
;;; belongs to the pool edge - type it, or Pick that point in the
;;; drawing and CABHD reads its number off the block.  Enter (or All)
;;; keeps every point, which is ABHD's behaviour.  The number is read
;;; from the point's label as the first run of digits in it, so "17",
;;; "P17" and "17A" all read as seventeen; a point whose label holds no
;;; digit at all falls back to its place in the selection, and CABHD
;;; says so before asking.  A cutoff that would starve the fit is
;;; refused and re-asked, and it can be moved (either way) at a Redo -
;;; setting it too low costs one prompt, not a run.  A straight wall,
;;; sharp corner or held point declared on a point the cutoff drops is
;;; dropped with it and said so, rather than being quietly snapped onto
;;; some other point.
;;;
;;; TWO MODES, chosen automatically from the selection:
;;;   * GUIDED  - the selection contains POOL geometry: the drawn
;;;               shape is used as the guide and re-fitted through the
;;;               points (described below).
;;;   * POINTS-ONLY - the selection contains no POOL geometry: the
;;;               program orders the points into a closed loop by
;;;               itself (nearest-neighbour tour + 2-opt uncrossing)
;;;               and covers them with as FEW long, overarching ARCS
;;;               as possible - each arc is grown to take in as many
;;;               consecutive points as it can hold.  No straight
;;;               lines are drawn (organic shapes have none); the only
;;;               exception is a stretch between two sharp corners
;;;               with no points in between, where an arc would be
;;;               pure invention.
;;;
;;; ON THE POINTS FIRST: every arc endpoint sits ON a survey point,
;;; and each arc is chosen so its MIDDLE passes exactly through one of
;;; its interior points too (a true 3-point arc) whenever such an arc
;;; holds the span.  Arcs that float between the points are a last
;;; resort and must cover at least 2 more points to be chosen - they
;;; should be the rare exception (roughly 1 arc in 10), not the rule.
;;;
;;; NEAR-TANGENT SMOOTHNESS: at every joint the new arc must start
;;; within *CAB-TANG-TOL* (8 degrees) of the previous arc's end
;;; tangent - close enough to look smooth, loose enough that the
;;; points stay in charge.  Sharp corners (over *CAB-CORNER-ANG*) stay
;;; free kinks; the closing seam is held to the same window (the fit
;;; is re-run once with a seeded start tangent when the seam comes
;;; out worse).
;;;
;;; NICE RADII: arc radii are snapped to friendly increments before a
;;; free ("weird") number is accepted - whole feet first, then half
;;; feet, then whole inches (*CAB-NICE-RADII*, drawing units = inches).
;;; The points outrank pretty radii: a snap may move covered points at
;;; most *CAB-SNAP-EPS* beyond where they already sat and may never
;;; pull an arc off its anchor point; endpoints never move.
;;;
;;; THE MISS ALLOWANCE: the perimeter does not have to thread every
;;; point exactly.  A share of the points - asked per run, standard
;;; *CAB-MISS-PCT* (15%), rounded UP to the nearest whole point - may
;;; sit off the result by up to the max distance (default 1 unit =
;;; about an inch, capped at *CAB-TOL-MAX*); every other point stays on
;;; it (within *CAB-ON-EPS*).  That slack is spent where it buys the
;;; most: longer arcs, fewer curves, nicer radii.  It is a share of the
;;; points the CUTOFF KEPT - the ones it dropped buy no slack, since
;;; the line was never asked to go near them.
;;;
;;; DECLARED STRAIGHT WALLS: the user may declare dead-straight walls
;;; up front by picking their two end points; each is marked with a
;;; dashed line on *CAB-WALL-LAYER* and comes out of the points-built
;;; fit as a straight LINE between exactly those two survey points -
;;; arcs never swallow or cross a declared wall.
;;;
;;; HELD POINTS: the user may also declare points that must be held
;;; ABSOLUTELY - control shots, tie-ins, anything surveyed as an
;;; exact position.  A held point is never buried inside a span, so
;;; every span ends ON it and the fitted line passes through it
;;; exactly, in every candidate; it costs nothing from the miss
;;; allowance and the tangency window still applies at its joint (it
;;; is not a corner).  In guided mode the drawn shape wins, as with
;;; declared walls - held points steer the points-built fit - and the
;;; report flags any held point the kept fit did not land on.
;;;
;;; THE CURVE CAP: the command also asks for a maximum number of
;;; curves ("None" = unlimited).  When a fit needs more, the whole
;;; loop is refitted with a progressively relaxed tolerance until the
;;; cap holds - merging arcs would break their tangency, so the chain
;;; is rebuilt instead and stays smooth.  The cap wins over the
;;; tolerance; whatever error it forces is shown in the hit report.
;;; The cap binds in EVERY mode: a guided run whose drawn perimeter
;;; needs more curves falls back to fitting from the points (the
;;; drawn shape still orders them), and an unreachably small cap
;;; returns the fewest-curves fit found - never the full-size one.
;;;
;;; THE THREE CANDIDATES: how much curve to spend on how much accuracy
;;; is a judgement, not a setting, so all three answers are drawn and
;;; the user points at one (*CAB-COMPARE*).  Fit 1 is the accurate end:
;;; it fits to *CAB-TIGHT-TOL*, writes off no point at all, and obeys
;;; neither the typed distance nor the curve cap - the most curves for
;;; the least error there is.  Fit 2 is the settings exactly as typed,
;;; cap included.  Fit 3 is the economical end: the same typed
;;; distance, but with the miss allowance and its per-span fair share
;;; lifted, so arcs run as long as that distance allows - the fewest
;;; curves that still hold it.  All three are then MEASURED against
;;; the typed distance, so the table compares like for like.
;;;
;;; The command rebuilds the perimeter as a single closed LWPOLYLINE
;;; (lines + arcs only, no splines); the candidates preview on layer
;;; "POOL-FIT" and the kept one moves onto the POOL layer:
;;;   * Every polyline vertex is snapped to the nearest surveyed point
;;;     within the tolerance (default 1 unit = 1 inch), so corners land
;;;     exactly on points whenever one is close enough.
;;;   * Every curved (arc/bulge) segment is re-fitted so that the arc
;;;     passes through the surveyed points lying along it.  A single
;;;     replacement arc is tried first (the best of the exact 3-point
;;;     arcs through the two snapped endpoints and the points, plus
;;;     their average), with its radius snapped to a nice increment
;;;     when possible; if it keeps every point within the tolerance
;;;     and the miss allowance can absorb the off ones, that ONE arc
;;;     is kept.  Only when that fails is the segment SUBDIVIDED into
;;;     a tangent-continuous chain of arcs through every point.
;;;   * Straight segments the user drew are trusted and kept straight
;;;     (only their endpoints snap to points); where the user found a
;;;     straight wall, the result has a straight wall.
;;;   * A point that turns more than *CAB-CORNER-ANG* (45 deg) is a
;;;     sharp corner: it can start or end a span but is never buried
;;;     inside one, so polygonal shapes keep their corners as lines.
;;; Everything is fitted on the 2D plane - Z coordinates are ignored.
;;; Every segment shares its endpoints with its neighbours, so the
;;; result stays closed.
;;;
;;; A hit report is printed: how many points the new perimeter passes
;;; through exactly, how many are within tolerance, how many missed.
;;; The points the cutoff left out are in none of those counts.
;;;
;;; WHEN A CANDIDATE WILL NOT DRAW: a fit can come out too degenerate
;;; for AutoCAD to accept - fewer than two segments is no closed
;;; outline, and AutoCAD answers entmake with nil rather than an error.
;;; The tight fit is the likeliest, since it must thread every point at
;;; *CAB-TIGHT-TOL* with no miss allowance and no curve cap, and a
;;; survey read whole (Enter at the cutoff) is where it happens.  One
;;; candidate failing costs only that candidate: the table marks it
;;; "would not draw", Enter defaults to one that did, and picking the
;;; missing one says so.  Only when NONE of them draws is that a dead
;;; end, and it says which cutoff to try.  Nothing here is ever silent:
;;; every run signs off naming the last step it reached, and the error
;;; handler names that step for cancels too.
;;;
;;; REDO: at the choose prompt, Redo refits without leaving the
;;; command.  Points can be omitted by clicking them (clicking a ringed
;;; one puts it back), the cutoff can move either way, straight walls,
;;; sharp corners and held points can be added or removed, and the
;;; three numbers are asked again with Enter keeping each.  The omit
;;; list picks out strays one at a time; the cutoff draws a line across
;;; the whole survey at once.  Either way, a declaration whose point
;;; has left the fit leaves with it.
;;;
;;; Everything CABHD draws to help you decide - dashed markers, the
;;; three candidate outlines, their labels - is stamped as its own and
;;; sweeps itself when the command ends, ESC included.  ABHD's stamped
;;; work is left alone, and never read back as guide geometry.
;;; ===================================================================

;; ---- configuration -------------------------------------------------
(setq *cabhd-version* "v1.2")       ; announced on load; release_lisp.py
                                    ; stamps the dated twin in releases/
                                    ; from it (vN.N -> CABHD_MMDDYY_
                                    ; REVNN), so the filename and the
                                    ; banner can never disagree - bump
                                    ; it with every revision
(setq *CAB-POOL-LAYER*   "POOL")     ; layer holding the drawn perimeter
(setq *CAB-POINT-LAYER*  "POINTS")   ; layer holding the survey points
(setq *CAB-POINT-BLOCK*  "ab_pt")    ; block name whose INSERTs mark survey
                                    ; points; the block's insertion point
                                    ; is taken as the point location
(setq *CAB-OUT-LAYER*    "POOL-FIT") ; layer the fitted polyline goes on
(setq *CAB-MISS-LAYER*   "FGStep")   ; layer the "could not hold this
                                    ; point" circles and their list go
                                    ; on.  This may well be a layer you
                                    ; already use, so CABHD stamps the
                                    ; objects it makes and only ever
                                    ; erases its own (see cab:tag-mine)
(setq *CAB-MISS-RADIUS*  4.0)        ; radius of those circles (4 inches)
(setq *CAB-PT-TAG*       "number")   ; attribute tag on the point block
                                    ; holding the surveyed point number,
                                    ; used to label it as "Pt.17"
(setq *CAB-WALL-LAYER*   "POOL-WALLS"); layer the dashed markers for
                                    ; user-declared straight walls go on
(setq *CAB-TOL-MAX*      2.0)        ; hard ceiling on the max-distance
                                    ; prompt (2 inches): further than
                                    ; that and the line is no longer a
                                    ; trace of the points
(setq *CAB-COMPARE*                  ; the three candidate fits offered:
  '(("tight" 1 "red"    "most curves - least error")
    ("asked" 2 "yellow" "as asked")
    ("few"   4 "cyan"   "fewest curves - still within the distance")))
                                    ; (mode, AutoCAD colour, colour name,
                                    ; description).  The three ask three
                                    ; different questions of the same
                                    ; points, so what is being chosen is
                                    ; an aim, not a tolerance:
                                    ;   "tight" - accuracy above all: it
                                    ;     fits to *CAB-TIGHT-TOL*, lets no
                                    ;     point miss and ignores both the
                                    ;     distance typed at step 2 and
                                    ;     the curve cap, so it draws the
                                    ;     most curves and the least error
                                    ;   "asked" - the settings exactly as
                                    ;     typed, curve cap and all
                                    ;   "few" - the fewest curves that
                                    ;     still hold every point within
                                    ;     the distance typed: the same
                                    ;     distance, but with the miss
                                    ;     allowance lifted so arcs run as
                                    ;     long as that distance permits
                                    ; Colours and wording are yours to
                                    ; edit; the three mode names are not
(setq *CAB-TIGHT-TOL*    0.01)       ; the "tight" candidate's accuracy
                                    ; target (units) - what it fits to
                                    ; instead of the distance typed at
                                    ; step 2, or that distance when it
                                    ; happens to be tighter still
(setq *CAB-EXACT-EPS*    0.001)      ; "exactly on" threshold (units)
(setq *CAB-FIT-EPS*      0.01)       ; if a single arc misses any of its
                                    ; points by more than this, split it
                                    ; into several arcs that hit exactly
(setq *CAB-ON-EPS*       0.25)       ; a point within this of the result
                                    ; counts as ON it; only points off by
                                    ; more than this eat into the miss
                                    ; allowance below.  Calibrated from a
                                    ; hand-drawn reference trace: ~87% of
                                    ; its points sat within a quarter inch
(setq *CAB-MISS-PCT*     0.15)       ; share of the points (rounded UP to
                                    ; a whole point) that may sit off the
                                    ; result by up to the tolerance
                                    ; (about an inch by default) - this
                                    ; slack is what buys longer spans and
                                    ; fewer curves
(setq *CAB-CORNER-ANG*   (/ pi 4.0)) ; a point that turns more than this
                                    ; (45 deg) is a sharp corner: it may
                                    ; start or end a span but never gets
                                    ; buried inside one, so polygonal
                                    ; shapes keep their corners.  Sample
                                    ; real tight curves with at least ~3
                                    ; points per quarter turn to stay
                                    ; under it.
(setq *CAB-NICE-RADII* '(12.0 6.0 1.0)) ; preferred arc-radius increments,
                                    ; tried in order: whole feet, half
                                    ; feet, whole inches (drawing units
                                    ; are inches).  A radius is snapped
                                    ; to the first increment whose arc
                                    ; still holds the points; only when
                                    ; none does is the free-fit ("weird")
                                    ; radius kept.
(setq *CAB-TANG-TOL* (/ pi 22.5))    ; wiggle room from perfect
                                    ; tangency at each joint between two
                                    ; arcs (8 degrees).  Being ON the
                                    ; points matters more than perfect
                                    ; tangency; this slack is what lets
                                    ; every arc endpoint sit on a survey
                                    ; point and radii stay nice.
                                    ; Calibrated from a hand-drawn
                                    ; reference trace whose joints ran up
                                    ; to 7.9 deg (median 3 deg); tighter
                                    ; values shatter the fit into many
                                    ; short arcs (5 deg is workable,
                                    ; 6 deg and below is not).
(setq *CAB-TANG-STEPS* '(1.0 1.25 1.5)) ; when nothing fits inside the
                                    ; tangent window, stretch it by
                                    ; these multiples in turn rather
                                    ; than abandon it; if even the
                                    ; widest finds nothing, a one-point
                                    ; stub takes over, and that
                                    ; continues the previous tangent
                                    ; exactly.  Smoothness is worth
                                    ; more than one extra arc, so keep
                                    ; the last step small: dropping the
                                    ; window outright allowed joints to
                                    ; kink three times the limit.
(setq *CAB-SNAP-EPS*     0.02)       ; a nice-radius snap may move the
                                    ; covered points at most this far
                                    ; beyond where they already sat, and
                                    ; it may never pull an arc off its
                                    ; anchor point entirely - the points
                                    ; outrank pretty radii
(setq *CAB-CHAIN-FUZZ*   1.0e-4)     ; endpoint-matching fuzz for
                                    ; chaining exploded segments
(if (null *CAB-TOL*) (setq *CAB-TOL* 1.0)) ; default tolerance, 1 inch
;; *CAB-MAX-ARCS* : cap on the number of curved segments in the output;
;; nil = no cap.  The command prompts for it (Enter keeps the current
;; value, "None" removes the cap) and remembers it for the session,
;; like *CAB-TOL*.

;; ---- circle / arc geometry -----------------------------------------

;; Circumcenter of three points, nil when (nearly) collinear.
(defun cab:circumcenter (pa pb pc / x1 y1 x2 y2 x3 y3 d s1 s2 s3)
  (setq x1 (car pa) y1 (cadr pa)
        x2 (car pb) y2 (cadr pb)
        x3 (car pc) y3 (cadr pc)
        d  (* 2.0 (+ (* x1 (- y2 y3)) (* x2 (- y3 y1)) (* x3 (- y1 y2)))))
  (if (< (abs d) 1.0e-10)
    nil
    (progn
      (setq s1 (+ (* x1 x1) (* y1 y1))
            s2 (+ (* x2 x2) (* y2 y2))
            s3 (+ (* x3 x3) (* y3 y3)))
      (list (/ (+ (* s1 (- y2 y3)) (* s2 (- y3 y1)) (* s3 (- y1 y2))) d)
            (/ (+ (* s1 (- x3 x2)) (* s2 (- x1 x3)) (* s3 (- x2 x1))) d)))))

;; Bulge of the unique circular arc that starts at P1, ends at P2 and
;; passes through Q.  0.0 when the three points are collinear, and
;; also when the arc would be a (near) full circle - P1 and P2 lying
;; at the same angle from the center makes the sweep 0 or 2*pi, which
;; no single bulge can express.  Nearly-collinear noisy survey points
;; can produce exactly that, so both ends of the range are guarded.
(defun cab:bulge-3pt (p1 q p2 / c a1 a2 aq dccw dq)
  (setq p1 (cal:2d p1) q (cal:2d q) p2 (cal:2d p2)
        c  (cab:circumcenter p1 q p2))
  (if (null c)
    0.0
    (progn
      (setq a1   (angle c p1)
            a2   (angle c p2)
            aq   (angle c q)
            dccw (cal:angnorm (- a2 a1))
            dq   (cal:angnorm (- aq a1)))
      (cond
        ((< dccw 1.0e-9) 0.0)                       ; degenerate sweep
        ((> dccw (- (* 2.0 pi) 1.0e-9)) 0.0)        ; degenerate sweep
        ((<= dq dccw) (cal:tan (/ dccw 4.0)))        ; CCW arc through Q
        (T (- (cal:tan (/ (- (* 2.0 pi) dccw) 4.0)))))))) ; CW through Q

;; Arc geometry of a bulged segment: (center radius angStart angEnd)
;; where the arc runs CCW from angStart to angEnd when bulge > 0 and
;; CW when bulge < 0.  nil for a straight segment.
(defun cab:arc-geom (p1 p2 b / ch dir apex c)
  (if (< (abs b) 1.0e-9)
    nil
    (progn
      (setq p1   (cal:2d p1)
            p2   (cal:2d p2)
            ch   (cal:dist p1 p2)
            dir  (cal:v* (cal:v- p2 p1) (/ 1.0 ch))
            ;; sagitta = (chord/2)*bulge; a positive (CCW) bulge apex
            ;; lies to the RIGHT of the p1->p2 chord direction
            apex (cal:v+ (cal:mid p1 p2)
                         (cal:v* (cal:perp dir) (* -0.5 ch b)))
            c    (cab:circumcenter p1 apex p2))
      (if (null c)
        nil
        (list c (cal:dist c p1) (angle c p1) (angle c p2))))))

;; Distance from point P to segment (p1 p2 bulge).
(defun cab:seg-dist (p seg / p1 p2 b v w len2 t2 g c r a1 a2 ap sweep rel)
  (setq p  (cal:2d p)
        p1 (cal:2d (car seg))
        p2 (cal:2d (cadr seg))
        b  (caddr seg))
  (if (< (abs b) 1.0e-9)
    ;; straight: project onto the segment, clamp to its ends
    (progn
      (setq v    (cal:v- p2 p1)
            w    (cal:v- p p1)
            len2 (cal:dot v v))
      (if (< len2 1.0e-20)
        (cal:dist p p1)
        (progn
          (setq t2 (/ (cal:dot w v) len2))
          (if (< t2 0.0) (setq t2 0.0))
          (if (> t2 1.0) (setq t2 1.0))
          (cal:dist p (cal:v+ p1 (cal:v* v t2))))))
    ;; arc: radial distance when P falls inside the sweep, else the
    ;; nearer endpoint
    (progn
      (setq g (cab:arc-geom p1 p2 b))
      (if (null g)
        (min (cal:dist p p1) (cal:dist p p2))
        (progn
          (setq c  (car g)  r (cadr g)
                a1 (caddr g) a2 (cadddr g)
                ap (angle c p))
          (if (> b 0.0)
            (setq sweep (cal:angnorm (- a2 a1)) rel (cal:angnorm (- ap a1)))
            (setq sweep (cal:angnorm (- a1 a2)) rel (cal:angnorm (- ap a2))))
          (if (<= rel sweep)
            (abs (- (cal:dist p c) r))
            (min (cal:dist p p1) (cal:dist p p2))))))))

;; Bulge of the arc that starts at A with tangent direction TANG
;; (radians) and ends at B.  The angle between a chord and the tangent
;; at its end is half the included angle, so delta = 2*phi.
(defun cab:tangent-bulge (a tang b / phi)
  (setq phi (cal:signed-dang tang (angle (cal:2d a) (cal:2d b))))
  (cal:tan (/ phi 2.0)))

;; Tangent direction (radians) at the END of the arc from A to B with
;; the given bulge: chord direction + delta/2, delta = 4*atan(bulge).
(defun cab:end-tangent (a b bulge)
  (+ (angle (cal:2d a) (cal:2d b)) (* 2.0 (atan bulge))))

;; Position of P along segment (p1 p2 bulge) as a 0..1 parameter,
;; used only to ORDER candidate points along the segment.
(defun cab:seg-param (p seg / p1 p2 b v w len2 g c a1 a2 ap sweep rel)
  (setq p  (cal:2d p)
        p1 (cal:2d (car seg))
        p2 (cal:2d (cadr seg))
        b  (caddr seg))
  (if (< (abs b) 1.0e-9)
    (progn
      (setq v (cal:v- p2 p1) w (cal:v- p p1) len2 (cal:dot v v))
      (if (< len2 1.0e-20) 0.0 (/ (cal:dot w v) len2)))
    (progn
      (setq g (cab:arc-geom p1 p2 b))
      (if (null g)
        0.0
        (progn
          (setq c (car g) a1 (caddr g) a2 (cadddr g) ap (angle c p))
          (if (> b 0.0)
            (setq sweep (cal:angnorm (- a2 a1))
                  rel   (cal:angnorm (- ap a1)))
            (setq sweep (cal:angnorm (- a1 a2))
                  rel   (- (cal:angnorm (- a1 a2))
                           (cal:angnorm (- ap a2)))))
          (if (< sweep 1.0e-10) 0.0 (/ rel sweep)))))))

;; ---- entity -> segment extraction ----------------------------------
;; A segment is (startPt endPt bulge), 2D points.

(defun cab:lw-segs (ed / pts bls item segs n closed)
  ;; collect (10) vertices and their (42) bulges, in order
  (setq pts nil bls nil)
  (foreach item ed
    (cond
      ((= (car item) 10)
       (setq pts (cons (cal:2d (cdr item)) pts)
             bls (cons 0.0 bls)))
      ((and (= (car item) 42) bls)
       (setq bls (cons (cdr item) (cdr bls))))))
  (setq pts (reverse pts) bls (reverse bls)
        closed (= 1 (logand 1 (cdr (assoc 70 ed))))
        segs nil n 0)
  (while (< n (1- (length pts)))
    (setq segs (cons (list (nth n pts) (nth (1+ n) pts) (nth n bls)) segs)
          n    (1+ n)))
  (if (and (> (length pts) 2)
           (or closed
               (< (cal:dist (last pts) (car pts)) *CAB-CHAIN-FUZZ*)))
    (if (>= (cal:dist (last pts) (car pts)) *CAB-CHAIN-FUZZ*)
      (setq segs (cons (list (last pts) (car pts) (last bls)) segs))))
  (reverse segs))

(defun cab:pl-segs (en / ed sub pts bls segs n closed)
  ;; heavy (old-style) 2D POLYLINE: walk its VERTEX sub-entities
  (setq ed (entget en)
        closed (= 1 (logand 1 (cdr (assoc 70 ed))))
        pts nil bls nil
        sub (entnext en))
  (while (and sub (= "VERTEX" (cdr (assoc 0 (setq ed (entget sub))))))
    ;; skip spline/fit control vertices (flag bits 1 and 16)
    (if (= 0 (logand 17 (cond ((cdr (assoc 70 ed))) (0))))
      (setq pts (cons (cal:2d (cdr (assoc 10 ed))) pts)
            bls (cons (cond ((cdr (assoc 42 ed))) (0.0)) bls)))
    (setq sub (entnext sub)))
  (setq pts (reverse pts) bls (reverse bls) segs nil n 0)
  (while (< n (1- (length pts)))
    (setq segs (cons (list (nth n pts) (nth (1+ n) pts) (nth n bls)) segs)
          n    (1+ n)))
  (if (and closed (> (length pts) 2))
    (setq segs (cons (list (last pts) (car pts) (last bls)) segs)))
  (reverse segs))

(defun cab:ent-segs (en / ed typ c r a1 a2 delta)
  (setq ed  (entget en)
        typ (cdr (assoc 0 ed)))
  (cond
    ((= typ "LINE")
     (list (list (cal:2d (cdr (assoc 10 ed)))
                 (cal:2d (cdr (assoc 11 ed)))
                 0.0)))
    ((= typ "ARC")
     (setq c  (cal:2d (cdr (assoc 10 ed)))
           r  (cdr (assoc 40 ed))
           a1 (cdr (assoc 50 ed))
           a2 (cdr (assoc 51 ed))
           delta (cal:angnorm (- a2 a1)))
     (if (< delta 1.0e-10) (setq delta (* 2.0 pi)))
     ;; a full-circle arc cannot be one bulged segment (its bulge is
     ;; infinite): hand back two semicircles instead
     (if (> delta (- (* 2.0 pi) 1.0e-9))
       (list (list (polar c a1 r) (polar c (+ a1 pi) r) 1.0)
             (list (polar c (+ a1 pi) r) (polar c a1 r) 1.0))
       (list (list (polar c a1 r) (polar c a2 r) (cal:tan (/ delta 4.0))))))
    ;; a CIRCLE is a legitimate pool perimeter (round spa): two
    ;; semicircles, so the chaining and fitting code sees a normal
    ;; closed loop instead of reporting a gap
    ((= typ "CIRCLE")
     (setq c (cal:2d (cdr (assoc 10 ed)))
           r (cdr (assoc 40 ed)))
     (list (list (polar c 0.0 r) (polar c pi r) 1.0)
           (list (polar c pi r) (polar c 0.0 r) 1.0)))
    ((= typ "LWPOLYLINE") (cab:lw-segs ed))
    ((= typ "POLYLINE") (cab:pl-segs en))
    (T nil)))

;; ---- chain loose segments into one closed loop ----------------------
;; Returns the ordered segment list, or nil (with a message) on failure.
(defun cab:chain (segs / loop start end found s rest)
  (if (null segs)
    nil
    (progn
      (setq loop  (list (car segs))
            start (car (car segs))
            end   (cadr (car segs))
            segs  (cdr segs))
      (while (and segs
                  (>= (cal:dist end start) *CAB-CHAIN-FUZZ*))
        (setq found nil rest nil)
        (foreach s segs
          (cond
            (found (setq rest (cons s rest)))
            ((< (cal:dist end (car s)) *CAB-CHAIN-FUZZ*)
             (setq found s))
            ((< (cal:dist end (cadr s)) *CAB-CHAIN-FUZZ*)
             ;; reverse the segment: swap ends, negate the bulge
             (setq found (list (cadr s) (car s) (- (caddr s)))))
            (T (setq rest (cons s rest)))))
        (if found
          (setq loop (cons found loop)
                end  (cadr found)
                segs (reverse rest))
          (setq segs nil end nil)))  ; gap -> bail out
      (cond
        ((null end)
         (princ "\nCABHD: gap in the POOL perimeter - could not close the loop.")
         nil)
        ((>= (cal:dist end start) *CAB-CHAIN-FUZZ*)
         (princ "\nCABHD: the POOL perimeter does not close.")
         nil)
        (T
         (if segs
           (princ (strcat "\nCABHD: warning - "
                          (itoa (length segs))
                          " POOL segment(s) not part of the closed loop were ignored.")))
         (reverse loop))))))

;; ---- span fitting helpers --------------------------------------------
;; A "span" is one candidate segment from A to B judged against QS, the
;; survey points it is supposed to represent.

;; Worst distance from any of QS to the segment (A B bulge).
(defun cab:span-dev (a b bul qs / seg mx d q)
  (setq seg (list a b bul) mx 0.0)
  (foreach q qs
    (setq d (cab:seg-dist q seg))
    (if (> d mx) (setq mx d)))
  mx)

;; The miss percentage in force for the current run: the command binds
;; cab-miss-pct from the user's answer; Enter keeps the standard value.
(defun cab:misspct ()
  (if cab-miss-pct cab-miss-pct *CAB-MISS-PCT*))

;; The "on the shape" threshold in force for the current run.  It
;; scales with the tolerance (a quarter of it, never below
;; *CAB-ON-EPS*): if the user accepts 4 inches of error, a point 1 inch
;; off is plainly still ON the shape, and counting it as a miss would
;; burn the whole allowance on the first span and starve the rest of
;; the loop into single-point stubs.  cab-on-eps is bound per run by
;; the command and per pass by cab:fit-pass.
(defun cab:oneps ()
  (if cab-on-eps cab-on-eps *CAB-ON-EPS*))

;; How many of QS sit farther than the on-the-shape threshold from the
;; segment - the points that would eat into the miss allowance.
(defun cab:span-misses (a b bul qs / seg c q lim)
  (setq seg (list a b bul) c 0 lim (cab:oneps))
  (foreach q qs
    (if (> (cab:seg-dist q seg) lim) (setq c (1+ c))))
  c)

;; Best single arc from A to B over the points QS: candidate bulges are
;; the exact 3-point fits through a few of the points plus the average
;; of them all; the one with the smallest worst-case deviation wins.
;; Returns (bulge . maxdev).
(defun cab:span-arc (a b qs / bls sum bl m cands best bd d)
  (setq bls (mapcar '(lambda (q) (cab:bulge-3pt a q b)) qs)
        sum 0.0
        m   (length qs))
  (foreach bl bls (setq sum (+ sum bl)))
  (setq cands (list (/ sum m) (nth (/ m 2) bls)))
  (if (>= m 4)
    (setq cands (append cands (list (nth (/ m 4) bls)
                                    (nth (/ (* 3 m) 4) bls)))))
  (setq best nil bd nil)
  (foreach bl cands
    (setq d (cab:span-dev a b bl qs))
    (if (or (null bd) (< d bd)) (setq best bl bd d)))
  (cons best bd))

;; Radius of the arc (A B bulge); nil for a straight segment.
(defun cab:bulge-radius (a b bl / h)
  (if (< (abs bl) 1.0e-9)
    nil
    (progn
      (setq h (/ (cal:dist a b) 2.0))
      (/ (* h (1+ (* bl bl))) (* 2.0 (abs bl))))))

;; Bulge of the arc from A to B with radius R, on the same side and
;; with the same minor/major-arc character as reference bulge BREF.
;; nil when R is too small to span the chord.
(defun cab:radius-bulge (a b r bref / h s bl)
  (setq h (/ (cal:dist a b) 2.0))
  (if (or (< r h) (< h 1.0e-9))
    nil
    (progn
      (setq s  (sqrt (- (* r r) (* h h)))
            bl (if (> (abs bref) 1.0)
                 (/ (+ r s) h)              ; major arc
                 (/ (- r s) h)))            ; minor arc
      (if (< bref 0.0) (- bl) bl))))

;; Try to snap the arc A->B (free-fit bulge BL over points QS) to a
;; "nice" radius - whole feet first, then half feet, then whole inches
;; (*CAB-NICE-RADII*) - keeping every point within TOL and at most LEFT
;; of them off by more than *CAB-ON-EPS*.  When WIN (a bulge interval)
;; is given the snapped bulge must stay inside it, so snapping never
;; breaks the tangency window.  The nearer multiple on each tier is
;; tried first; the arc's endpoints never move.  Returns
;; (bulge . misses) of the snapped arc, or nil.
(defun cab:snap-arc (a b bl qs tol left win / r0 h best tier lo hi
                                              cands r bl2 mis)
  (setq r0   (cab:bulge-radius a b bl)
        h    (/ (cal:dist a b) 2.0)
        best nil)
  (if (and r0 (< r0 1.0e6))       ; a huge radius is basically straight
    (foreach tier *CAB-NICE-RADII*
      (if (null best)
        (progn
          (setq lo    (* tier (fix (/ r0 tier)))
                hi    (+ lo tier)
                cands (if (< (- r0 lo) (- hi r0))
                        (list lo hi)
                        (list hi lo)))
          (foreach r cands
            (if (and (null best) (>= r h) (> r 0.0))
              (progn
                (setq bl2 (cab:radius-bulge a b r bl))
                (if (and bl2
                         (or (null win)
                             (and (>= bl2 (car win)) (<= bl2 (cdr win))))
                         (<= (cab:span-dev a b bl2 qs) tol)
                         (<= (setq mis (cab:span-misses a b bl2 qs))
                             left))
                  (setq best (cons bl2 mis))))))))))
  best)

;; ---- arc segment re-fitting ------------------------------------------
;; Re-fit one curved segment from P1 to P2 (original bulge B) through
;; CANDS, its nearby survey points sorted along the segment.  Returns a
;; list of one or more segments (p1 p2 bulge):
;;   * no candidates          -> the original arc, endpoints updated
;;   * a nice-radius (foot / half-foot / inch) arc holds every point
;;     within TOL and the miss allowance (cab-miss-left, set by the
;;     command) can absorb the off points
;;                            -> that single snapped arc, preferred
;;                               even over an exact free fit
;;   * one arc holds them all -> that single arc
;;   * one free arc keeps every point within TOL and the allowance
;;     covers it              -> that single arc; fewer curves beats
;;                               exactness, by design
;;   * otherwise              -> a tangent-continuous chain of arcs
;;                               passing exactly through every point
(defun cab:cap-bulge (b)
  (cond ((> b 5.0) 5.0) ((< b -5.0) -5.0) (T b)))

(defun cab:fit-arc-seg (p1 p2 b cands tol / ar bavg maxres mis nb q segs
                                            prev tang sn)
  (if (null cands)
    (list (list p1 p2 b))
    (progn
      (setq ar     (cab:span-arc p1 p2 cands)
            bavg   (car ar)
            maxres (cdr ar)
            sn     (cab:snap-arc p1 p2 bavg cands tol cab-miss-left nil))
      (cond
        ;; a nice-radius arc holds every point: take it first
        (sn
         (setq cab-miss-left (- cab-miss-left (cdr sn)))
         (list (list p1 p2 (car sn))))
        ;; a single free arc genuinely holds every point
        ((<= maxres *CAB-FIT-EPS*)
         (list (list p1 p2 bavg)))
        ;; a single arc is close enough and the allowance covers it
        ((and (<= maxres tol)
              (<= (setq mis (cab:span-misses p1 p2 bavg cands))
                  cab-miss-left))
         (setq cab-miss-left (- cab-miss-left mis))
         (list (list p1 p2 bavg)))
        ;; subdivide.  First arc runs from P1 through the 1st point to
        ;; the 2nd; every further arc starts tangent to the previous one
        ;; and lands exactly on the next point; the last lands on P2.
        ;; All points are hit exactly and every internal joint is
        ;; tangent-continuous (smooth).
        (T
         (setq nb   (cab:bulge-3pt p1 (car cands) (cadr cands))
               segs (list (list p1 (cadr cands) nb))
               tang (cab:end-tangent p1 (cadr cands) nb)
               prev (cadr cands))
         (foreach q (cddr cands)
           (setq nb   (cab:cap-bulge (cab:tangent-bulge prev tang q))
                 segs (cons (list prev q nb) segs)
                 tang (cab:end-tangent prev q nb)
                 prev q))
         (setq nb (cab:cap-bulge (cab:tangent-bulge prev tang p2)))
         (reverse (cons (list prev p2 nb) segs)))))))

;; ---- points-only / ordering-sketch mode -------------------------------

;; Pure-AutoLISP list helpers (no Visual LISP / vl-* dependency, so the
;; command works even when (vl-load-com) has not been run).

;; Remove every element equal (within fuzz) to VAL from LST.
(defun cab:remove (val lst / out x)
  (foreach x lst
    (if (not (equal x val 1.0e-9)) (setq out (cons x out))))
  (reverse out))

;; Insert (key . val) pair X into the already-sorted list LST, keeping
;; ascending order by the pair's car (key).
(defun cab:ins-car (x lst)
  (cond ((null lst) (list x))
        ((< (car x) (car (car lst))) (cons x lst))
        (T (cons (car lst) (cab:ins-car x (cdr lst))))))

;; Insertion-sort a list of (key . val) pairs ascending by key.
(defun cab:sort-car (lst / out x)
  (foreach x lst (setq out (cab:ins-car x out)))
  out)

;; T when the chained loop contains at least one curved segment
(defun cab:has-arcs (loop / r)
  (foreach s loop (if (>= (abs (caddr s)) 1.0e-9) (setq r T)))
  r)

;; Order points into a closed tour: nearest-neighbour walk from the
;; leftmost point, then 2-opt passes to remove crossings.
(defun cab:order-points (pts / start cur tour rest best bd q d n i j k
                              pass improved ti ti1 tj tj1 delta head midl
                              taill)
  (setq start (car pts))
  (foreach q (cdr pts)
    (if (or (< (car q) (car start))
            (and (= (car q) (car start)) (< (cadr q) (cadr start))))
      (setq start q)))
  (setq cur  start
        rest (cab:remove start pts)
        tour (list start))
  (while rest
    (setq best nil bd nil)
    (foreach q rest
      (setq d (cal:dist cur q))
      (if (or (null bd) (< d bd)) (setq best q bd d)))
    (setq tour (cons best tour)
          cur  best
          rest (cab:remove best rest)))
  (setq tour (reverse tour)
        n    (length tour)
        pass 0
        improved T)
  (while (and improved (< pass 40))
    (setq improved nil pass (1+ pass) i 0)
    (while (< i (1- n))
      (setq j (1+ i))
      (while (< j n)
        (if (not (and (= i 0) (= j (1- n))))
          (progn
            (setq ti    (nth i tour)
                  ti1   (nth (1+ i) tour)
                  tj    (nth j tour)
                  tj1   (nth (rem (1+ j) n) tour)
                  delta (- (+ (cal:dist ti tj) (cal:dist ti1 tj1))
                           (+ (cal:dist ti ti1) (cal:dist tj tj1))))
            (if (< delta -1.0e-9)
              (progn                    ; reverse tour[i+1 .. j]
                (setq head nil midl nil taill nil k 0)
                (foreach q tour
                  (cond ((<= k i) (setq head (cons q head)))
                        ((<= k j) (setq midl (cons q midl)))
                        (T        (setq taill (cons q taill))))
                  (setq k (1+ k)))
                (setq tour     (append (reverse head) midl (reverse taill))
                      improved T)))))
        (setq j (1+ j)))
      (setq i (1+ i))))
  tour)

;; Order points by their position along a user-drawn ordering sketch
;; (the chained loop): each point keys on segment-index + parameter.
(defun cab:loop-order (loop pts / keyed q best bd d i s tp)
  (foreach q pts
    (setq best 0 bd nil i 0)
    (foreach s loop
      (setq d (cab:seg-dist q s))
      (if (or (null bd) (< d bd)) (setq bd d best i))
      (setq i (1+ i)))
    (setq tp (cab:seg-param q (nth best loop)))
    (if (< tp 0.0) (setq tp 0.0))
    (if (> tp 1.0) (setq tp 1.0))
    (setq keyed (cons (cons (+ best tp) q) keyed)))
  (mapcar 'cdr (cab:sort-car keyed)))

;; The surveyed number carried by a point block, read from its
;; *CAB-PT-TAG* attribute ("number" on ab_pt).  nil when the block has
;; no such attribute.
;;
;; DELIBERATELY strict: no first-numeric-attribute fallback, unlike
;; ABFIND/BPCALLOUT/LHD/FITABHD and cal:block-number.  The fitter
;; consumes every point it is handed, so a stray numbered block (a
;; detail bubble, a keynote) silently joining the survey would warp the
;; whole fit - a dropped untagged point is the visible, recoverable
;; failure.  Reviewed 2026-08-27 and kept on purpose; this is ABHD's
;; pf:block-number line, held here too.
(defun cab:block-number (en / sub ed val)
  (setq sub (entnext en) val nil)
  (while (and sub
              (setq ed (entget sub))
              (= "ATTRIB" (cdr (assoc 0 ed))))
    (if (and (null val)
             (cdr (assoc 2 ed))
             (= (strcase (cdr (assoc 2 ed))) (strcase *CAB-PT-TAG*)))
      (setq val (cdr (assoc 1 ed))))
    (setq sub (entnext sub)))
  val)

;; Remember a point, what to call it, and the number the run sorts it
;; by, so a miss can be reported as "Pt.17" using the number in the
;; drawing rather than a private index, and the cutoff below knows how
;; far up the survey the point sits.  Points with no number of their
;; own get the next count.
(defun cab:add-point (p nm / num)
  (setq num         (cab:num-in nm)
        npt         (1+ npt)
        pts         (cons p pts)
        cab-allpts  (cons p cab-allpts)
        cab-ptnames (cons (cons p (if (and nm (/= nm "")) nm (itoa npt)))
                          cab-ptnames)
        cab-ptkeys  (cons (cons p (if num num npt)) cab-ptkeys))
  (if num (setq cab-numbered (1+ cab-numbered))))

;; The whole number a surveyed label carries: the FIRST run of digits
;; in it, so "17", "P17" and "17A" all read as seventeen.  nil when the
;; label holds no digit at all - such a point falls back to its place
;; in the selection (see cab:add-point).
(defun cab:num-in (s / i n c out done)
  (setq out "" done nil i 1 n (if s (strlen s) 0))
  (while (and (<= i n) (null done))
    (setq c (substr s i 1))
    (cond
      ((and (>= (ascii c) 48) (<= (ascii c) 57)) (setq out (strcat out c)))
      ((/= out "") (setq done T)))            ; the run of digits ended
    (setq i (1+ i)))
  (if (= out "") nil (atoi out)))

;; What to call the surveyed point at Q.
(defun cab:pt-name (q / nm p)
  (setq nm nil)
  (foreach p cab-ptnames
    (if (and (null nm) (< (cal:dist (car p) q) *CAB-EXACT-EPS*))
      (setq nm (cdr p))))
  (if nm nm "?"))

;; The number the cutoff sorts Q by.  0 for a point that was never
;; registered, so a stray can never be cut out by surprise.
(defun cab:pt-key (q / k p)
  (setq k nil)
  (foreach p cab-ptkeys
    (if (and (null k) (< (cal:dist (car p) q) *CAB-EXACT-EPS*))
      (setq k (cdr p))))
  (if k k 0))

;; ---- the point cutoff -------------------------------------------------
;; The one rule CABHD adds to ABHD's.  A survey run rarely stops where
;; the pool edge does: the shots tracing the edge come first and the
;; rest - steps, benches, deck, depth shots - carry on in the same
;; numbering, so a hundred-point survey may hold a twenty-point
;; perimeter.  The user says how far up the numbers the edge runs, and
;; everything past that is out of the perimeter ENTIRELY: not ordered,
;; not fitted, not counted against the miss allowance, and never
;; reported as a point the line failed to hold.  It is not the omit
;; list - that picks out strays one at a time and is undone by picking
;; them again; this draws a line across the whole survey at once.

;; T when Q is inside the cutoff (no cutoff = every point is).
(defun cab:in-cut (q)
  (or (null cab-cut) (<= (cab:pt-key q) cab-cut)))

;; T when Q has been picked out of the fit at a Redo.
(defun cab:omitted-p (q / found e)
  (setq found nil)
  (foreach e cab-omitted
    (if (< (cal:dist (car e) q) *CAB-EXACT-EPS*) (setq found T)))
  found)

;; The points actually in the fit: everything selected that the cutoff
;; keeps and the user has not omitted.  Rebuilt from cab-allpts rather
;; than whittled down, so a cutoff moved at a Redo can go either way.
;; The order matches the one cab:add-point built (cab-allpts is
;; selection order, this reverses it exactly as the consing did), so a
;; rebuilt list walks the tour the same way the first pass did.
(defun cab:live-pts ( / out q)
  (setq out nil)
  (foreach q (reverse cab-allpts)
    (if (and (cab:in-cut q) (not (cab:omitted-p q)))
      (setq out (cons q out))))
  out)

;; The numbers a point list spans, as (lowest . highest); nil when the
;; list is empty.
(defun cab:key-range (qs / lo hi k q)
  (foreach q qs
    (setq k (cab:pt-key q))
    (if (or (null lo) (< k lo)) (setq lo k))
    (if (or (null hi) (> k hi)) (setq hi k)))
  (if lo (cons lo hi)))

;; How many of QS a cutoff of CUT would keep (nil = all of them).
(defun cab:cut-count (qs cut / n q)
  (setq n 0)
  (foreach q qs
    (if (or (null cut) (<= (cab:pt-key q) cut)) (setq n (1+ n))))
  n)

;; Ask how far up the numbers the pool edge runs.  Enter keeps DEF
;; (nil = every point), All clears the cutoff, and Pick reads the
;; number off a point in the drawing - hunting for a number on screen
;; beats reading it out of the survey sheet.  A cutoff that would
;; starve the fit is refused and re-asked, so the answer that comes
;; back is always one the fitter can use.  DALL is every selected
;; point, cut or not.  Asked again at every Redo, so a cutoff set too
;; low or too high costs one prompt, not a whole run.
(defun cab:ask-cut (dall def / rng ans wp q cut lim done out)
  (setq rng  (cab:key-range dall)
        lim  (min 3 (length dall))
        out  def
        done nil)
  (if rng
    (princ (strcat "\n  " (itoa (length dall))
                   " point(s) selected, numbered " (itoa (car rng))
                   " to " (itoa (cdr rng)) ".")))
  (while (null done)
    (setq done T)
    (initget 6 "Pick All")
    (setq ans (getint (strcat "\n  Include points up to [Pick/All] <"
                              (if out (itoa out) "All") ">: ")))
    (cond
      ((null ans) (setq cut out))                     ; Enter: unchanged
      ((eq 'STR (type ans))
       (if (= ans "All")
         (setq cut nil)
         (progn
           (setq wp (getpoint "\n  Pick the LAST point that belongs to the pool edge: "))
           (cond
             ((null wp) (setq cut out))
             ((setq q (cab:nearest (cal:2d wp) dall))
              (setq cut (cab:pt-key q))
              (princ (strcat "  - Pt." (cab:pt-name q)
                             " (number " (itoa cut) ")")))
             (T (setq cut out))))))
      (T (setq cut ans)))
    (if (and cut (< (cab:cut-count dall cut) lim))
      (progn
        (princ (strcat "\n  (up to " (itoa cut) " leaves "
                       (itoa (cab:cut-count dall cut))
                       " point(s) and a fit needs at least " (itoa lim)
                       " - try a higher number, or All)"))
        (setq done nil))
      (setq out cut)))
  out)

;; T when P was picked at a point the cutoff has since left out.  A
;; wall, corner or hold declared there is not a near miss to be snapped
;; onto some other point - it is a declaration about a stretch of
;; survey that is no longer in the perimeter at all, so it goes.
(defun cab:cut-away-p (p dall dlive / q live)
  (setq q    (cab:nearest p dall)
        live (cab:nearest p dlive))
  (and q
       (not (cab:in-cut q))
       (or (null live) (< (cal:dist p q) (cal:dist p live)))))

;; Declarations only hold while the points they are anchored on are
;; still in the fit.  A point that leaves - omitted at a Redo, or left
;; out by a cutoff moved at one - takes its wall, corner or hold with
;; it.
(defun cab:prune-decls (dpts / out w)
  (setq out nil)
  (foreach w cab-walls
    (if (and (cab:memb (car w) dpts) (cab:memb (cadr w) dpts))
      (setq out (cons w out))))
  (if (< (length out) (length cab-walls))
    (princ "\n  (a declared wall lost an end and was dropped)"))
  (setq cab-walls (reverse out)
        out       nil)
  (foreach w cab-corners
    (if (cab:memb w dpts) (setq out (cons w out))))
  (setq cab-corners (reverse out)
        out         nil)
  (foreach w cab-holds
    (if (cab:memb w dpts) (setq out (cons w out))))
  (if (< (length out) (length cab-holds))
    (princ "\n  (a point that left the fit was held - its hold went with it)"))
  (setq cab-holds (reverse out))
  (princ))

;; The member of LST nearest to P.
(defun cab:nearest (p lst / best bd q d)
  (setq best nil bd nil)
  (foreach q lst
    (setq d (cal:dist p q))
    (if (or (null bd) (< d bd)) (setq best q bd d)))
  best)

;; Index of point P in TOUR (exact-point fuzz), or nil.
(defun cab:tour-index (p tour / i k q)
  (setq i nil k 0)
  (foreach q tour
    (if (and (null i) (< (cal:dist p q) *CAB-EXACT-EPS*)) (setq i k))
    (setq k (1+ k)))
  i)

;; Rotate the closed TOUR so it starts at point P (used so a declared
;; straight wall never straddles the walk's origin).
(defun cab:rotate-to-point (tour p / i)
  (setq i (cab:tour-index p tour))
  (if (and i (> i 0))
    (append (cal:nthcdr i tour) (cal:sublist tour 0 i))
    tour))

;; Rotate the closed TOUR so it starts at its sharpest turn: the fitter
;; walks the loop from there, so the most corner-like point is always a
;; span endpoint and never gets buried inside a span.
(defun cab:rotate-to-corner (tour / n i prev cur next turn best bi)
  (setq n (length tour) i 0 best -1.0 bi 0)
  (repeat n
    (setq prev (nth (rem (+ i n -1) n) tour)
          cur  (nth i tour)
          next (nth (rem (1+ i) n) tour)
          turn (abs (cal:signed-dang (angle prev cur) (angle cur next))))
    (if (> turn best) (setq best turn bi i))
    (setq i (1+ i)))
  (append (cal:nthcdr bi tour) (cal:sublist tour 0 bi)))

;; Number of curved segments in a span list.
(defun cab:arc-count (spans / c sp)
  (setq c 0)
  (foreach sp spans (if (>= (abs (caddr sp)) 1.0e-9) (setq c (1+ c))))
  c)

;; ---- near-tangent span fitting ---------------------------------------
;; Arcs sit ON the survey points: every span runs from tour point to
;; tour point and its interior is fitted through the points with exact
;; 3-point arcs.  Tangency is a WINDOW, not a chain: at each joint the
;; new arc's start tangent may differ from the previous arc's end
;; tangent by at most *CAB-TANG-TOL* (8 degrees), so the perimeter
;; stays visually smooth while the points stay in charge.  A bulge
;; window is a cons (lo . hi); nil means unconstrained.

;; Allowed bulge interval for the span A->B whose START tangent must
;; lie within *CAB-TANG-TOL* of the incoming tangent TE.  WF stretches
;; that limit (see *CAB-TANG-STEPS*).  The window edges are clamped so
;; extreme (U-turn) geometry stays finite.
(defun cab:tang-window (te a b wf / tt phi alo ahi lo hi)
  (setq tt  (* *CAB-TANG-TOL* wf)
        phi (cal:signed-dang te (angle a b))
        alo (max (min (/ (- phi tt) 2.0) 1.373) -1.373)
        ahi (max (min (/ (+ phi tt) 2.0) 1.373) -1.373)
        lo  (cal:tan alo)
        hi  (cal:tan ahi))
  (if (<= lo hi) (cons lo hi) (cons hi lo)))

;; Allowed bulge interval for the CLOSING span A->B whose END tangent
;; must lie within *CAB-TANG-TOL* (times WF) of the loop's start
;; tangent TS0.
(defun cab:end-window (ts0 a b wf / tt psi alo ahi lo hi)
  (setq tt  (* *CAB-TANG-TOL* wf)
        psi (cal:signed-dang (angle a b) ts0)
        alo (max (min (/ (- psi tt) 2.0) 1.373) -1.373)
        ahi (max (min (/ (+ psi tt) 2.0) 1.373) -1.373)
        lo  (cal:tan alo)
        hi  (cal:tan ahi))
  (if (<= lo hi) (cons lo hi) (cons hi lo)))

;; Intersect two bulge windows.  When they don't overlap no bulge can
;; satisfy both joints, so the bulge halfway between them is used and
;; the leftover kink is split evenly across the two joints.
(defun cab:merge-windows (win win2 / lo hi)
  (cond
    ((null win) win2)
    ((null win2) win)
    (T
     (setq lo (max (car win) (car win2))
           hi (min (cdr win) (cdr win2)))
     (if (<= lo hi)
       (cons lo hi)
       (progn
         (setq lo (if (< (cdr win) (car win2))
                    (/ (+ (cdr win) (car win2)) 2.0)
                    (/ (+ (cdr win2) (car win)) 2.0)))
         (cons lo lo))))))

;; Clamp bulge B into window WIN (nil = unconstrained).
(defun cab:clamp-b (b win)
  (cond ((null win) b)
        ((< b (car win)) (car win))
        ((> b (cdr win)) (cdr win))
        (T b)))

;; Closest any of QS comes to the segment (A B bulge) - used to test
;; whether an arc still passes through one of its interior points.
(defun cab:span-min (a b bul qs / seg mn d q)
  (setq seg (list a b bul) mn nil)
  (foreach q qs
    (setq d (cab:seg-dist q seg))
    (if (or (null mn) (< d mn)) (setq mn d)))
  mn)

;; Best bulge for the span A->B over interior points QS, restricted to
;; the tangent window WIN (nil = free).  EXACT 3-POINT ARCS COME
;; FIRST: an unclamped 3-point bulge through one of the actual
;; interior points - so the arc's middle lands ON a survey point - is
;; preferred whenever one holds the span within TOL and LEFT misses.
;; Compromise bulges (average / window-clamped / window edges), which
;; float between the points, are used only when no exact arc works.
;; Returns (bulge dev misses exactflag).
(defun cab:span-fit (a b qs win tol left / bls m sum bl cands best d mis)
  (setq bls  (mapcar '(lambda (q) (cab:bulge-3pt a q b)) qs)
        m    (length qs)
        best nil)
  ;; exact candidates: through an interior point AND inside the window
  (foreach bl bls
    (if (or (null win)
            (and (>= bl (car win)) (<= bl (cdr win))))
      (progn
        (setq d (cab:span-dev a b bl qs))
        (if (and (<= d tol)
                 (or (null best) (< d (cadr best))))
          (progn
            (setq mis (cab:span-misses a b bl qs))
            (if (<= mis left)
              (setq best (list bl d mis T))))))))
  ;; compromise candidates, only when no exact arc holds the span
  (if (null best)
    (progn
      (setq sum 0.0)
      (foreach bl bls (setq sum (+ sum bl)))
      (setq cands (list (/ sum m) (nth (/ m 2) bls)))
      (if (>= m 4)
        (setq cands (append cands (list (nth (/ m 4) bls)
                                        (nth (/ (* 3 m) 4) bls)))))
      (if win
        (setq cands (append (mapcar '(lambda (bl) (cab:clamp-b bl win))
                                    cands)
                            (list (car win) (cdr win)
                                  (/ (+ (car win) (cdr win)) 2.0)))))
      (foreach bl cands
        (setq d (cab:span-dev a b bl qs))
        (if (or (null best) (< d (cadr best)))
          (setq best (list bl d (cab:span-misses a b bl qs) nil))))))
  best)

;; Cover the rotated closed TOUR with arcs whose endpoints sit ON the
;; tour points, every joint within *CAB-TANG-TOL* of tangent.  Sharp
;; corners stay free kinks.  TE0 (may be nil) seeds the first span's
;; tangent window - used to close the seam.  LEFT is the miss
;; allowance for this pass; when PRO is true each span may spend only
;; its own fair share of it, so one greedy span cannot exhaust the
;; budget and starve the rest of the loop (the curve cap turns PRO off
;; because there the whole point is to trade accuracy for few curves).
;; Straight walls the user declared (cab-walls, bound by the command as
;; snapped point pairs) are emitted verbatim as LINE spans; ordinary
;; spans may neither swallow nor cross them.  Returns the segment list.
(defun cab:span-loop (tour tol left te0 pro / n sharp i prev cur next
                                             turn strtshp segs pos te
                                             ts0 lim a best bstx len go
                                             bnd win qs fr bl mis sn
                                             dev0 anch steps wf lm
                                             walls w i1 i2 fwd nogrow f
                                             wrec)
  (setq n (length tour))
  ;; flag the sharp corners (intentional kinks, window resets): turns
  ;; sharper than *CAB-CORNER-ANG*, plus every point the user declared
  ;; a corner - there the tangency rule is waived on purpose
  (setq sharp nil i 0)
  (repeat n
    (setq prev (nth (rem (+ i n -1) n) tour)
          cur  (nth i tour)
          next (nth (rem (1+ i) n) tour)
          turn (abs (cal:signed-dang (angle prev cur) (angle cur next))))
    (setq sharp (cons (or (> turn *CAB-CORNER-ANG*)
                          (cab:memb cur cab-corners))
                      sharp)
          i     (1+ i)))
  (setq sharp (reverse sharp))
  ;; map the declared straight walls onto tour indices, walking the
  ;; short way around; the tour was rotated so none straddles index 0
  (setq walls nil)
  (foreach w cab-walls
    (setq i1 (cab:tour-index (car w) tour)
          i2 (cab:tour-index (cadr w) tour))
    (if (and i1 i2 (/= i1 i2))
      (progn
        (setq fwd (rem (+ (- i2 i1) n) n))
        (if (> (* 2 fwd) n)
          (setq i1 i2 fwd (- n fwd)))
        (if (<= (+ i1 fwd) n)
          (setq walls (cons (list i1 (+ i1 fwd)) walls))))))
  ;; indices ordinary spans may not swallow: sharp corners, every
  ;; index a declared wall covers, and every HELD point - a span may
  ;; end on a held point (landing on it exactly) but never bury it
  (setq nogrow nil i 0)
  (repeat n
    (setq f (nth i sharp))
    (foreach w walls
      (if (and (>= i (car w)) (<= i (cadr w))) (setq f T))
      (if (and (= (cadr w) n) (= i 0)) (setq f T)))
    (if (cab:memb (nth i tour) cab-holds) (setq f T))
    (setq nogrow (cons f nogrow)
          i      (1+ i)))
  (setq nogrow  (reverse nogrow)
        strtshp (car sharp)
        segs    nil
        pos     0
        te      (if strtshp nil te0)
        ts0     nil)
  (while (< pos n)
    (setq a    (nth pos tour)
          wrec (assoc pos walls))
    (if wrec
      ;; ---- a declared straight wall starts here: emit it verbatim --
      (progn
        (setq len  (- (cadr wrec) pos)
              bnd  (nth (rem (cadr wrec) n) tour)
              qs   (cal:sublist tour (1+ pos) (1- len))
              mis  (cab:span-misses a bnd 0.0 qs)
              segs (cons (list a bnd 0.0) segs)
              left (max 0 (- left mis)))
        (if (and (null ts0) (not strtshp))
          (setq ts0 (angle a bnd)))
        (setq pos (cadr wrec)
              te  (if (and (< pos n) (nth (rem pos n) sharp))
                    nil
                    (angle a bnd))))
      ;; ---- an ordinary span --------------------------------------
      (progn
    ;; one span may never swallow the whole loop: the first span stops
    ;; one point short so the result always has at least two real
    ;; segments instead of a single zero-length one
    (setq lim  (if (= pos 0) (1- (- n pos)) (- n pos))
          best nil                   ; longest feasible span of any kind
          bstx nil                   ; longest span through an interior point
          steps *CAB-TANG-STEPS*)
    ;; Smoothness is worth more than one extra arc, so the tangent
    ;; window is stretched by degrees rather than thrown away.  Only
    ;; when even the widest step finds nothing does the stub below take
    ;; over, and that continues the previous tangent exactly - so the
    ;; tangency rule is never simply abandoned.
    (while (and (null best) steps)
      (setq wf    (car steps)
            steps (cdr steps)
            len   2
            go    T)
      (while (and go (<= len lim))
        (if (nth (rem (+ pos len -1) n) nogrow)
          (setq go nil)         ; never bury a corner or a wall point
          (progn
            (setq bnd (nth (rem (+ pos len) n) tour)
                  win (if te (cab:tang-window te a bnd wf)))
            ;; the span that closes the loop must also end within the
            ;; tangent window of the loop's start
            (if (and (= (+ pos len) n) (not strtshp) ts0)
              (setq win (cab:merge-windows win
                                          (cab:end-window ts0 a bnd wf))))
            (setq qs (cal:sublist tour (1+ pos) (1- len))
                  lm (if pro
                       (min left (cal:ceil (* (cab:misspct) len)))
                       left)
                  fr (cab:span-fit a bnd qs win tol lm))
            (if (and (<= (cadr fr) tol) (<= (caddr fr) lm))
              (progn
                (setq best (list len (car fr) (caddr fr) win))
                (if (cadddr fr) (setq bstx best))
                (setq len (1+ len)))
              (setq go nil))))))
    ;; an arc that floats between the points has to earn its keep:
    ;; only take it when it covers at least 2 more points than the
    ;; longest arc that passes exactly through a point
    (if (and bstx best (< (car best) (+ (car bstx) 2)))
      (setq best bstx))
    (if (null best)
      ;; stub to the very next point: continue the incoming tangent
      ;; (clamped to a semicircle); with no tangent it stays straight
      (progn
        (setq bnd (nth (rem (1+ pos) n) tour))
        (if te
          (progn
            (setq bl (cab:tangent-bulge a te bnd))
            (if (and (= (1+ pos) n) (not strtshp) ts0)
              ;; closing stub: split the kink between both joints
              (setq bl (/ (+ bl (cal:tan (/ (cal:signed-dang (angle a bnd)
                                                           ts0)
                                           2.0)))
                          2.0)))
            (if (> bl 1.0) (setq bl 1.0))
            (if (< bl -1.0) (setq bl -1.0)))
          (setq bl 0.0))
        (setq best (list 1 bl 0 nil)))
      ;; nice-radius snap inside the same tangent window.  A snap may
      ;; never pull the arc off its points: covered points may only
      ;; move a hair (*CAB-SNAP-EPS*) beyond where they already sat,
      ;; and an arc that passed through an interior point must still
      ;; pass through one after snapping.
      (progn
        (setq len  (car best)
              bl   (cadr best)
              win  (cadddr best)
              bnd  (nth (rem (+ pos len) n) tour)
              qs   (cal:sublist tour (1+ pos) (1- len))
              dev0 (cab:span-dev a bnd bl qs)
              anch (<= (cab:span-min a bnd bl qs) (* 2.0 *CAB-FIT-EPS*))
              sn   (cab:snap-arc a bnd bl qs
                                (max dev0 *CAB-SNAP-EPS*) left win))
        (if (and sn
                 (or (not anch)
                     (<= (cab:span-min a bnd (car sn) qs)
                         (* 2.0 *CAB-FIT-EPS*))))
          (setq best (list len (car sn) (cdr sn) win)))))
    (setq len  (car best)
          bl   (cadr best)
          mis  (caddr best)
          bnd  (nth (rem (+ pos len) n) tour)
          segs (cons (list a bnd bl) segs)
          left (- left mis))
    (if (and (null ts0) (not strtshp))
      (setq ts0 (- (angle a bnd) (* 2.0 (atan bl)))))
    (setq pos (+ pos len)
          te  (if (nth (rem pos n) sharp)
                nil
                (+ (angle a bnd) (* 2.0 (atan bl))))))))
  (reverse segs))

;; Tangent mismatch at the loop's closing joint (radians).
(defun cab:seam-kink (segs / sl sf te ts)
  (setq sl (last segs)
        sf (car segs)
        te (+ (angle (car sl) (cadr sl)) (* 2.0 (atan (caddr sl))))
        ts (- (angle (car sf) (cadr sf)) (* 2.0 (atan (caddr sf)))))
  (abs (cal:signed-dang te ts)))

;; One full fit; if the seam closes with more than *CAB-TANG-TOL* of
;; kink, refit once seeding the first span's window with the arrival
;; tangent, and keep whichever seam is straighter.  The on-the-shape
;; threshold is bound here so it tracks this pass's tolerance.
(defun cab:fit-pass (tour tol left pro / segs k1 sl te0 segs2 cab-on-eps)
  (setq cab-on-eps (max *CAB-ON-EPS* (* 0.25 tol))
        segs      (cab:span-loop tour tol left nil pro)
        k1        (cab:seam-kink segs))
  (if (> k1 (+ *CAB-TANG-TOL* 0.001))
    (progn
      (setq sl    (last segs)
            te0   (+ (angle (car sl) (cadr sl))
                     (* 2.0 (atan (caddr sl))))
            segs2 (cab:span-loop tour tol left te0 pro))
      (if (< (cab:seam-kink segs2) k1) (setq segs segs2))))
  segs)

;; Points-only / ordering-sketch fit: arcs on the points, joints
;; within *CAB-TANG-TOL* of tangent, nice radii.  LEFT is the miss
;; allowance the walk may spend and PRO whether each span is held to
;; its own fair share of it - lifting both is what buys long arcs at
;; an unchanged tolerance, which is how the "few" candidate trades
;; curves for nothing but slack the user already granted.  MAXARCS,
;; when set, is enforced by refitting the whole loop with a
;; progressively relaxed tolerance, which keeps the tangent windows
;; intact.  The fewest-curves result seen is kept, so an unreachably
;; small cap still returns the smallest fit possible - never the
;; biggest.
(defun cab:coarse-loop (tour tol maxarcs left pro / segs segs2 tol2 tries)
  ;; start the walk at a declared wall or corner when there is one, so
  ;; neither straddles the walk's origin; otherwise at the sharpest turn
  (setq tour (cond
               (cab-walls   (cab:rotate-to-point tour (car (car cab-walls))))
               (cab-corners (cab:rotate-to-point tour (car cab-corners)))
               (T          (cab:rotate-to-corner tour)))
        segs (cab:fit-pass tour tol left pro))
  ;; the cap deliberately buys few curves with accuracy, so the refits
  ;; drop both the miss allowance and the per-span fair share
  (if maxarcs
    (progn
      (setq tol2 tol tries 0)
      (while (and (> (cab:arc-count segs) maxarcs) (< tries 40))
        (setq tol2  (* tol2 1.4)
              tries (1+ tries)
              segs2 (cab:fit-pass tour tol2 1000000 nil))
        (if (< (cab:arc-count segs2) (cab:arc-count segs))
          (setq segs segs2)))))
  segs)

;; ---- self-intersection check -----------------------------------------
;; A loop that crosses itself almost always means the automatic point
;; ordering went around a narrow waist the wrong way.  We cannot fix
;; that from the points alone, but we can spot it and say so.

;; Cross product of (P-O) x (Q-O); its sign says which side Q is on.
(defun cab:cross3 (o p q)
  (- (* (- (car p) (car o)) (- (cadr q) (cadr o)))
     (* (- (cadr p) (cadr o)) (- (car q) (car o)))))

;; T when segments A-B and C-D properly cross.  Touching or shared
;; endpoints give a zero product and do not count.
(defun cab:segs-cross (a b c d / d1 d2 d3 d4)
  (setq d1 (cab:cross3 a b c) d2 (cab:cross3 a b d)
        d3 (cab:cross3 c d a) d4 (cab:cross3 c d b))
  (and (< (* d1 d2) 0.0) (< (* d3 d4) 0.0)))

;; Sample the fitted loop into a point list; arcs get intermediate
;; points so a bulging arc's real path is tested, not just its chord.
(defun cab:loop-pts (segs / out s g c r a1 a2 sweep k j aa)
  (setq out nil)
  (foreach s segs
    (setq out (cons (cal:2d (car s)) out))
    (if (>= (abs (caddr s)) 1.0e-9)
      (progn
        (setq g (cab:arc-geom (car s) (cadr s) (caddr s)))
        (if g
          (progn
            (setq c  (car g)   r  (cadr g)
                  a1 (caddr g) a2 (cadddr g))
            (if (> (caddr s) 0.0)
              (setq sweep (cal:angnorm (- a2 a1)))
              (setq sweep (- (cal:angnorm (- a1 a2)))))
            (setq k 4 j 1)
            (while (< j k)
              (setq aa  (+ a1 (* sweep (/ (float j) (float k))))
                    out (cons (list (+ (car c) (* r (cos aa)))
                                    (+ (cadr c) (* r (sin aa))))
                              out)
                    j   (1+ j))))))))
  (reverse out))

;; T when the fitted loop crosses itself.
(defun cab:self-crosses (segs / p n found ti tj i j a b c d)
  (setq p (cab:loop-pts segs))
  (if (< (length p) 4)
    nil
    (progn
      (setq p     (append p (list (car p)))  ; close the point ring
            n     (1- (length p))            ; number of chords
            found nil
            ti    p
            i     0)
      (while (and (not found) (< i (- n 2)))
        (setq a  (car ti)
              b  (cadr ti)
              tj (cddr ti)
              j  (+ i 2))
        (while (and (not found) (< j n))
          (setq c (car tj) d (cadr tj))
          ;; the first and last chords legitimately share a vertex
          (if (not (and (= i 0) (= j (1- n))))
            (if (cab:segs-cross a b c d) (setq found T)))
          (setq tj (cdr tj) j (1+ j)))
        (setq ti (cdr ti) i (1+ i)))
      found)))

;; How many fitted polylines are already on the output layer (counted
;; before the new one is drawn).
(defun cab:prior-fits (/ ss)
  (setq ss (ssget "_X" (list (cons 8 *CAB-OUT-LAYER*)
                             '(0 . "LWPOLYLINE"))))
  (if ss (sslength ss) 0))

;; T when R is a whole multiple of one of the *CAB-NICE-RADII* tiers.
(defun cab:nice-radius-p (r / found tier q)
  (setq found nil)
  (if (and r (< r 1.0e6))
    (foreach tier *CAB-NICE-RADII*
      (setq q (/ r tier))
      (if (< (abs (- q (fix (+ q 0.5)))) 1.0e-6) (setq found T))))
  found)

;; verts: list of (pt bulge) in order, closed.  COL is an AutoCAD
;; colour index, or nil for BYLAYER.
(defun cab:make-pline (verts layer col / dxf v)
  (setq dxf (list '(0 . "LWPOLYLINE") '(100 . "AcDbEntity")
                  (cons 8 layer)))
  (if col (setq dxf (append dxf (list (cons 62 col)))))
  (setq dxf (append dxf (list '(100 . "AcDbPolyline")
                              (cons 90 (length verts)) '(70 . 1))))
  (foreach v verts
    (setq dxf (append dxf (list (cons 10 (car v)) (cons 42 (cadr v))))))
  (entmakex dxf))

;; The kept fit joins the POOL layer in ByLayer colour: the preview
;; colour and the preview layer both belonged to the comparison - the
;; result belongs with the pool.
(defun cab:set-bylayer (en / ed)
  (cal:ensure-layer *CAB-POOL-LAYER* 4)
  (setq ed (entget en)
        ed (subst (cons 8 *CAB-POOL-LAYER*) (assoc 8 ed) ed))
  (if (assoc 62 ed) (setq ed (subst '(62 . 256) (assoc 62 ed) ed)))
  (entmod ed))

;; The points SEGS fails to hold within TOL.
(defun cab:unheld (segs pts tol / out q s d dmin)
  (setq out nil)
  (foreach q pts
    (setq dmin nil)
    (foreach s segs
      (setq d (cab:seg-dist q s))
      (if (or (null dmin) (< d dmin)) (setq dmin d)))
    (if (> dmin tol) (setq out (cons q out))))
  (reverse out))

;; List membership by position, within the exact-point fuzz.
(defun cab:memb (q lst / found p)
  (setq found nil)
  (foreach p lst
    (if (< (cal:dist p q) *CAB-EXACT-EPS*) (setq found T)))
  found)

(defun cab:isect (a b / out q)
  (setq out nil)
  (foreach q a
    (if (cab:memb q b) (setq out (cons q out))))
  (reverse out))

;; ---- temporary preview geometry --------------------------------------
;; Everything CABHD draws to help you decide - the dashed straight-wall
;; markers, the three candidate outlines, their number labels - is
;; scaffolding, not a result.  Each piece is registered here as it is
;; created and swept away when the command ends, whether that is
;; normally, by ESC, or by an error, so no run leaves litter behind.
;; Whatever the user chooses to keep is dropped from the list first.

(defun cab:temp-add (en)
  (if en (setq cab-temp (cons en cab-temp)))
  en)

(defun cab:temp-drop (en / out x)
  (setq out nil)
  (foreach x cab-temp
    (if (not (eq x en)) (setq out (cons x out))))
  (setq cab-temp (reverse out))
  en)

;; entget returns nil for something already gone, so a piece erased
;; earlier is simply skipped instead of raising an error
(defun cab:temp-clear ( / en)
  (foreach en cab-temp
    (if (and en (entget en)) (entdel en)))
  (setq cab-temp nil))

;; ---- "this one is mine" stamping -------------------------------------
;; CABHD writes onto layers the drawing may already be using - FGStep in
;; particular - so it must never clear a layer wholesale.  Everything it
;; creates carries a small piece of extended data naming this command,
;; and only stamped objects are ever erased again.

(defun cab:tag-mine (en / ed)
  (if en
    (progn
      (regapp "CABHD")
      (setq ed (entget en))
      (entmod (append ed (list (list -3 (list "CABHD" (cons 1000 "CABHD"))))))))
  en)

;; Erase only CABHD's own objects on a layer; anything the user drew
;; there is left alone.  Returns how many went.
(defun cab:purge-mine (name / ss i n en)
  (setq n 0)
  (if (tblsearch "LAYER" name)
    (progn
      (setq ss (ssget "_X" (list (cons 8 name))))
      (if ss
        (progn
          (setq i 0)
          (repeat (sslength ss)
            (setq en (ssname ss i))
            (if (assoc -3 (entget en '("CABHD")))
              (progn (entdel en) (setq n (1+ n))))
            (setq i (1+ i)))))))
  n)

;; Make sure the DASHED linetype exists (pure entmake, no command
;; calls).  Dash lengths are in drawing units - sized for an inch
;; drawing, so the dashes read at pool scale.
(defun cab:ensure-dashed ()
  (if (not (tblsearch "LTYPE" "DASHED"))
    (entmake (list '(0 . "LTYPE") '(100 . "AcDbSymbolTableRecord")
                   '(100 . "AcDbLinetypeTableRecord")
                   '(2 . "DASHED") '(70 . 0)
                   '(3 . "Dashed __ __ __ __ __")
                   '(72 . 65) '(73 . 2) '(40 . 18.0)
                   '(49 . 12.0) '(74 . 0)
                   '(49 . -6.0) '(74 . 0)))))

;; Draw the dashed ring marking a user-declared sharp corner.
(defun cab:draw-corner-marker (p)
  (cab:ensure-dashed)
  (cal:ensure-layer *CAB-WALL-LAYER* 8)
  (entmakex (list '(0 . "CIRCLE") '(100 . "AcDbEntity")
                  (cons 8 *CAB-WALL-LAYER*) '(6 . "DASHED")
                  '(100 . "AcDbCircle")
                  (cons 10 (list (car p) (cadr p) 0.0))
                  (cons 40 *CAB-MISS-RADIUS*))))

;; Draw the marker for a user-declared HELD point: a dashed ring at
;; half the miss-ring radius, so it reads apart from corner rings.
(defun cab:draw-hold-marker (p)
  (cab:ensure-dashed)
  (cal:ensure-layer *CAB-WALL-LAYER* 8)
  (entmakex (list '(0 . "CIRCLE") '(100 . "AcDbEntity")
                  (cons 8 *CAB-WALL-LAYER*) '(6 . "DASHED")
                  '(100 . "AcDbCircle")
                  (cons 10 (list (car p) (cadr p) 0.0))
                  (cons 40 (* 0.5 *CAB-MISS-RADIUS*)))))

;; Draw the dashed marker for a user-declared straight wall.
(defun cab:draw-wall-marker (p1 p2)
  (cab:ensure-dashed)
  (cal:ensure-layer *CAB-WALL-LAYER* 8)
  (entmakex (list '(0 . "LINE") '(100 . "AcDbEntity")
                  (cons 8 *CAB-WALL-LAYER*) '(6 . "DASHED")
                  '(100 . "AcDbLine")
                  (cons 10 (list (car p1) (cadr p1) 0.0))
                  (cons 11 (list (car p2) (cadr p2) 0.0)))))

;; Bounding box of a point list, as (minx miny maxx maxy).
(defun cab:bbox (pts / x0 y0 x1 y1 q)
  (foreach q pts
    (if (null x0)
      (setq x0 (car q) x1 (car q) y0 (cadr q) y1 (cadr q))
      (setq x0 (min x0 (car q)) x1 (max x1 (car q))
            y0 (min y0 (cadr q)) y1 (max y1 (cadr q)))))
  (list x0 y0 x1 y1))

;; Draw "1", "2", "3" beside each candidate, in that candidate's own
;; colour, with that fit's numbers spelled out to the right of it - so
;; the whole choice can be made from the drawing without reading the
;; command line at all.  The labels stack down the right-hand side of
;; the shape and are sized to the drawing, so they read at any zoom.
;; Returns the list of entities that make up the label.  The figures
;; go on two lines bracketing the number, so the label stays readable
;; instead of trailing a single very long line across the drawing.
(defun cab:label (num colour bb hgt row top bot / x y out e pr)
  (setq x   (+ (caddr bb) (* 0.6 hgt))
        y   (- (cadddr bb) (* row hgt 2.1))
        out nil)
  ;; the number itself, full height
  (setq e (entmakex (list '(0 . "TEXT") '(100 . "AcDbEntity")
                          (cons 8 *CAB-OUT-LAYER*) (cons 62 colour)
                          '(100 . "AcDbText")
                          (cons 10 (list x y 0.0))
                          (cons 40 hgt)
                          (cons 1 num))))
  (if e (setq out (cons e out)))
  ;; its figures, smaller, on two lines to the right of the number
  (foreach pr (list (cons top (* 0.55 hgt)) (cons bot (* -0.05 hgt)))
    (setq e (entmakex (list '(0 . "TEXT") '(100 . "AcDbEntity")
                            (cons 8 *CAB-OUT-LAYER*) (cons 62 colour)
                            '(100 . "AcDbText")
                            (cons 10 (list (+ x (* 1.4 hgt))
                                           (+ y (cdr pr))
                                           0.0))
                            (cons 40 (* 0.42 hgt))
                            (cons 1 (car pr)))))
    (if e (setq out (cons e out))))
  (reverse out))

;; Ring every point the chosen fit could not hold, on its own layer,
;; so they are easy to zoom to and judge: a mis-shot, a duplicate, or
;; a real feature the tolerance is too tight for.
;; Also writes the list of them to the side of the shape, worst first,
;; as "Pt.17   off by 1-7/8"" - so the misses can be worked through
;; without hunting for red circles.
(defun cab:mark-unheld (bad segs bb hgt / q d s dmin keyed pair th x y
                                         line)
  ;; markers from an earlier run describe a fit that no longer exists;
  ;; only CABHD's own are removed, never anything else on the layer
  (cab:purge-mine *CAB-MISS-LAYER*)
  (if bad
    (progn
      (cal:ensure-layer *CAB-MISS-LAYER* 1)
      ;; rings on the points themselves
      (foreach q bad
        (cab:tag-mine
          (entmakex (list '(0 . "CIRCLE") '(100 . "AcDbEntity")
                          (cons 8 *CAB-MISS-LAYER*) '(100 . "AcDbCircle")
                          (cons 10 (list (car q) (cadr q) 0.0))
                          (cons 40 *CAB-MISS-RADIUS*)))))
      ;; how far off each one is, worst first
      (setq keyed nil)
      (foreach q bad
        (setq dmin nil)
        (foreach s segs
          (setq d (cab:seg-dist q s))
          (if (or (null dmin) (< d dmin)) (setq dmin d)))
        (setq keyed (cons (cons dmin q) keyed)))
      (setq keyed (reverse (cab:sort-car keyed))
            th    (* 0.5 hgt)
            x     (+ (caddr bb) (* 0.6 hgt))
            y     (cadddr bb))
      (cab:tag-mine
        (entmakex (list '(0 . "TEXT") '(100 . "AcDbEntity")
                        (cons 8 *CAB-MISS-LAYER*) '(100 . "AcDbText")
                        (cons 10 (list x y 0.0))
                        (cons 40 th)
                        (cons 1 (strcat "POINTS OFF THE LINE ("
                                        (itoa (length bad)) ")")))))
      (foreach pair keyed
        (setq y    (- y (* th 1.6))
              line (strcat "Pt." (cab:pt-name (cdr pair))
                           "   off by " (rtos (car pair) 4 4)))
        (cab:tag-mine
          (entmakex (list '(0 . "TEXT") '(100 . "AcDbEntity")
                          (cons 8 *CAB-MISS-LAYER*) '(100 . "AcDbText")
                          (cons 10 (list x y 0.0))
                          (cons 40 th)
                          (cons 1 line)))))))
  keyed)

;; Print the hit report for the fit the user kept.  ALLOW is the run's
;; miss allowance (how many points were permitted to sit between the
;; on-the-shape threshold and the tolerance off the result).
(defun cab:report (newsegs pts tol allow prior / nl na hiton hitok miss
                                                q s s2 d dmin worst sum
                                                sumo no nice onpt inner
                                                ns i te ts kk mk nk
                                                hw hq cab-on-eps)
  ;; report against the same on-the-shape threshold the fit used
  (setq cab-on-eps (max *CAB-ON-EPS* (* 0.25 tol)))
  (progn
      ;; -- segment mix, nice radii, arcs anchored on a point --------
      (setq nl 0 na 0 nice 0 onpt 0)
      (foreach s newsegs
        (if (< (abs (caddr s)) 1.0e-9)
          (setq nl (1+ nl))
          (progn
            (setq na (1+ na))
            (if (cab:nice-radius-p
                  (cab:bulge-radius (car s) (cadr s) (caddr s)))
              (setq nice (1+ nice)))
            ;; does this arc pass through a point other than its ends?
            (setq inner nil)
            (foreach q pts
              (if (and (> (cal:dist q (car s)) *CAB-EXACT-EPS*)
                       (> (cal:dist q (cadr s)) *CAB-EXACT-EPS*)
                       (<= (cab:seg-dist q s) (* 2.0 *CAB-FIT-EPS*)))
                (setq inner T)))
            (if inner (setq onpt (1+ onpt))))))
      ;; -- how the survey points landed ------------------------------
      (setq hiton 0 hitok 0 miss 0 worst 0.0 sum 0.0 sumo 0.0 no 0)
      (foreach q pts
        (setq dmin nil)
        (foreach s newsegs
          (setq d (cab:seg-dist q s))
          (if (or (null dmin) (< d dmin)) (setq dmin d)))
        (if (> dmin worst) (setq worst dmin))
        (setq sum (+ sum dmin))
        (if (> dmin (cab:oneps))
          (setq sumo (+ sumo dmin) no (1+ no)))
        (cond
          ((<= dmin (cab:oneps)) (setq hiton (1+ hiton)))
          ((<= dmin tol)        (setq hitok (1+ hitok)))
          (T                    (setq miss  (1+ miss)))))
      ;; -- smoothness: worst kink at a joint that is not a corner ----
      (setq ns (length newsegs) i 0 mk 0.0 nk 0)
      (while (< i ns)
        (setq s  (nth i newsegs)
              s2 (nth (rem (1+ i) ns) newsegs)
              te (+ (angle (car s) (cadr s)) (* 2.0 (atan (caddr s))))
              ts (- (angle (car s2) (cadr s2)) (* 2.0 (atan (caddr s2))))
              kk (abs (cal:signed-dang te ts)))
        (if (<= kk *CAB-CORNER-ANG*)     ; bigger = an intentional corner
          (progn
            (if (> kk mk) (setq mk kk))
            (if (> kk (+ *CAB-TANG-TOL* 1.0e-6)) (setq nk (1+ nk)))))
        (setq i (1+ i)))
      (princ (strcat "\nCABHD: " (itoa ns) " segments ("
                     (itoa nl) " lines + " (itoa na)
                     " curves) written to layer " *CAB-POOL-LAYER* "."
                     "\n  Points on the perimeter:      " (itoa hiton)
                     "\n  Points off within tolerance:  " (itoa hitok)
                     "  (allowance " (itoa allow) ")"
                     "\n  Points beyond tolerance:      " (itoa miss)
                     "\n  Worst point deviation:        " (rtos worst 2 3)
                     "\n  Average off, all points:      "
                     (rtos (if (> (length pts) 0)
                             (/ sum (length pts))
                             0.0)
                           2 3)
                     "\n  Average off, off points only: "
                     (if (> no 0)
                       (strcat (rtos (/ sumo no) 2 3)
                               "  (" (itoa no) " point(s))")
                       "-  (every point is on the line)")
                     "\n  Curves through a point:       " (itoa onpt)
                     " of " (itoa na)
                     "\n  Curves on foot/half/inch radii:" (itoa nice)
                     " of " (itoa na)
                     "\n  Largest joint kink:           "
                     (rtos (* 180.0 (/ mk pi)) 2 1) " deg  (limit "
                     (rtos (* 180.0 (/ *CAB-TANG-TOL* pi)) 2 1) ")"))
      (if (> nk 0)
        (princ (strcat "\n  (" (itoa nk)
                       " joint(s) needed more than the tangent limit to"
                       " close the loop)")))
      (if cab-walls
        (princ (strcat "\n  (" (itoa (length cab-walls))
                       " declared straight wall(s) kept dead straight)")))
      (if cab-holds
        (progn
          ;; every held point must sit ON the kept fit exactly; one
          ;; that does not means the drawn shape or a declared wall
          ;; overruled it, and that deserves a loud line of its own
          (setq hw 0.0)
          (foreach q cab-holds
            (setq dmin nil)
            (foreach s newsegs
              (setq d (cab:seg-dist q s))
              (if (or (null dmin) (< d dmin)) (setq dmin d)))
            (if (> dmin hw) (setq hw dmin hq q)))
          (if (<= hw *CAB-EXACT-EPS*)
            (princ (strcat "\n  (" (itoa (length cab-holds))
                           " held point(s) all landed on the line"
                           " exactly)"))
            (princ (strcat "\n  WARNING: held Pt." (cab:pt-name hq)
                           " is off by " (rtos hw 2 4)
                           " - the drawn shape or a declared wall"
                           " overruled it.")))))
      (if (and *CAB-MAX-ARCS* (> na *CAB-MAX-ARCS*))
        (princ (strcat "\n  (the curve cap is " (itoa *CAB-MAX-ARCS*)
                       " but " (itoa na) " curves was the fewest"
                       " reachable: a closed loop needs at least 2"
                       " segments)")))
      (if (> miss 0)
        (princ "\n  (points beyond tolerance: the curve cap and/or the drawn shape overruled them)"))
      (if (cab:self-crosses newsegs)
        (princ (strcat "\n  WARNING: the result crosses itself - the"
                       " automatic point order is probably wrong."
                       "  Draw a rough lines-only loop on layer "
                       *CAB-POOL-LAYER*
                       " through the points in the right order and"
                       " select it too.")))
      (if (> prior 0)
        (princ (strcat "\n  (" (itoa prior)
                       " earlier fit(s) were already on layer "
                       *CAB-OUT-LAYER* " - erase them if you only want"
                       " the new one)"))))
  (princ))

;; ---- guided mode ------------------------------------------------------
;; Re-fit the drawn perimeter LOOP through the survey points: every
;; vertex snaps to the nearest point within TOL, every drawn arc is
;; re-fitted through the points lying along it, and drawn straight
;; walls stay straight.  TOL and FTOL are two different jobs one number
;; used to do: TOL is the reach - which point belongs to which vertex
;; and which drawn arc - and is always the distance the user typed, so
;; every candidate reads the drawn shape the same way; FTOL is how
;; exactly the re-fit then has to hold those points, and is what a
;; candidate varies.  If the result needs more curves than MAXARCS, the
;; fit falls back to the points-driven builder - the drawn loop still
;; supplies the point order.
(defun cab:guided-fit (loop pts dpts tol ftol allow maxarcs
                      / verts used n s p1 p2 b cands clean ns newsegs
                        q d)
  ;; -- 1. snap each vertex to its nearest point within tol ----------
  (setq verts (mapcar '(lambda (s) (car s)) loop)
        used  nil)
  (setq verts
    (mapcar
      '(lambda (v / best bd)
         (setq best nil bd tol)
         (foreach q pts
           (setq d (cal:dist v q))
           (if (and (<= d bd) (not (member q used)))
             (setq best q bd d)))
         (if best (progn (setq used (cons best used)) best) v))
      verts))
  ;; -- 2. re-fit every arc segment through the points near it -------
  (setq newsegs nil n 0)
  (repeat (length loop)
    (setq s  (nth n loop)
          p1 (nth n verts)
          p2 (nth (rem (1+ n) (length verts)) verts)
          b  (caddr s))
    (if (< (abs b) 1.0e-9)
      ;; straight wall: trust the user, keep it straight
      (setq newsegs (cons (list p1 p2 0.0) newsegs))
      (progn
        ;; survey points lying near the ORIGINAL arc, excluding the
        ;; ones already consumed as vertices, sorted along the arc and
        ;; de-duplicated
        (setq cands nil)
        (foreach q pts
          (if (and (not (member q used))
                   (<= (cab:seg-dist q s) tol)
                   (> (cal:dist q p1) *CAB-EXACT-EPS*)
                   (> (cal:dist q p2) *CAB-EXACT-EPS*))
            (setq cands (cons (cons (cab:seg-param q s) q) cands))))
        (setq cands (mapcar 'cdr (cab:sort-car cands)))
        (setq clean nil)
        (foreach q cands
          (if (or (null clean)
                  (> (cal:dist q (car clean)) *CAB-EXACT-EPS*))
            (setq clean (cons q clean))))
        (foreach ns (cab:fit-arc-seg p1 p2 b (reverse clean) ftol)
          (setq newsegs (cons ns newsegs)))))
    (setq n (1+ n)))
  (setq newsegs (reverse newsegs))
  ;; -- 3. the drawn shape is trusted, but the curve cap still wins --
  (if (and maxarcs
           (> (cab:arc-count newsegs) maxarcs)
           (>= (length dpts) 3))
    (progn
      (princ (strcat "\n  (the drawn perimeter needs "
                     (itoa (cab:arc-count newsegs))
                     " curves but the cap is " (itoa maxarcs)
                     " - refitting from the points instead)"))
      (setq cab-miss-left allow
            newsegs (cab:coarse-loop (cab:loop-order loop dpts)
                                    ftol maxarcs allow T))))
  newsegs)

;; Build one candidate fit in MODE - "tight", "asked" or "few", the
;; three aims listed against *CAB-COMPARE*.  A non-nil TOUR means the
;; points drive the shape (points-only and ordering-sketch modes);
;; otherwise the drawn LOOP is re-fitted (guided mode).  TOL is always
;; the distance the user typed - it is what reads the drawn shape and
;; what the table judges every candidate against - and the mode sets
;; the three knobs that actually differ:
;;
;;   FTOL  how exactly the arcs must hold their points.  "tight" fits
;;         to *CAB-TIGHT-TOL* (or to TOL when that is tighter yet),
;;         which is what drives its error towards nothing and its
;;         curve count up; the other two fit to TOL.
;;   LEFT  the miss allowance.  "tight" grants none, so no point is
;;         written off; "few" lifts it (and the per-span fair share
;;         with it), which is the whole trick - the arcs run as long
;;         as TOL permits instead of stopping at the standard share,
;;         and every point is still held to TOL by the span fitter.
;;   CAP   the curve cap.  Only "asked" honours it: capping the other
;;         two would be asking for the most curves, or the fewest,
;;         and then overruling the answer.
;;
;; Each call gets its own miss allowance and on-the-shape threshold.
(defun cab:build (tour loop pts dpts tol allow mode
                 / cab-miss-left cab-on-eps ftol left cap)
  (setq ftol (if (= mode "tight") (min tol *CAB-TIGHT-TOL*) tol)
        left (cond ((= mode "tight") 0)
                   ((= mode "few")   1000000)
                   (T                allow))
        cap  (if (= mode "asked") *CAB-MAX-ARCS*)
        cab-miss-left left
        cab-on-eps    (max *CAB-ON-EPS* (* 0.25 ftol)))
  (if tour
    (cab:coarse-loop tour ftol cap left (not (= mode "few")))
    (cab:guided-fit loop pts dpts tol ftol left cap)))

;; Deviation summary for SEGS against PTS: (worst avg avg-off).
;;   worst   - furthest any point sits from the line
;;   avg     - mean over ALL points, so it counts the ones sitting on
;;             the line as the zeros they are
;;   avg-off - mean over only the points that are actually OFF the
;;             line (further than ON from it), which says how far the
;;             strays really stray; nil when nothing is off
(defun cab:devstats (segs pts on / w q s d dmin sum n sumo no)
  (setq w 0.0 sum 0.0 n 0 sumo 0.0 no 0)
  (foreach q pts
    (setq dmin nil)
    (foreach s segs
      (setq d (cab:seg-dist q s))
      (if (or (null dmin) (< d dmin)) (setq dmin d)))
    (if (> dmin w) (setq w dmin))
    (setq sum (+ sum dmin) n (1+ n))
    (if (> dmin on) (setq sumo (+ sumo dmin) no (1+ no))))
  (list w
        (if (> n 0) (/ sum n) 0.0)
        (if (> no 0) (/ sumo no) nil)))

;; A deviation for a table cell; "-" when there is nothing to average.
(defun cab:fmt-dev (x)
  (if x (rtos x 2 2) "-"))

;; ---- offer three fits and let the user pick ---------------------------
;; Knowing up front how much curve to spend on how much accuracy is the
;; hardest part of the command, so instead of asking the user to
;; imagine it, draw the two ends of that trade and the middle: the
;; most curves for the least error, the settings as typed, and the
;; fewest curves that still hold the distance.  Each goes on in its own
;; colour with what it costs, and the one they point at is kept.
;; Everything is judged against the tolerance the user actually typed,
;; so the columns compare like for like even though the three were not
;; built alike.

;; The candidates that actually reached the screen.  A fit can come out
;; too degenerate for AutoCAD to accept - fewer than two segments is no
;; closed outline - and the tight one is the likeliest to, since it must
;; thread every point at *CAB-TIGHT-TOL*.  Losing it is no reason to
;; throw away the two that drew, so this is what the chooser works from
;; and only an empty list is a dead end.
(defun cab:drawn (vars / out v)
  (foreach v vars (if (cadr v) (setq out (cons v out))))
  (reverse out))

(defun cab:compare (tour loop pts dpts tol allow
                   / prior vars v e ent lab st onv segs bad allbad first
                     i pick idx keep ce bb hgt sel picked keyed pr res
                     dflt)
  (setq prior (cab:prior-fits))
  (cal:ensure-layer *CAB-OUT-LAYER* 3)
  ;; every candidate is judged against the distance the user typed, so
  ;; "off the line" means the same thing in all three rows
  (setq onv (max *CAB-ON-EPS* (* 0.25 tol)))
  ;; label height: a twentieth of the shape, so it reads at any zoom
  (setq bb  (cab:bbox pts)
        hgt (/ (max (- (caddr bb) (car bb))
                    (- (cadddr bb) (cadr bb)))
               20.0))
  (if (<= hgt 0.0) (setq hgt 1.0))
  (setq cab-phase "building the three candidate fits"
        vars     nil
        allbad   nil
        first    T
        i        1)
  (foreach v *CAB-COMPARE*
    (setq segs (cab:build tour loop pts dpts tol allow (car v))
          ent  (cab:temp-add
                 (cab:make-pline
                   (mapcar '(lambda (s) (list (car s) (caddr s))) segs)
                   *CAB-OUT-LAYER* (cadr v)))
          bad  (cab:unheld segs pts tol)
          st   (cab:devstats segs pts onv)
          ;; the same figures the table prints, spelled out so they
          ;; stand on their own beside the number in the drawing
          lab  (cab:label
                 (itoa i) (cadr v) bb hgt i
                 (strcat (itoa (length segs)) " segs    "
                         (itoa (cab:arc-count segs)) " curves    "
                         (itoa (length bad)) " not held    "
                         (cadddr v))
                 (strcat "worst " (cab:fmt-dev (car st))
                         "    avg all " (cab:fmt-dev (cadr st))
                         "    avg off " (cab:fmt-dev (caddr st))))
          vars (cons (list segs ent bad v lab st) vars)
          i    (1+ i))
    (foreach e lab (cab:temp-add e))
    ;; the note below is about points NO fit could hold, so only the
    ;; fits actually built to the user's distance get a vote.  The
    ;; tight one threads every point by construction - counting it
    ;; would empty the intersection every time and quietly retire the
    ;; warning that catches mis-shots
    (if (not (= (car v) "tight"))
      (if first
        (setq allbad bad first nil)
        (setq allbad (cab:isect allbad bad)))))
  (setq vars (reverse vars))
  (if (null (cab:drawn vars))
    (progn
      (princ (strcat "\nCABHD: none of the " (itoa (length vars))
                     " candidate fits would draw ("
                     (itoa (length (car (car vars))))
                     " segment(s) in the first)."))
      (princ "\n  A closed outline needs at least two segments, so this is")
      (princ "\n  nearly always the points rather than the drawing: too few")
      (princ "\n  left after the cutoff, or points that all sit on one line.")
      (princ (strcat "\n  Check the cutoff (All puts every point back), and"
                     " that layer\n  " *CAB-OUT-LAYER*
                     " is not locked or read-only.")))
    (progn
      (princ (strcat "\n\n" (itoa (length (cab:drawn vars)))
                     " candidate fit(s) are now drawn on layer "
                     *CAB-OUT-LAYER*
                     ",\neach numbered on screen in its own colour:\n"))
      (princ "\n   #  segs  curves  worst off  avg all  avg off  not held  ")
      (princ "\n   -  ----  ------  ---------  -------  -------  --------  ")
      (setq i 1)
      (foreach v vars
        (setq segs (car v) bad (caddr v) ce (cadddr v) st (nth 5 v))
        (princ (strcat "\n   " (itoa i) "  "
                       (cal:pad (itoa (length segs)) 6)
                       (cal:pad (itoa (cab:arc-count segs)) 8)
                       (cal:pad (cab:fmt-dev (car st)) 11)
                       (cal:pad (cab:fmt-dev (cadr st)) 9)
                       (cal:pad (cab:fmt-dev (caddr st)) 9)
                       (cal:pad (itoa (length bad)) 10)
                       (cadddr ce)
                       (if (cadr v) "" "   -- would not draw")))
        (setq i (1+ i)))
      (princ (strcat "\n\n  \"not held\" = points further than "
                     (rtos tol 2 3) " from that fit."
                     "\n  \"avg all\" averages every point; \"avg off\""
                     " averages only the points that are off the line"
                     "\n  (further than " (rtos onv 2 3) " from it)."))
      (princ (strcat "\n  All three are measured against the "
                     (rtos tol 2 3) " you typed, but only one is built"
                     " to it:"
                     "\n  the tight fit spends curves to drive the error"
                     " towards nothing (it"
                     "\n  ignores that distance"
                     (if *CAB-MAX-ARCS* " and the curve cap" "")
                     "), the middle one is your settings exactly,"
                     "\n  and the few fit holds the same distance with"
                     " as few curves as it can."))
      (if allbad
        (princ (strcat "\n  NOTE: " (itoa (length allbad))
                       " point(s) could not be held by ANY fit built to"
                       " that distance - likely a mis-shot, a duplicate,"
                       " or a corner that needs more points around it."
                       "\n  (the tight fit threads every point it can"
                       " reach, so it does not get a vote here.)")))
      ;; -- let the user choose ---------------------------------------
      ;; Clicking the outline you want beats translating a colour into
      ;; a number, so a pick on screen is offered first; typing the
      ;; number still works for anyone who prefers the keyboard.
      (setq cab-phase "waiting for the choice of fit")
      ;; Enter has to produce something that is actually on screen.  The
      ;; middle fit - the settings as typed - stays the default exactly
      ;; as long as it drew; only when it did not does the default move
      ;; to the first one that did.
      (setq dflt (if (and (nth 1 vars) (cadr (nth 1 vars)))
                   "2"
                   (itoa (1+ (- (length vars)
                                (length (member (car (cab:drawn vars))
                                                vars)))))))
      (princ "\n\n  Click the outline you want to keep, or type its number.")
      (princ "\n  Redo refits with new settings, and lets you omit points first.")
      (initget "1 2 3 All None Redo")
      (setq pick (getkword
                   (strcat "\n  Keep which fit - click one, or"
                           " [1/2/3/All/None/Redo] <" dflt ">: ")))
      (if (null pick)
        ;; no keyword typed: give them a click, and fall back to the
        ;; default above
        (progn
          (setq sel (entsel (strcat "\n  Pick the outline to keep (or Enter for "
                                    dflt "): ")))
          (if sel
            (progn
              (setq picked (car sel) i 1)
              (foreach v vars
                (if (or (eq picked (cadr v))
                        (member picked (nth 4 v)))
                  (setq pick (itoa i)))
                (setq i (1+ i)))
              (if (null pick)
                (progn
                  (princ (strcat "\n  (that is not one of the three - keeping "
                                 dflt ")"))
                  (setq pick dflt))))
            (setq pick dflt))))
      ;; anything not explicitly kept stays registered as scaffolding
      ;; and is swept when the command ends
      (cond
        ((= pick "Redo")
         ;; clear this trio off the screen right away - the caller
         ;; asks its questions and draws a fresh one
         (foreach v vars
           (if (and (cadr v) (entget (cadr v))) (entdel (cadr v)))
           (foreach e (nth 4 v)
             (if (and e (entget e)) (entdel e))))
         (setq res 'REDO))
        ((= pick "All")
         (foreach v (cab:drawn vars)
           (cab:temp-drop (cadr v))
           (foreach e (nth 4 v) (cab:temp-drop e)))
         (princ (strcat "\nKeeping all "
                        (itoa (length (cab:drawn vars)))
                        " that drew, in their preview colours."))
         (princ "\n  (the number labels are kept too - erase them when done)"))
        ((= pick "None")
         (princ "\nAll three erased - nothing was added to the drawing."))
        (T
         (setq idx (atoi pick) i 1)
         (foreach v vars
           (if (= i idx)
             (setq keep v)
             ;; erase the losers now, so the keeper is clear on screen
             ;; while the report is read
             (if (and (cadr v) (entget (cadr v))) (entdel (cadr v))))
           (setq i (1+ i)))
         ;; name the aim that was kept, not just its number - the three
         ;; were built to different ends and the report that follows is
         ;; read against the settings as typed
         (if (and keep (null (cadr keep)))
           (progn
             (princ (strcat "\n  Fit " pick
                            " never drew - there is nothing to keep."))
             (princ "\n  Pick one the table shows on screen.")
             (setq keep nil)))
         (if keep
           (progn
             (princ (strcat "\n  Keeping fit " pick " - "
                            (cadddr (cadddr keep)) "."))
             (cab:temp-drop (cadr keep))
             (cab:set-bylayer (cadr keep))))))
      (if keep
        (progn
          (setq keyed (cab:mark-unheld (caddr keep) (car keep) bb hgt))
          (cab:report (car keep) pts tol allow prior)
          (if keyed
            (progn
              (princ (strcat "\n  " (itoa (length keyed))
                             " point(s) beyond the distance are ringed"
                             " on layer " *CAB-MISS-LAYER*
                             " and listed beside the pool, worst first:"))
              (foreach pr keyed
                (princ (strcat "\n    Pt." (cab:pt-name (cdr pr))
                               "   off by " (rtos (car pr) 4 4))))))))))
  (princ)
  res)

;; Snap a picked point onto the nearest survey point, warning when the
;; pick was nowhere near one (the rule declared walls are held to, used
;; again wherever a Redo re-picks a wall, a corner or a hold).
(defun cab:snap-pick (p dpts / q)
  (setq p (cal:2d p)
        q (cab:nearest p dpts))
  (if (null q)
    p
    (progn
      (if (> (cal:dist p q) (* 3.0 *CAB-TOL*))
        (princ "\n  (picked well away from any survey point - snapped to the nearest one)"))
      q)))

;; ---- the numeric parameters ------------------------------------------
;; Asked identically at the start of a run and again on a Redo -
;; Enter keeps the shown value each time.

;; Maximum distance from a point; remembered in *CAB-TOL*.
(defun cab:ask-tol (/ tol)
  (initget 6)
  (setq tol (getdist (strcat "\n  Maximum distance from a point <"
                             (rtos *CAB-TOL* 2 3) ">: ")))
  (if (null tol) (setq tol *CAB-TOL*))
  (if (> tol *CAB-TOL-MAX*)
    (progn
      (princ (strcat "\n  (more than " (rtos *CAB-TOL-MAX* 2 1)
                     " and the line is no longer a trace of the points"
                     " - using " (rtos *CAB-TOL-MAX* 2 1) ")"))
      (setq tol *CAB-TOL-MAX*)))
  (setq *CAB-TOL* tol)
  tol)

;; Share of the points allowed off the line, returned as a fraction;
;; DEF is the fraction Enter keeps.
(defun cab:ask-pct (def / pct)
  (initget 4)
  (setq pct (getint (strcat "\n  Percent of points allowed off <"
                            (itoa (fix (+ 0.5 (* 100.0 def))))
                            ">: ")))
  (cond
    ((null pct) def)
    ((> pct 100)
     (princ "\n  (more than 100 makes no sense - using 100)")
     1.0)
    (T (/ pct 100.0))))

;; Curve cap; remembered in *CAB-MAX-ARCS* (nil = no cap).
(defun cab:ask-cap (/ mx)
  (initget 4 "None")
  (setq mx (getint (strcat "\n  Maximum curves <"
                           (if *CAB-MAX-ARCS* (itoa *CAB-MAX-ARCS*) "None")
                           ">: ")))
  (cond ((null mx) nil)                            ; Enter: keep as-is
        ((eq 'STR (type mx)) (setq *CAB-MAX-ARCS* nil))
        (T (setq *CAB-MAX-ARCS* mx)))
  *CAB-MAX-ARCS*)

;; ---- redo-time editing of walls and corners --------------------------
;; A Redo may change more than the numbers: straight walls and sharp
;; corners can be added or removed before the refit.  Both editors
;; work on the run-scoped cab-walls / cab-corners lists and keep the
;; dashed markers in step with them.

;; Erase this run's scaffolding markers of one entity type on the
;; marker layer (walls are the LINEs, rings the CIRCLEs), so the set
;; can be redrawn to match an edited declaration list.
(defun cab:sweep-marks (etype / keep en ed)
  (setq keep nil)
  (foreach en cab-temp
    (setq ed (if (and en (entget en)) (entget en)))
    (if (and ed
             (= etype (cdr (assoc 0 ed)))
             (= (strcase *CAB-WALL-LAYER*)
                (strcase (cdr (assoc 8 ed)))))
      (entdel en)
      (setq keep (cons en keep))))
  (setq cab-temp (reverse keep)))

;; Add or remove declared straight walls.  Ends snap to the survey
;; points; each change is confirmed by name and the dashed markers
;; follow.
(defun cab:edit-walls (dpts / ans wp1 wp2 w1 w2 best bd w d)
  (setq ans T)
  (while ans
    (initget "Add Remove Keep")
    (setq ans (getkword (strcat
                "\n  Straight walls (" (itoa (length cab-walls))
                " declared) - [Add/Remove/Keep] <Keep>: ")))
    (cond
      ((= ans "Add")
       (setq cab-phase "picking a straight wall"
             wp1      (getpoint "\n  First end of the straight wall: ")
             wp2      (if wp1 (getpoint wp1 "\n  Second end: ")))
       (if wp2
         (progn
           (setq w1 (cab:snap-pick wp1 dpts)
                 w2 (cab:snap-pick wp2 dpts))
           (if (< (cal:dist w1 w2) *CAB-EXACT-EPS*)
             (princ "\n  (both ends landed on the same survey point - ignored)")
             (progn
               (setq cab-walls (append cab-walls (list (list w1 w2))))
               (cab:temp-add (cab:tag-mine (cab:draw-wall-marker w1 w2)))
               (princ (strcat "\n  wall Pt." (cab:pt-name w1)
                              " - Pt." (cab:pt-name w2) " added")))))))
      ((= ans "Remove")
       (if (null cab-walls)
         (princ "\n  (no straight walls to remove)")
         (progn
           (setq cab-phase "removing a straight wall"
                 wp1      (getpoint "\n  Pick near the straight wall to remove: "))
           (if wp1
             (progn
               (setq wp1 (cal:2d wp1) best nil bd nil)
               (foreach w cab-walls
                 (setq d (cab:seg-dist wp1 (list (car w) (cadr w) 0.0)))
                 (if (or (null bd) (< d bd)) (setq best w bd d)))
               (setq cab-walls (cab:remove best cab-walls))
               ;; redraw the wall markers to match what is left
               (cab:sweep-marks "LINE")
               (foreach w cab-walls
                 (cab:temp-add (cab:tag-mine
                   (cab:draw-wall-marker (car w) (cadr w)))))
               (princ (strcat "\n  wall Pt." (cab:pt-name (car best))
                              " - Pt." (cab:pt-name (cadr best))
                              " removed")))))))
      (T (setq ans nil)))))

;; Add or remove declared sharp corners the same way.  (The corners
;; the fitter finds by itself - turns over *CAB-CORNER-ANG* - are not
;; declarations and cannot be removed here.)
(defun cab:edit-corners (dpts / ans wp1 w1 best bd w)
  (setq ans T)
  (while ans
    (initget "Add Remove Keep")
    (setq ans (getkword (strcat
                "\n  Sharp corners (" (itoa (length cab-corners))
                " declared) - [Add/Remove/Keep] <Keep>: ")))
    (cond
      ((= ans "Add")
       (setq cab-phase "picking a sharp corner"
             wp1      (getpoint "\n  Corner point: "))
       (if wp1
         (progn
           (setq w1 (cab:snap-pick wp1 dpts))
           (if (cab:memb w1 cab-corners)
             (princ "\n  (that corner is already declared)")
             (progn
               (setq cab-corners (append cab-corners (list w1)))
               (cab:temp-add (cab:tag-mine (cab:draw-corner-marker w1)))
               (princ (strcat "\n  corner Pt." (cab:pt-name w1)
                              " added")))))))
      ((= ans "Remove")
       (if (null cab-corners)
         (princ "\n  (no declared corners to remove)")
         (progn
           (setq cab-phase "removing a sharp corner"
                 wp1      (getpoint "\n  Pick the declared corner to remove: "))
           (if wp1
             (progn
               (setq wp1 (cal:2d wp1) best nil bd nil)
               (foreach w cab-corners
                 (if (or (null bd) (< (cal:dist wp1 w) bd))
                   (setq best w bd (cal:dist wp1 w))))
               (setq cab-corners (cab:remove best cab-corners))
               ;; the rings share their look with the omit markers;
               ;; redraw the corner and hold rings (spent omit rings
               ;; go quietly - the omissions already happened)
               (cab:sweep-marks "CIRCLE")
               (foreach w cab-corners
                 (cab:temp-add (cab:tag-mine (cab:draw-corner-marker w))))
               (foreach w cab-holds
                 (cab:temp-add (cab:tag-mine (cab:draw-hold-marker w))))
               (princ (strcat "\n  corner Pt." (cab:pt-name best)
                              " removed")))))))
      (T (setq ans nil)))))

;; Add or remove HELD points the same way.
(defun cab:edit-holds (dpts / ans wp1 w1 best bd w)
  (setq ans T)
  (while ans
    (initget "Add Remove Keep")
    (setq ans (getkword (strcat
                "\n  Held points (" (itoa (length cab-holds))
                " declared) - [Add/Remove/Keep] <Keep>: ")))
    (cond
      ((= ans "Add")
       (setq cab-phase "picking a held point"
             wp1      (getpoint "\n  Point to hold exactly: "))
       (if wp1
         (progn
           (setq w1 (cab:snap-pick wp1 dpts))
           (if (cab:memb w1 cab-holds)
             (princ "\n  (that point is already held)")
             (progn
               (setq cab-holds (append cab-holds (list w1)))
               (cab:temp-add (cab:tag-mine (cab:draw-hold-marker w1)))
               (princ (strcat "\n  held Pt." (cab:pt-name w1)
                              " added")))))))
      ((= ans "Remove")
       (if (null cab-holds)
         (princ "\n  (no held points to remove)")
         (progn
           (setq cab-phase "removing a held point"
                 wp1      (getpoint "\n  Pick the held point to release: "))
           (if wp1
             (progn
               (setq wp1 (cal:2d wp1) best nil bd nil)
               (foreach w cab-holds
                 (if (or (null bd) (< (cal:dist wp1 w) bd))
                   (setq best w bd (cal:dist wp1 w))))
               (setq cab-holds (cab:remove best cab-holds))
               ;; redraw the rings to match what is left
               (cab:sweep-marks "CIRCLE")
               (foreach w cab-corners
                 (cab:temp-add (cab:tag-mine (cab:draw-corner-marker w))))
               (foreach w cab-holds
                 (cab:temp-add (cab:tag-mine (cab:draw-hold-marker w))))
               (princ (strcat "\n  held Pt." (cab:pt-name best)
                              " released")))))))
      (T (setq ans nil)))))

;; Which build is loaded - the first thing to check when a run does
;; something the notes above say it should not.
(defun c:CABHDVER ()
  (princ (strcat "\nCABHD " *cabhd-version* " loaded."))
  (princ))

;; ---- CABHD: the perimeter, and nothing but ---------------------------
(defun c:CABHD ( / tol ans go wp1 wp2 rawwalls rawcnrs rawholds w w1 w2
                    ss i en ed lay typ ext nunsup nocs dall cut0 ent
                    segs pts dpts allow loop tour ok stale npt
                    again ring cab-cut cab-allpts cab-ptkeys cab-numbered
                    cab-omitted cab-miss-pct cab-walls cab-corners
                    cab-holds cab-temp cab-ptnames
                    *error* cab-old-err cab-phase)
  ;; report which step failed if anything goes wrong, sweep away any
  ;; preview geometry drawn so far, then restore the old handler - a
  ;; cancelled run must not leave dashed markers or candidate outlines
  ;; lying around
  (setq cab-temp    nil
        cab-numbered 0
        cab-old-err *error*
        *error*
          (lambda (m)
            ;; ALWAYS say where it stopped, cancels included: a
            ;; command that vanishes without a word is the one thing
            ;; nobody can debug from the other end of a phone
            (princ (strcat "\nCABHD stopped while "
                           (if cab-phase cab-phase "starting up")
                           (if (and m (not (wcmatch (strcase m)
                                    "*BREAK*,*CANCEL*,*QUIT*,*EXIT*")))
                             (strcat " -- " m)
                             " (cancelled).")))
            (cab:temp-clear)
            (setq *error* cab-old-err)
            (princ)))

  ;; sweep leftovers from a run that was interrupted before it could
  ;; tidy up after itself
  (setq stale (cab:purge-mine *CAB-WALL-LAYER*))
  (if (> stale 0)
    (princ (strcat "\nCABHD: cleared " (itoa stale)
                   " leftover marker(s) from layer " *CAB-WALL-LAYER*
                   ".")))

  (princ "\n\nCABHD - fit a pool perimeter through the surveyed points,")
  (princ "\n        up to the point number where the edge stops.")

  ;; -- step 1: how close must the line stay to the points? ----------
  ;; This is the one prompt people misread, so it says in plain words
  ;; what the number means and which way it moves the result.
  ;; initget 6 refuses zero and negative values - a zero tolerance
  ;; would silently collapse the fit into single-point stubs.
  (setq cab-phase "reading the tolerance")
  (princ "\n\n  Step 1 of 8 - how far may the fitted line sit from a survey point?")
  (princ "\n  Type a distance in drawing units (1 = one inch, 2 at most), or")
  (princ "\n  pick two points in the drawing to measure one.")
  (princ "\n  Smaller = hugs the points.  Bigger = smoother, with fewer curves.")
  (setq tol (cab:ask-tol))

  ;; -- step 2: how many of the points may sit off the line? ---------
  ;; Enter means the standard share; the answer is per run, on purpose.
  (setq cab-phase "reading the miss percentage")
  (princ "\n\n  Step 2 of 8 - what percent of the points may sit OFF the line")
  (princ "\n  (off, but still within the distance above)?")
  (princ (strcat "\n  Press Enter for the standard "
                 (itoa (fix (+ 0.5 (* 100.0 *CAB-MISS-PCT*))))
                 " percent."))
  (setq cab-miss-pct (cab:ask-pct *CAB-MISS-PCT*))

  ;; -- step 3: optional cap on how many curves the result may use ---
  (setq cab-phase "reading the curve limit")
  (princ "\n\n  Step 3 of 8 - limit how many curves the result may use?")
  (princ "\n  Type a whole number, or None for no limit.")
  (cab:ask-cap)

  ;; -- step 4: any dead-straight walls to declare? ------------------
  ;; Each declared wall is marked with a dashed line right away and
  ;; comes out of the fit as a straight LINE between those two survey
  ;; points, no matter what the arcs around it are doing.
  (setq cab-phase "asking about straight lines")
  (princ "\n\n  Step 4 of 8 - does the pool edge have any dead-straight walls?")
  (princ "\n  If Yes you will pick the two end points of each (snap to the")
  (princ "\n  survey points); a dashed line marks each declared wall.")
  (princ "\n  Pick them among the points that trace the EDGE - a wall anchored")
  (princ "\n  past the cutoff asked at step 8 is dropped with the points it used.")
  (initget "Yes No")
  (setq ans      (getkword "\n  Any straight lines? [Yes/No] <No>: ")
        rawwalls nil)
  (if (= ans "Yes")
    (progn
      (setq go T)
      (while go
        (setq cab-phase "picking a straight wall"
              wp1       (getpoint "\n  First end of the straight wall: "))
        (if wp1
          (progn
            (setq wp2 (getpoint wp1 "\n  Second end: "))
            (if wp2
              (progn
                (setq wp1 (cal:2d wp1) wp2 (cal:2d wp2))
                ;; the dashed marker is scaffolding: it confirms what
                ;; you declared, and goes when the command ends
                (cab:temp-add (cab:tag-mine (cab:draw-wall-marker wp1 wp2)))
                (setq rawwalls (cons (list wp1 wp2) rawwalls))
                (initget "Yes No")
                (if (/= (getkword "\n  Another straight line? [Yes/No] <No>: ")
                        "Yes")
                  (setq go nil)))
              (setq go nil)))
          (setq go nil)))
      (setq rawwalls (reverse rawwalls))
      (if rawwalls
        (princ (strcat "\n  " (itoa (length rawwalls))
                       " straight wall(s) noted - the dashed markers on "
                       *CAB-WALL-LAYER*
                       " clear themselves when the command finishes.")))))

  ;; -- step 5: any sharp corners to declare? ------------------------
  ;; The fitter finds obvious corners itself (turns over
  ;; *CAB-CORNER-ANG*), but a gentler one still reads as a corner on
  ;; site.  A declared point is exempt from the tangency rule: the fit
  ;; breaks there instead of rounding it off.
  (setq cab-phase "asking about sharp corners")
  (princ "\n\n  Step 5 of 8 - are there any sharp corners the fit must not round off?")
  (princ "\n  Obvious ones are found automatically; declare the gentler ones here.")
  (princ "\n  If Yes you will pick each corner point (snap to the survey points).")
  (initget "Yes No")
  (setq ans     (getkword "\n  Any sharp corners? [Yes/No] <No>: ")
        rawcnrs nil)
  (if (= ans "Yes")
    (progn
      (setq go T)
      (while go
        (setq cab-phase "picking a sharp corner"
              wp1       (getpoint "\n  Corner point (Enter when done): "))
        (if wp1
          (progn
            (setq wp1     (cal:2d wp1)
                  rawcnrs (cons wp1 rawcnrs))
            (cab:temp-add (cab:tag-mine (cab:draw-corner-marker wp1))))
          (setq go nil)))
      (setq rawcnrs (reverse rawcnrs))
      (if rawcnrs
        (princ (strcat "\n  " (itoa (length rawcnrs))
                       " corner(s) noted - the markers clear themselves"
                       " when the command finishes.")))))

  ;; -- step 6: any points that must be held absolutely? -------------
  ;; Control shots and tie-ins are surveyed as exact positions: a held
  ;; point always ends a span, so the fit passes through it exactly
  ;; and the miss allowance can never write it off.
  (setq cab-phase "asking about held points")
  (princ "\n\n  Step 6 of 8 - any points that must be held ABSOLUTELY?")
  (princ "\n  A held point can never be fudged: the line passes through it")
  (princ "\n  exactly, in every candidate.  If Yes you will pick each one")
  (princ "\n  (snap to the survey points); a small dashed ring marks it.")
  (initget "Yes No")
  (setq ans      (getkword "\n  Any held points? [Yes/No] <No>: ")
        rawholds nil)
  (if (= ans "Yes")
    (progn
      (setq go T)
      (while go
        (setq cab-phase "picking a held point"
              wp1       (getpoint "\n  Point to hold exactly (Enter when done): "))
        (if wp1
          (progn
            (setq wp1      (cal:2d wp1)
                  rawholds (cons wp1 rawholds))
            (cab:temp-add (cab:tag-mine (cab:draw-hold-marker wp1))))
          (setq go nil)))
      (setq rawholds (reverse rawholds))
      (if rawholds
        (princ (strcat "\n  " (itoa (length rawholds))
                       " held point(s) noted - the markers clear"
                       " themselves when the command finishes.")))))

  ;; -- step 7: the selection ----------------------------------------
  ;; Select the WHOLE survey - the cutoff at step 8 is what decides how
  ;; much of it the perimeter uses, and it can be moved at a Redo, so
  ;; there is nothing to gain by window-selecting carefully here.
  (princ "\n\n  Step 7 of 8 - select the survey points (POINTS layer or ab_pt")
  (princ "\n  blocks) and, if you have one, the POOL perimeter or ordering sketch.")
  (princ "\n  Take the whole survey - step 8 says how much of it is the pool.")
  (princ "\n  Select objects: ")
  (setq cab-phase "waiting for the selection")
  ;; only entity types this command can actually read, so a sloppy
  ;; crossing window over dimensions, hatches or text is harmless.
  ;; SPLINE and ELLIPSE are let in ON PURPOSE - not to fit them, but
  ;; so the classifier below can name them in a useful message.
  (setq ss (ssget '((0 . "POINT,INSERT,LINE,ARC,CIRCLE,LWPOLYLINE,POLYLINE,SPLINE,ELLIPSE"))))
  (if (null ss)
    (princ "\nNothing usable selected (points, and optionally POOL lines/arcs/polylines).")
    (progn
      ;; -- sort the selection into perimeter segments and points -----
      (setq cab-phase "reading the selected entities")
      (setq segs nil pts nil i 0 nunsup 0 nocs 0
            npt 0 cab-ptnames nil cab-ptkeys nil cab-allpts nil
            cab-omitted nil cab-cut nil)
      (while (< i (sslength ss))
        (setq en  (ssname ss i)
              ed  (entget en)
              lay (strcase (cdr (assoc 8 ed)))
              typ (cdr (assoc 0 ed))
              ext (cdr (assoc 210 ed))
              i   (1+ i))
        ;; geometry drawn in a tilted UCS reads back in its own plane,
        ;; so a flat 2D fit of it would be wrong - count and warn
        (if (and ext (< (abs (caddr ext)) 0.999)) (setq nocs (1+ nocs)))
        (cond
          ;; survey points stored as block references (e.g. "ab_pt"):
          ;; a block with this name is ALWAYS a point, on any layer, and
          ;; its insertion point is taken as the location (the blocks are
          ;; never exploded - non-destructive).  Checked first so such
          ;; blocks are never mistaken for perimeter geometry.
          ((and (= typ "INSERT")
                (= (strcase (cdr (assoc 2 ed))) (strcase *CAB-POINT-BLOCK*)))
           (cab:add-point (cal:2d (cdr (assoc 10 ed)))
                          (cab:block-number en)))
          ;; curve types we cannot fit, sitting on the POOL layer: count
          ;; them so the user gets told what to do, instead of a
          ;; mystifying "the perimeter does not close" later on
          ((and (= lay (strcase *CAB-POOL-LAYER*))
                (member typ '("SPLINE" "ELLIPSE")))
           (setq nunsup (1+ nunsup)))
          ;; CABHD's own stamped work on the POOL layer is never read
          ;; back as a guide - nor is ABHD's, whose pool-bottom lines
          ;; live there too and would wreck a fit read as perimeter
          ((and (= lay (strcase *CAB-POOL-LAYER*))
                (or (assoc -3 (entget en '("CABHD")))
                    (assoc -3 (entget en '("ABHD")))))
           nil)
          ;; perimeter / ordering sketch on the POOL layer
          ((= lay (strcase *CAB-POOL-LAYER*))
           (setq segs (append segs (cab:ent-segs en))))
          ;; plain POINT entities on the POINTS layer
          ((and (= lay (strcase *CAB-POINT-LAYER*)) (= typ "POINT"))
           (cab:add-point (cal:2d (cdr (assoc 10 ed))) nil))
          ;; any other block dropped on the POINTS layer -> a point too
          ((and (= typ "INSERT") (= lay (strcase *CAB-POINT-LAYER*)))
           (cab:add-point (cal:2d (cdr (assoc 10 ed)))
                          (cab:block-number en)))))
      (setq cab-allpts (reverse cab-allpts)      ; selection order
            dall       (if pts (cal:dedupe pts *CAB-EXACT-EPS*)))
      (if (> nunsup 0)
        (princ (strcat "\nCABHD: warning - " (itoa nunsup)
                       " SPLINE/ELLIPSE object(s) on layer "
                       *CAB-POOL-LAYER*
                       " were ignored (only lines, arcs, circles and"
                       " polylines can be read - explode or convert"
                       " them first).")))
      (if (> nocs 0)
        (princ (strcat "\nCABHD: warning - " (itoa nocs)
                       " selected object(s) are not drawn in the world"
                       " plane; the fit is flat (XY) and may be wrong."
                       "  Set UCS to World and flatten them first.")))
      (cond
        ((null pts)
         (princ (strcat "\nNo survey points found (looked for POINT entities on layer "
                        *CAB-POINT-LAYER* " and \"" *CAB-POINT-BLOCK*
                        "\" block insertions).")))
        ((and (null segs) (< (length dall) 3))
         (princ "\nPoints-only mode needs at least 3 distinct points."))
        (T
         ;; -- step 8: how far up the survey is the pool? -------------
         ;; The rule CABHD exists for.  Everything past the answer is
         ;; out of the perimeter entirely, so the fit never chases a
         ;; step, a bench or a depth shot it was never meant to trace.
         (setq cab-phase "reading the point cutoff")
         (princ "\n\n  Step 8 of 8 - how far up the point numbers does the pool edge run?")
         (princ "\n  A survey usually carries on past the pool - steps, benches, deck,")
         (princ "\n  depth shots - all numbered in the same run.  Everything past the")
         (princ "\n  number you give is left out of the perimeter: not fitted, not")
         (princ "\n  counted against the miss allowance, never reported as a miss.")
         (if (= cab-numbered 0)
           (princ (strcat "\n  NOTE: none of these points carry a "
                          *CAB-PT-TAG*
                          " attribute, so they are counted in the"
                          "\n  order they came out of the drawing -"
                          " usually the order they were created,"
                          "\n  but check the result before trusting it.")))
         (setq cab-cut  (cab:ask-cut dall nil)
               cab-phase "applying the point cutoff"
               pts     (cab:live-pts)
               dpts    (cal:dedupe pts *CAB-EXACT-EPS*))
         (if cab-cut
           (princ (strcat "\n  Up to Pt." (itoa cab-cut) " - "
                          (itoa (length dpts)) " point(s) in the perimeter, "
                          (itoa (- (length dall) (length dpts)))
                          " left out."))
           (princ (strcat "\n  Using all " (itoa (length dpts))
                          " point(s).")))
         ;; the miss allowance: this share of the points (the answer to
         ;; step 2, rounded UP to a whole point) may sit off the result
         ;; by up to TOL.  It is a share of the points the cutoff KEPT -
         ;; the ones it dropped buy no slack, since the line was never
         ;; asked to go near them
         (setq allow (cal:ceil (* (cab:misspct) (length dpts))))
         ;; snap the declared straight-wall ends onto actual survey
         ;; points - arc and wall endpoints always sit ON points
         (setq cab-phase "checking the declared walls, corners and holds"
               cab-walls nil)
         (foreach w rawwalls
           (setq w1 (cab:nearest (car w) dpts)
                 w2 (cab:nearest (cadr w) dpts))
           (cond
             ((or (cab:cut-away-p (car w) dall dpts)
                  (cab:cut-away-p (cadr w) dall dpts))
              (princ "\n  (a declared wall was anchored past the cutoff - that wall is ignored)"))
             ((or (null w1) (null w2)) nil)
             ((< (cal:dist w1 w2) *CAB-EXACT-EPS*)
              (princ "\n  (both ends of a declared wall landed on the same survey point - that wall is ignored)"))
             (T
              (if (or (> (cal:dist (car w) w1) (* 3.0 tol))
                      (> (cal:dist (cadr w) w2) (* 3.0 tol)))
                (princ "\n  (a declared wall end was picked well away from any survey point - snapped to the nearest one)"))
              (setq cab-walls (cons (list w1 w2) cab-walls)))))
         (setq cab-walls (reverse cab-walls))
         ;; declared corners snap onto survey points the same way
         (setq cab-corners nil)
         (foreach w rawcnrs
           (setq w1 (cab:nearest w dpts))
           (cond
             ((cab:cut-away-p w dall dpts)
              (princ "\n  (a declared corner was picked past the cutoff - it is ignored)"))
             (w1
              (if (> (cal:dist w w1) (* 3.0 tol))
                (princ "\n  (a declared corner was picked well away from any survey point - snapped to the nearest one)"))
              (setq cab-corners (cons w1 cab-corners)))))
         (setq cab-corners (reverse cab-corners))
         ;; held points snap onto survey points the same way; duplicates
         ;; collapse to one
         (setq cab-holds nil)
         (foreach w rawholds
           (setq w1 (cab:nearest w dpts))
           (cond
             ((cab:cut-away-p w dall dpts)
              (princ "\n  (a held point was picked past the cutoff - it is ignored)"))
             (w1
              (if (> (cal:dist w w1) (* 3.0 tol))
                (princ "\n  (a held point was picked well away from any survey point - snapped to the nearest one)"))
              (if (not (cab:memb w1 cab-holds))
                (setq cab-holds (cons w1 cab-holds))))))
         (setq cab-holds (reverse cab-holds))
         (if (> (length dpts) 150)
           (princ (strcat "\nCABHD: " (itoa (length dpts))
                          " points - ordering and fitting will take a"
                          " little while, please wait...")))
         ;; work out the mode, then hand all three modes to the same
         ;; compare-and-choose step
         (setq tour nil loop nil ok T)
         ;; below three points there is no perimeter to draw in ANY
         ;; mode; say so here rather than let the fitter hand back an
         ;; outline AutoCAD will refuse
         (if (< (length dpts) 3)
           (progn
             (princ (strcat "\nCABHD: only " (itoa (length dpts))
                            " point(s) are in the fit and a perimeter"
                            " needs at least 3."))
             (princ "\n  Run it again and give a higher cutoff, or All.")
             (setq ok nil)))
         (cond
           ((null ok) nil)
           ((null segs)
            ;; ---- POINTS-ONLY: order the points ourselves ----------
            (princ "\nNo POOL geometry selected - ordering the points automatically.")
            (setq cab-phase "ordering the points"
                  tour      (cab:order-points dpts)))
           ((null (setq loop (cab:chain segs)))
            (setq ok nil))                     ; cab:chain said why
           ((not (cab:has-arcs loop))
            ;; ---- ORDERING SKETCH: the drawn loop is all straight
            ;; lines, so it only tells us the ORDER of the points;
            ;; the shape itself comes from the points
            (if (< (length dpts) 3)
              (progn
                (princ (strcat "\nThe lines-only POOL sketch only orders"
                               " the points, and at least 3 distinct"
                               " points are needed to build a shape."))
                (setq ok nil))
              (progn
                (princ "\nPOOL sketch is lines only - using it just to order the points.")
                (setq cab-phase "following the sketch order"
                      tour      (cab:loop-order loop dpts)))))
           (T
            (princ "\nUsing the drawn POOL perimeter as the guide.")
            (princ "\n  (only the part of it the kept points reach is re-fitted)")
            (if cab-walls
              (princ (strcat "\n  (declared straight walls only steer"
                             " the points-built fit; here your drawn"
                             " straight segments are already kept)")))
            (if cab-holds
              (princ (strcat "\n  (held points only bind the"
                             " points-built fit; the drawn shape wins"
                             " here - the report flags any held point"
                             " the kept fit missed)")))))
         (if ok
           (progn
             (setq again T)
             (while again
               (setq again nil)
               (if (eq 'REDO (cab:compare tour loop pts dpts tol allow))
                 (progn
                   ;; -- redo: maybe omit points, move the cutoff,
                   ;; re-ask the numbers, draw a fresh trio ---------
                   (setq cab-phase "picking points to omit")
                   (princ "\n\nRedoing the fit.  Any points to leave out this time?")
                   (princ "\n  Pick each one (Enter for none) - mis-shots, duplicates, or")
                   (princ "\n  anything the line should not chase; each gets a dashed ring.")
                   (princ "\n  (this is for strays one at a time - the cutoff, asked next,")
                   (princ "\n  is what moves the end of the pool edge.)")
                   (if cab-omitted
                     (princ (strcat "\n  " (itoa (length cab-omitted))
                                    " point(s) are already out -"
                                    " picking one of those puts it"
                                    " BACK IN.")))
                   (while (setq wp1 (getpoint
                                      "\n  Point to omit - or a ringed one to restore (Enter when done): "))
                     (setq wp1 (cal:2d wp1)
                           w1  (cab:nearest wp1 dpts)
                           w2  (cab:nearest wp1 (mapcar 'car cab-omitted)))
                     (cond
                       ;; nearer to an already-omitted point: this
                       ;; click un-omits it - the point and its
                       ;; duplicates rejoin the fit, its ring goes
                       ((and w2 (or (null w1)
                                    (<= (cal:dist wp1 w2)
                                        (cal:dist wp1 w1))))
                        (setq ent (assoc w2 cab-omitted))
                        (if (and (cadr ent) (entget (cadr ent)))
                          (progn
                            (cab:temp-drop (cadr ent))
                            (entdel (cadr ent))))
                        (setq cab-omitted (cab:remove ent cab-omitted)
                              pts         (cab:live-pts)
                              dpts        (cal:dedupe pts *CAB-EXACT-EPS*))
                        (princ (strcat "  - Pt." (cab:pt-name w2)
                                       " back in")))
                       ;; otherwise omit: pull it - and its duplicates
                       ;; - out of the fit, the stats and the miss
                       ;; allowance alike, and remember how to undo it
                       (w1
                        (setq ring (cab:temp-add (cab:tag-mine
                                     (cab:draw-corner-marker w1)))
                              cab-omitted (cons (list w1 ring) cab-omitted)
                              pts         (cab:live-pts)
                              dpts        (cal:dedupe pts *CAB-EXACT-EPS*))
                        (princ (strcat "  - omitting Pt."
                                       (cab:pt-name w1))))))
                   ;; -- the cutoff can move too: the edge may run
                   ;; further up the survey than the first answer said,
                   ;; or stop short of it ---------------------------
                   (setq cab-phase "reading the point cutoff"
                         cut0      cab-cut)
                   (princ "\n\n  How far up the point numbers does the pool edge run?")
                   (princ "\n  Enter keeps the cutoff as it is; All puts every point back.")
                   (setq cab-cut (cab:ask-cut dall cab-cut))
                   (if (not (equal cut0 cab-cut))
                     (setq pts  (cab:live-pts)
                           dpts (cal:dedupe pts *CAB-EXACT-EPS*)))
                   (cab:prune-decls dpts)
                   (princ (strcat "\n  "
                                  (if cab-cut
                                    (strcat "Up to Pt." (itoa cab-cut))
                                    "Every point")
                                  ", "
                                  (if cab-omitted
                                    (strcat (itoa (length cab-omitted))
                                            " omitted, ")
                                    "")
                                  (itoa (length dpts))
                                  " point(s) in the fit."))
                   (if (< (length dpts) 3)
                     (princ "\nToo few points remain for a fit - nothing redone.")
                     (progn
                       ;; walls and corners may change for the retry
                       (princ "\n\n  Straight walls and sharp corners can change too -")
                       (princ "\n  Enter keeps each list as it is.")
                       (setq cab-phase "editing straight walls")
                       (cab:edit-walls dpts)
                       (setq cab-phase "editing sharp corners")
                       (cab:edit-corners dpts)
                       (setq cab-phase "editing held points")
                       (cab:edit-holds dpts)
                       (princ "\n\n  New settings - Enter keeps each one as it is.")
                       (setq cab-phase "reading the tolerance"
                             tol       (cab:ask-tol))
                       (setq cab-phase "reading the miss percentage"
                             cab-miss-pct (cab:ask-pct cab-miss-pct))
                       (setq cab-phase "reading the curve limit")
                       (cab:ask-cap)
                       (setq allow (cal:ceil (* (cab:misspct)
                                                (length dpts))))
                       ;; the point order must forget everything the
                       ;; omit list and the cutoff took out
                       (cond
                         ((null loop)
                          (setq cab-phase "ordering the points"
                                tour      (cab:order-points dpts)))
                         ((not (cab:has-arcs loop))
                          (setq tour (cab:loop-order loop dpts))))
                       (setq again T))))))))))))
  ;; sweep the dashed wall markers and any candidate the user did not
  ;; keep - the command tidies up after itself
  (cab:temp-clear)
  ;; and sign off, naming the last step reached: a run that ends with
  ;; nothing on screen still has to say that it ended on purpose
  (princ (strcat "\nCABHD done (last step: "
                 (if cab-phase cab-phase "start") ")."))
  (setq *error* cab-old-err)   ; restore the previous error handler
  (princ))

;; ----------------------------------------------------------------------
(princ (strcat "\nCABHD " *cabhd-version*
               " loaded.  Type CABHD to fit a pool perimeter through"
               " the surveyed"))
(princ "\npoints, up to the point number where the pool edge stops.")
(princ "\nCABHDVER prints the version.")
(princ)


;;; ======================================================================
;;; >>> AUTOBEAD.lsp
;;; ======================================================================

;;; ==========================================================================
;;; AUTOBEAD.lsp
;;; --------------------------------------------------------------------------
;;; Commands:
;;;   AUTOBEAD          - bead the selected POOL lines
;;;   TUTORIALAUTOBEAD  - guided walkthrough (read it, or watch a live demo)
;;;   AUTOBEADVER       - report which version is loaded
;;;
;;; SHARED BUILD: requires CALOFIN-LIB.lsp (load via CALOFIN-LOADER.lsp).
;;; Generic helpers live there under cal: - see STANDARDS.md.
;;;
;;; Select POOL lines to "bead" (LINEs, ARCs, and polylines on any POOL*
;;; layer), then click the side to bead toward.  The selection is copied,
;;; joined into continuous chains, and each chain is offset 2" toward the
;;; clicked side using AutoCAD's native offset engine, so corners resolve
;;; automatically:
;;;   - convex (outside) corners have the excess trimmed
;;;   - concave (inside) corners are extended to meet
;;;   - arc / radius corners offset as true concentric arcs
;;;
;;; Step lines - selected lines that cross the pool, touching walls at both
;;; ends - are recognized automatically and always bead full length.
;;;
;;; After the direction click, AUTOBEAD asks whether the side walls are
;;; beaded.  Answer Yes and click each step that has beaded side walls:
;;; each click assumes its breakline - the next step line from the click
;;; in the direction the bead is heading (toward the direction click).
;;; The wall bead is cut flush at that line, kept on the clicked side,
;;; and removed everywhere else.  Answer No to bead every selected wall
;;; full length.
;;;
;;; The finished beads land on the "Bead Track" layer.  The original pool
;;; geometry is never modified, and the whole run undoes with one U.
;;;
;;; Tunables: see the AUTOBEAD SETTINGS block below.
;;;
;;; --------------------------------------------------------------------------
;;; VERSION
;;;   This file ships under two names with identical contents:
;;;     AUTOBEAD.lsp                  - static name, for appload / startup
;;;     AUTOBEAD_MMDDYY_REV##.lsp     - dated name, so a stack can be
;;;                                     identified at a glance
;;;   Both report the same revision, so AUTOBEADVER tells you what someone
;;;   is actually running regardless of which filename they loaded.  The
;;;   filename's REV## is the version below with the dot dropped
;;;   (v0.4 -> REV04).  Regenerate the dated copy with
;;;   python3 tools/release_lisp.py -- do not hand-copy, or the two
;;;   will drift.
;;; ==========================================================================

(vl-load-com)

;; ---- AUTOBEAD SETTINGS ----------------------------------------------------

(setq *autobead-version* "v0.7"      ; revision stamp; the dated twin is
                                     ; named for it (v0.4 -> REV04)
      *autobead-offset* 2.0          ; bead offset, drawing units (2 = 2")
      *autobead-layer*  "Bead Track" ; output layer
      *autobead-filter* "POOL*"      ; selectable source layers
      *autobead-fuzz*   0.001)       ; endpoint join tolerance

;; ---- helpers --------------------------------------------------------------

(defun autobead-copy (e / o c)
  ;; Duplicate an entity in place and return the new ename (nil on failure).
  ;; This deliberately avoids the COPY command: COPY's point input depends on
  ;; the base-point / displacement prompt sequence and on the current copy
  ;; mode, so a mis-timed response silently translates the duplicate instead
  ;; of leaving it put.  vla-Copy always duplicates in place.
  (setq o (vlax-ename->vla-object e)
        c (vl-catch-all-apply 'vla-Copy (list o)))
  (if (vl-catch-all-error-p c)
    nil
    (vlax-vla-object->ename c)))

(defun autobead-minpt (e / o mn mx)
  ;; Lower-left corner of an entity's bounding box, or nil if unavailable.
  (setq o (vlax-ename->vla-object e))
  (if (vl-catch-all-error-p
        (vl-catch-all-apply 'vla-GetBoundingBox (list o 'mn 'mx)))
    nil
    (vlax-safearray->list mn)))

(defun autobead-inplace-p (src new / a b)
  ;; T if 'new' really did land on top of 'src'.  Guards against any future
  ;; copy path quietly displacing the geometry.
  (setq a (autobead-minpt src)
        b (autobead-minpt new))
  (or (null a) (null b) (< (distance a b) 1e-6)))

(defun autobead-gap (src bead / len p q)
  ;; Measured perpendicular gap between a finished bead and the chain it came
  ;; from, sampled at the bead's midpoint.  Purely diagnostic: it reports what
  ;; the offset actually produced rather than what it was asked for.
  (setq len (vl-catch-all-apply 'vlax-curve-getDistAtParam
              (list bead (vlax-curve-getEndParam bead))))
  (if (or (vl-catch-all-error-p len) (null len))
    nil
    (progn
      (setq p (vl-catch-all-apply 'vlax-curve-getPointAtDist
                (list bead (/ len 2.0))))
      (if (or (vl-catch-all-error-p p) (null p))
        nil
        (progn
          (setq q (vl-catch-all-apply 'vlax-curve-getClosestPointTo
                    (list src p)))
          (if (or (vl-catch-all-error-p q) (null q))
            nil
            (distance p q)))))))

(defun autobead-layers (ss / i lay res)
  ;; Distinct layer names present in a selection set.
  (setq res '() i 0)
  (while (< i (sslength ss))
    (setq lay (cdr (assoc 8 (entget (ssname ss i)))))
    (if (not (member lay res)) (setq res (cons lay res)))
    (setq i (1+ i)))
  (reverse res))

(defun autobead-newents (mark / e res)
  ;; Every entity added to the database after 'mark' that is still alive.
  (setq res '()
        e   (if mark (entnext mark) (entnext)))
  (while e
    (if (entget e) (setq res (cons e res)))
    (setq e (entnext e)))
  (reverse res))

(defun autobead-flush ()
  ;; Safety valve: if an internal command was left waiting for input
  ;; (e.g. OFFSET rejected a pick), feed it Enters until it terminates.
  (while (> (getvar "CMDACTIVE") 0) (command "")))

(defun autobead-ensure-layer (name / def flags)
  ;; Create the target layer if missing; thaw / unlock it if it exists
  ;; frozen or locked so the beads are visible and editable.
  (if (setq def (tblsearch "LAYER" name))
    (progn
      (setq flags (cdr (assoc 70 def)))
      (if (= 1 (logand 1 flags))                 ; frozen
        (command "._-layer" "_thaw" name ""))
      (if (= 4 (logand 4 flags))                 ; locked
        (command "._-layer" "_unlock" name "")))
    (entmake (list '(0 . "LAYER")
                   '(100 . "AcDbSymbolTableRecord")
                   '(100 . "AcDbLayerTableRecord")
                   (cons 2 name)
                   (cons 70 0)
                   (cons 62 1)                   ; color: red
                   (cons 6 "Continuous")))))

;; ---- side-wall geometry helpers -------------------------------------------

(defun autobead-curve-end (e which / p)
  ;; Start or end point of a curve, or nil.  which: 'start or 'end.
  (setq p (vl-catch-all-apply
            (if (eq which 'start)
              'vlax-curve-getStartPoint
              'vlax-curve-getEndPoint)
            (list e)))
  (if (vl-catch-all-error-p p) nil p))

(defun autobead-midpt-of (e / ep len p)
  ;; Point halfway along a curve's length, or nil.
  (setq ep (vl-catch-all-apply 'vlax-curve-getEndParam (list e)))
  (if (vl-catch-all-error-p ep)
    nil
    (progn
      (setq len (vl-catch-all-apply 'vlax-curve-getDistAtParam (list e ep)))
      (if (or (vl-catch-all-error-p len) (null len))
        nil
        (progn
          (setq p (vl-catch-all-apply 'vlax-curve-getPointAtDist
                    (list e (/ len 2.0))))
          (if (or (vl-catch-all-error-p p) (null p)) nil p))))))

(defun autobead-on-other-p (pt chains self / hit cp o)
  ;; T if pt lies on some chain other than self (within drafting slop).
  (setq hit nil)
  (foreach o chains
    (if (and (null hit) (not (eq o self)) (entget o))
      (progn
        (setq cp (vl-catch-all-apply 'vlax-curve-getClosestPointTo
                   (list o pt)))
        (if (and (not (vl-catch-all-error-p cp)) cp
                 (< (distance cp pt) 0.05))
          (setq hit T)))))
  hit)

(defun autobead-side (pt a b / cr)
  ;; Which side of line a->b the point is on: -1 or 1.
  (setq cr (- (* (- (car b) (car a)) (- (cadr pt) (cadr a)))
              (* (- (cadr b) (cadr a)) (- (car pt) (car a)))))
  (if (minusp cr) -1 1))

(defun autobead-breakline (p dirw steplines / h len far best bestd i s a b
                                              ab abl x t1 t2)
  ;; The assumed breakline for a clicked step: cast a ray from the click p
  ;; toward the direction click dirw (the way the bead is heading) and
  ;; return the index of the FIRST step line it meets, or nil.  Step lines
  ;; are given 6" of slop past their drawn ends.
  (setq h   (list (- (car dirw) (car p)) (- (cadr dirw) (cadr p)) 0.0)
        len (distance '(0.0 0.0 0.0) h))
  (if (< len 1e-6)
    nil
    (progn
      (setq h     (mapcar '(lambda (v) (/ v len)) h)
            far   (mapcar '+ p (mapcar '(lambda (v) (* v 1e6)) h))
            best  nil
            bestd 1e99
            i     0)
      (foreach s steplines
        (setq a (car s)
              b (cadr s)
              x (inters p far a b nil))       ; both extended; filter below
        (if x
          (progn
            (setq ab  (mapcar '- b a)
                  abl (distance a b)
                  t1  (cal:dot (mapcar '- x p) h)
                  t2  (if (> abl 1e-6)
                        (/ (cal:dot (mapcar '- x a) ab) abl)
                        -1e99))
            ;; ahead of the click, within the (padded) step segment,
            ;; and nearer than anything found so far
            (if (and (> t1 0.5)
                     (>= t2 -6.0) (<= t2 (+ abl 6.0))
                     (< t1 bestd))
              (setq best i bestd t1))))
        (setq i (1+ i)))
      best)))

(defun autobead-ixpoints (bead step / o1 o2 v a l res)
  ;; WCS points where 'step' (extended to infinity) crosses 'bead'.
  (setq o1 (vlax-ename->vla-object bead)
        o2 (vlax-ename->vla-object step)
        v  (vl-catch-all-apply 'vla-IntersectWith (list o1 o2 2))) ; 2 = acExtendOtherEntity
  (setq res '())
  (if (not (vl-catch-all-error-p v))
    (progn
      (setq a (vl-catch-all-apply 'vlax-variant-value (list v)))
      (if (not (vl-catch-all-error-p a))
        (progn
          (setq l (vl-catch-all-apply 'vlax-safearray->list (list a)))
          (if (vl-catch-all-error-p l) (setq l nil))
          (while (and l (cddr l))               ; flat (x y z x y z ...)
            (setq res (cons (list (car l) (cadr l) 0.0) res)
                  l   (cdddr l))))))
    )
  (reverse res))

(defun autobead-break-at (pieces pt / host cp sp ep mark p)
  ;; Break whichever piece passes through pt (strictly mid-span) at pt.
  ;; Returns the updated piece list; a pt at a piece boundary is a no-op.
  (setq host nil)
  (foreach p pieces
    (if (and (null host) (entget p))
      (progn
        (setq cp (vl-catch-all-apply 'vlax-curve-getClosestPointTo
                   (list p pt))
              sp (autobead-curve-end p 'start)
              ep (autobead-curve-end p 'end))
        (if (and (not (vl-catch-all-error-p cp)) cp
                 (< (distance cp pt) 1e-4)
                 sp (> (distance pt sp) 1e-6)
                 ep (> (distance pt ep) 1e-6))
          (setq host p)))))
  (if host
    (progn
      (setq mark (entlast))
      ;; BREAK takes UCS points; intersections are WCS
      (command "._break" host "_f"
               "_non" (trans pt 0 1) "_non" (trans pt 0 1))
      (autobead-flush)
      (append (vl-remove-if-not '(lambda (x) (entget x)) pieces)
              (autobead-newents mark)))
    pieces))

;; ---- engine ----------------------------------------------------------------
;; Everything that touches the drawing lives here, so AUTOBEAD and the
;; tutorial exercise exactly the same code path.  sidewalls / treadpts come
;; from the side-wall question (treadpts in WCS); pass nil nil to bead every
;; selected wall full length.  Returns the number of bead objects created.

(defun autobead-build (ss dirpt sidewalls treadpts
                       / *error* beadoff layname fuzz
                         oldcmd oldos oldpa temps undo-open
                         mark copies ss2 chains mark2 news
                         beadcount failcount c e i src dup drift
                         gaps g sp ep perimchains stepchains steplines
                         perimbeads bps pieces mp kept culled filtered
                         misses brks dirw hit p)

  (setq beadoff *autobead-offset*
        layname *autobead-layer*
        fuzz    *autobead-fuzz*)

  ;; -- error handler: cancel stuck commands, purge temp geometry,
  ;;    restore system variables, close the undo group -------------------
  (defun *error* (msg)
    (autobead-flush)
    (foreach e temps
      (if (and e (entget e)) (entdel e)))
    (if oldpa (setvar "PEDITACCEPT" oldpa))
    (if oldos (setvar "OSMODE" oldos))
    ;; only close a group that was actually opened -- an error thrown
    ;; before the _Begin below (a cancelled selection, a failed getvar)
    ;; used to run _End on nothing, which errors inside the handler
    (if undo-open (command "_.UNDO" "_End"))
    (setq undo-open nil)
    (if oldcmd (setvar "CMDECHO" oldcmd))
    (if (not (wcmatch (strcase msg) "*BREAK*,*CANCEL*,*QUIT*,*EXIT*"))
      (princ (strcat "\nAUTOBEAD error: " msg)))
    (princ))

  (setq oldcmd (getvar "CMDECHO"))
  (setvar "CMDECHO" 0)
  (command "_.UNDO" "_Begin")
  (setq undo-open T)
  (setq oldos (getvar "OSMODE")
        oldpa (getvar "PEDITACCEPT")
        temps '()
        beadcount 0)

  (autobead-ensure-layer layname)
  (setvar "OSMODE" 0)          ; keep osnaps out of the internal commands
  (setvar "PEDITACCEPT" 1)     ; auto-accept line/arc -> pline conversion

  ;; 1) copy the selection in place so the originals are never touched
  (setq mark   (entlast)
        copies '()
        drift  nil
        i      0)
  (while (< i (sslength ss))
    (setq src (ssname ss i)
          dup (autobead-copy src))
    (if dup
      (progn
        (if (not (autobead-inplace-p src dup)) (setq drift T))
        (setq copies (cons dup copies))))
    (setq i (1+ i)))
  (setq copies (reverse copies)
        temps  copies)

  (cond
    ((null copies)
     (prompt "\nCould not copy the selection (locked source layer?)."))

    (drift
     (foreach e copies (if (entget e) (entdel e)))
     (setq temps '())
     (prompt (strcat "\nAborted: the working copies did not land on the"
                     " source geometry.\nNothing was drawn.")))

    (T
     ;; 2) join the copies into continuous polyline chains
     (setq ss2 (ssadd))
     (foreach c copies (ssadd c ss2))
     (command "._pedit" "_multiple" ss2 "" "_join" fuzz "")
     (autobead-flush)
     (setq chains (autobead-newents mark)
           temps  chains)

     ;; 3) classify: a chain whose BOTH endpoints land mid-span on other
     ;;    chains is a step line crossing the pool; the rest are walls
     (setq perimchains '() stepchains '() steplines '())
     (if (> (length chains) 1)
       (foreach c chains
         (setq sp (autobead-curve-end c 'start)
               ep (autobead-curve-end c 'end))
         (if (and sp ep
                  (autobead-on-other-p sp chains c)
                  (autobead-on-other-p ep chains c))
           (setq stepchains (cons c stepchains)
                 steplines  (cons (list sp ep) steplines))
           (setq perimchains (cons c perimchains))))
       (setq perimchains chains))

     ;; 4) offset every chain toward the click; native offset trims
     ;;    convex corners and extends concave ones automatically
     (setq failcount 0 gaps '() perimbeads '())
     (foreach c chains
       (setq mark2 (entlast))
       (command "._offset" beadoff c "_non" dirpt "")
       (autobead-flush)
       (setq news (autobead-newents mark2))
       (if news
         (foreach e news
           (entmod (subst (cons 8 layname)
                          (assoc 8 (entget e))
                          (entget e)))
           ;; measure before the source chain is deleted
           (if (setq g (autobead-gap c e)) (setq gaps (cons g gaps)))
           (if (member c perimchains)
             (setq perimbeads (cons e perimbeads)))
           (setq beadcount (1+ beadcount)))
         (setq failcount (1+ failcount))))

     ;; 5) side walls: each clicked step ASSUMES its breakline - the next
     ;;    step line from the click in the direction the bead is heading
     ;;    (toward the direction click).  Wall bead is broken at those
     ;;    lines and kept only on the clicked side of them; everything
     ;;    past a breakline, and every unclicked span, is removed.
     ;;    Step-face beads are never touched.
     (setq kept 0 culled 0 filtered nil misses 0 brks '())
     (if (and sidewalls treadpts steplines perimbeads)
       (progn
         (setq dirw (trans dirpt 1 0))
         (foreach p treadpts
           (setq hit (autobead-breakline p dirw steplines))
           (if hit
             (setq brks (cons (list (nth hit stepchains)
                                    (car (nth hit steplines))
                                    (cadr (nth hit steplines))
                                    (autobead-side p
                                      (car (nth hit steplines))
                                      (cadr (nth hit steplines))))
                              brks))
             (setq misses (1+ misses))))
         (if brks
           (progn
             (setq filtered T)
             (foreach e perimbeads
               (setq bps '())
               (foreach c brks
                 (if (entget (car c))
                   (setq bps (append bps (autobead-ixpoints e (car c))))))
               (setq pieces (list e))
               (foreach g bps
                 (setq pieces (autobead-break-at pieces g)))
               (foreach c pieces
                 (if (entget c)
                   (progn
                     (setq mp (autobead-midpt-of c))
                     (if (and mp
                              (vl-some
                                '(lambda (k)
                                   (= (autobead-side mp (cadr k) (caddr k))
                                      (cadddr k)))
                                brks))
                       (setq kept (1+ kept))
                       (progn
                         (entdel c)
                         (setq culled (1+ culled))))))))
             ;; recount: step beads + surviving wall pieces
             (setq beadcount (+ (- beadcount (length perimbeads)) kept))))))

     ;; 6) discard the temporary chains
     (foreach c chains
       (if (entget c) (entdel c)))
     (setq temps '())

     ;; 7) report -- including what was actually built, so a bead that
     ;;    lands in the wrong place can be diagnosed from the command line
     (prompt (strcat "\n--- AUTOBEAD " *autobead-version* " ---"
                     "\n  source layers : "
                     (apply 'strcat
                       (mapcar '(lambda (l) (strcat l " "))
                               (autobead-layers ss)))
                     "\n  objects picked: " (itoa (sslength ss))
                     "\n  joined chains : " (itoa (length chains))
                     "  (" (itoa (length perimchains)) " wall, "
                     (itoa (length stepchains)) " step)"
                     "\n  side walls    : "
                     (cond
                       (filtered
                        (strcat "beaded at " (itoa (length treadpts))
                                " clicked step(s), " (itoa (length brks))
                                " assumed breakline(s) -- kept "
                                (itoa kept) " wall piece(s), removed "
                                (itoa culled)))
                       ((and sidewalls (null steplines))
                        "requested, but no step lines were recognized")
                       ((and sidewalls treadpts)
                        "requested, but no breakline was found toward the direction click")
                       (T "full length (not restricted)"))
                     "\n  offset asked  : " (rtos beadoff)
                     "\n  offset measured: "
                     (if gaps
                       (strcat (rtos (apply 'min gaps)) " to "
                               (rtos (apply 'max gaps)))
                       "n/a")
                     "\n  beads created : " (itoa beadcount)
                     " on " layname))
     (if (> misses 0)
       (prompt (strcat "\n  " (itoa misses)
                       " clicked step(s) found no step line toward the"
                       " direction click - ignored.")))
     (if (> failcount 0)
       (prompt (strcat "\n  " (itoa failcount)
                       " chain(s) could not be offset -- try clicking"
                       " farther from the pool line.")))))

  ;; -- restore --------------------------------------------------------------
  (setvar "PEDITACCEPT" oldpa)
  (setvar "OSMODE" oldos)
  (command "_.UNDO" "_End")
  (setq undo-open nil)
  (setvar "CMDECHO" oldcmd)
  beadcount)

;; ---- AUTOBEAD --------------------------------------------------------------

(defun c:AUTOBEAD ( / ss dirpt stage done ans sidewalls treadpts p )
  (autobead-ensure-layer *autobead-layer*)
  ;; staged: Back (or Undo) at any later prompt re-opens the stage before
  (setq stage 1 done nil)
  (while (not done)
    (cond
      ((= stage 1)
       (prompt (strcat "\nSelect POOL lines to bead (layers "
                       *autobead-filter* "): "))
       (setq ss (ssget (list '(0 . "LINE,ARC,LWPOLYLINE,POLYLINE")
                             (cons 8 *autobead-filter*))))
       (if (null ss)
         (progn
           (prompt (strcat "\nNothing selected on a " *autobead-filter*
                           " layer."))
           (setq done T))
         (setq stage 2)))
      ((= stage 2)
       (initget "Back Undo")
       (setq dirpt (getpoint "\nClick the side to bead toward [Back]: "))
       (cond
         ((= (type dirpt) 'STR) (setq stage 1))
         ((null dirpt)
          (prompt "\nNo direction point picked.")
          (setq done T))
         (T (setq stage 3))))
      (T
       (initget "Yes No Back Undo")
       (setq ans (getkword
                   "\nAre the side walls beaded? [Yes/No/Back] <No>: "))
       (cond
         ((member ans '("Back" "Undo")) (setq stage 2))
         (T
          (setq sidewalls (= ans "Yes")
                treadpts  '())
          (if sidewalls
            (progn
              (prompt (strcat "\nClick each step (tread) that has beaded"
                              " side walls."))
              (while (setq p (getpoint
                               "\n  Click a step <Enter = done>: "))
                (setq treadpts (cons (trans p 1 0) treadpts)))
              (if (null treadpts)
                (progn
                  (prompt (strcat "\nNo steps clicked - side walls will"
                                  " be beaded full length."))
                  (setq sidewalls nil)))))
          (autobead-build ss dirpt sidewalls treadpts)
          (setq done T))))))
  (princ))

;; ---- AUTOBEADVER -----------------------------------------------------------

(defun c:AUTOBEADVER ()
  (prompt (strcat "\nAUTOBEAD " *autobead-version*
                  "\n  offset : " (rtos *autobead-offset*)
                  "\n  layer  : " *autobead-layer*
                  "\n  filter : " *autobead-filter*))
  (princ))

;; ==========================================================================
;;; TUTORIALAUTOBEAD
;;; --------------------------------------------------------------------------
;;; Two modes:
;;;   Read - a written walkthrough: every step, every check, every setting
;;;   Demo - draws a sample pool and beads it live, pausing at each stage
;;; ==========================================================================

(defun autobead-pause (msg)
  ;; Print a step heading and wait for Enter.
  (prompt (strcat "\n" msg))
  (getstring "\n      [Enter] to continue: ")
  (princ))

(defun autobead-say (lines)
  ;; Print a list of strings, one per line.
  (foreach l lines (prompt (strcat "\n" l)))
  (princ))

;; ---- read mode -------------------------------------------------------------

(defun autobead-tutorial-read ()
  (autobead-say
    (list
      ""
      "==========================================================="
      (strcat " AUTOBEAD " *autobead-version* " - how it works")
      "==========================================================="
      ""
      "WHAT IT DOES"
      "  Draws a bead line at a fixed offset from your pool edge,"
      (strcat "  on the \"" *autobead-layer* "\" layer. Corners are resolved for")
      "  you: outside corners get trimmed, inside corners get"
      "  extended to meet, and radius corners stay concentric."
      "  Lines that cross the pool touching walls at both ends are"
      "  recognized as STEP lines and always bead full length."
      ""
      "USING IT"
      "  1. Type AUTOBEAD."
      (strcat "  2. Select your pool lines. Only objects on a "
              *autobead-filter* " layer")
      "     can be picked, so a window select is safe - dimensions,"
      "     text and hatch are ignored."
      "  3. Click the side you want the bead on. One click sets the"
      "     direction for everything you selected."
      "  4. Answer: are the side walls beaded?"
      "       No  - every selected wall beads full length."
      "       Yes - click each step (tread) that has beaded side"
      "             walls, then Enter. Each click assumes its"
      "             breakline: the next step line from the click"
      "             toward the direction click (the way the bead"
      "             is heading). Wall bead is cut flush there,"
      "             kept on your side, removed everywhere else."
      "             Step-face beads always draw either way."
      ""
      "CURRENT SETTINGS"
      (strcat "  offset distance : " (rtos *autobead-offset*)
              "   (drawing units)")
      (strcat "  output layer    : " *autobead-layer*)
      (strcat "  selectable from : " *autobead-filter*)
      (strcat "  join tolerance  : " (rtos *autobead-fuzz*))
      ""
      "WHAT IT CHECKS, IN ORDER"
      (strcat "   1. Output layer \"" *autobead-layer* "\" exists - creates it if not.")
      "   2. That layer is thawed and unlocked - fixes it if not, so"
      "      beads can never be drawn somewhere invisible."
      (strcat "   3. Something was actually selected on a "
              *autobead-filter* " layer.")
      "   4. A direction point was actually picked."
      "   5. Every selected object copies successfully. The originals"
      "      are never touched - all work happens on copies."
      "   6. Each copy landed exactly on top of its original. If any"
      "      copy drifted, the run aborts and draws nothing rather"
      "      than leaving geometry in the wrong place."
      "   7. Copies join into continuous chains, so corners can be"
      "      resolved across segment boundaries."
      "   8. Chains are classified into walls and step lines, and"
      "      the split is printed in the report."
      "   9. Each chain offsets successfully. Any chain that fails is"
      "      counted and reported instead of failing silently."
      "  10. With beaded side walls, each click resolves to a"
      "      breakline; clicks that find none are counted and"
      "      ignored, and kept/removed pieces are reported."
      "  11. The finished bead is measured back against the chain it"
      "      came from, and the real distance is reported."
      "  12. Temporary geometry is deleted."
      "  13. OSMODE, PEDITACCEPT and CMDECHO are restored."
      ""
      "IF SOMETHING GOES WRONG"
      "  The run is wrapped in a single undo group - one U undoes all"
      "  of it. Pressing Esc mid-run is safe: temporary geometry is"
      "  cleaned up and your settings are restored."
      ""
      "READING THE REPORT"
      "  Every run prints a summary. The lines worth reading:"
      "    offset asked / offset measured - if these disagree, the"
      "      offset distance is not being applied as requested."
      "    joined chains (wall, step) - check the tool recognized"
      "      your step lines; a step counted as a wall will bead"
      "      full length and drag wall bead with it."
      "    side walls - confirms which treads were honored and how"
      "      many wall pieces were kept vs removed."
      ""
      "OTHER COMMANDS"
      "  AUTOBEADVER      - which version is loaded"
      "  TUTORIALAUTOBEAD - this walkthrough"
      "==========================================================="
      "")))

;; ---- demo mode -------------------------------------------------------------

(defun autobead-demo-layer (name / def)
  ;; Temporary POOL-matching layer for the sample geometry.
  (if (not (tblsearch "LAYER" name))
    (entmake (list '(0 . "LAYER")
                   '(100 . "AcDbSymbolTableRecord")
                   '(100 . "AcDbLayerTableRecord")
                   (cons 2 name)
                   (cons 70 0)
                   (cons 62 4)               ; cyan
                   (cons 6 "Continuous")))))

(defun autobead-demo-line (a b lay / e)
  ;; Draw one demo segment and return its ename.
  (entmakex (list '(0 . "LINE")
                  (cons 8 lay)
                  (cons 10 a)
                  (cons 11 b))))

(defun autobead-tutorial-demo ( / base lay pts prev ents ss dirpt
                                  x y made e )
  (setq lay "POOL-TUTORIAL")

  (autobead-say
    (list ""
          "DEMO MODE"
          "  A sample pool with two step lines will be drawn in your"
          "  drawing and beaded for real, using the same code AUTOBEAD"
          "  uses. It goes on a temporary layer and you will be offered"
          "  a cleanup at the end. Undo (U) also removes all of it."))

  (if (null (setq base (getpoint
                         "\nPick an empty spot for the demo pool: ")))
    (progn (prompt "\nDemo cancelled.") (princ))

    (progn
      (autobead-demo-layer lay)
      (setq x (car base)
            y (cadr base))

      ;; open-ended pool run: bottom wall, end wall, top wall, plus two
      ;; step lines crossing the pool near the end wall
      (setq ents
        (list
          (autobead-demo-line (list x y 0.0)
                              (list (+ x 300.0) y 0.0) lay)
          (autobead-demo-line (list (+ x 300.0) y 0.0)
                              (list (+ x 300.0) (+ y 144.0) 0.0) lay)
          (autobead-demo-line (list (+ x 300.0) (+ y 144.0) 0.0)
                              (list x (+ y 144.0) 0.0) lay)
          ;; step lines at 66" and 90" from the end wall
          (autobead-demo-line (list (+ x 234.0) y 0.0)
                              (list (+ x 234.0) (+ y 144.0) 0.0) lay)
          (autobead-demo-line (list (+ x 210.0) y 0.0)
                              (list (+ x 210.0) (+ y 144.0) 0.0) lay)))

      (command "._zoom" "_window"
               (list (- x 60.0) (- y 60.0))
               (list (+ x 360.0) (+ y 204.0)))

      (autobead-pause
        (strcat "STEP 1 - the pool\n"
                "      A pool run on layer " lay ": bottom wall, end wall,\n"
                "      top wall, and two step lines crossing the pool near\n"
                "      the end. The step lines touch the walls at both"
                " ends,\n      which is how AUTOBEAD recognizes them as"
                " steps."))

      (autobead-pause
        (strcat "STEP 2 - selecting\n"
                "      AUTOBEAD would now ask you to select. Only objects"
                " on\n      a " *autobead-filter* " layer are selectable,"
                " so a window select\n      cannot pick up dimensions,"
                " text or hatch by accident.\n"
                "      Here all 5 lines are selected for you."))

      (setq ss (ssadd))
      (foreach e ents (if (entget e) (ssadd e ss)))

      (autobead-say
        (list "STEP 3 - the direction click"
              "      One click decides which side every bead goes on,"
              "      and it is also the direction the bead is heading -"
              "      step clicks find their breakline by looking this"
              "      way. Click INSIDE the pool, out in the main body"
              "      (away from the step lines)."))
      (setq dirpt (getpoint "\n      Click a side to bead toward: "))

      (if (null dirpt)
        (prompt "\nDemo cancelled.")
        (progn
          (autobead-pause
            (strcat "STEP 4 - the side-wall question\n"
                    "      AUTOBEAD would now ask: are the side walls"
                    " beaded?\n"
                    "      For this demo the answer is Yes, with the top"
                    " step\n      (between the end wall and the first"
                    " step line)\n      clicked as the beaded one. That"
                    " click assumes its\n      breakline - the next step"
                    " line toward your direction\n      click - so wall"
                    " bead survives only on the click's\n      side of"
                    " that line."))

          (setq made (autobead-build ss dirpt T
                       (list (list (+ x 267.0) (+ y 72.0) 0.0))))

          (autobead-say
            (list ""
                  "STEP 5 - the result"
                  (strcat "      " (itoa made) " bead object(s) on \""
                          *autobead-layer* "\".")
                  "      Note what happened:"
                  "        - both step lines got full-length beads"
                  "        - wall bead survives only around the top"
                  "          tread, cut flush at the first step line"
                  "        - the rest of the walls have no bead"
                  ""
                  "      The report above is printed on every real run."
                  ""))))

      ;; cleanup
      (initget "Yes No")
      (if (/= "No" (getkword
                     "\nErase the demo pool and its bead? [Yes/No] <Yes>: "))
        (progn
          (foreach e ents (if (entget e) (entdel e)))
          (if (setq ss (ssget "_X" (list (cons 8 *autobead-layer*))))
            (command "._erase" ss ""))
          (prompt "\nDemo geometry erased.")))
      (prompt "\nTutorial complete. Type AUTOBEAD to use it for real.")
      (princ))))

;; ---- entry point -----------------------------------------------------------

(defun c:TUTORIALAUTOBEAD ( / ans )
  ;; the tutorial selector of STANDARDS section 3; the old Read stays
  ;; accepted typed in full, hidden
  (initget "Checks Demo Both READ")
  (setq ans (getkword
              (strcat "\nAUTOBEAD tutorial - read the Checks, or watch a live Demo?"
                      "\n  [Checks/Demo/Both] <Both>: ")))
  (if (null ans) (setq ans "Both"))
  (if (= ans "READ") (setq ans "Checks"))
  (if (member ans '("Checks" "Both")) (autobead-tutorial-read))
  (if (member ans '("Demo" "Both")) (autobead-tutorial-demo))
  (princ))

;; ---------------------------------------------------------------------------

(prompt (strcat "\nAUTOBEAD " *autobead-version* " loaded."
                "\n  AUTOBEAD          - bead selected pool lines"
                "\n  TUTORIALAUTOBEAD  - how it works"
                "\n  AUTOBEADVER       - version check"))
(princ)


;;; ======================================================================
;;; >>> AutoDim.lsp
;;; ======================================================================

;;; ======================================================================
;;;  AutoDim.lsp
;;;
;;;  AUTODIM  - Step 1. Asks the user to highlight the stuff to
;;;                auto-dim (the plan geometry).  Everything else in
;;;                the drawing is ignored from then on.  Highlight a
;;;                flight of steps drawn in side view instead and it
;;;                is recognised as one - see "Steps in side view"
;;;                below - and steps 2 to 5 are skipped, being all
;;;                about a plan.
;;;             Step 2. Dimensions the perimeter of the highlighted
;;;                geometry, at least a foot outside the plan: its
;;;                straight sides (LINE entities and straight
;;;                LWPOLYLINE segments) with aligned dimensions, then
;;;                its arcs (ARC and CIRCLE entities and bulged
;;;                LWPOLYLINE segments) with radius dimensions.  A
;;;                measurement that repeats is called out once and
;;;                noted "Typ." - see "One dim per size" below.
;;;             Step 3. Asks the user to highlight the stairs.  The
;;;                treads (the largest group of parallel lines in the
;;;                selection) get their widths dimensioned and the
;;;                distances between them chained beside the stair.
;;;             Step 4. Asks whether you would like floor dims, and if
;;;                you do, has you draw two lines across the plan.
;;;                Each one becomes a continued dimension chain
;;;                (DIMALIGNED + DIMCONTINUE) that breaks at every
;;;                highlighted object standing in its way.  A start or
;;;                end point that is not on an object is pulled back to
;;;                the last object before it, so every dim runs object
;;;                to object and none hangs off the end into open
;;;                drawing.
;;;             Step 5. Places the two overall dims, no input needed:
;;;                the plan's full width about 2ft above the topmost
;;;                dimension and its full height about 2ft to the left
;;;                of the left-most one.
;;;
;;;  STAIRDIM - Runs just the stairs part again for another selection.
;;;  FLOORDIM - Runs just the floor dims part for one extra line
;;;             (breaks at everything in model space).
;;;
;;;  AUTODIMSIDEPOV - Dimensions steps drawn in side view (elevation).
;;;             Highlight the step profile: every vertical riser gets a
;;;             vertical dimension placed beside its step - extension
;;;             lines hooked to the nosing corners, each dim stepping
;;;             down the flight with the stairs - plus one overall
;;;             height dimension further out.  The dims are created on
;;;             layer "DIMENSION" in the "STANDARD INCHES" style, like
;;;             the reference drawing, and work whichever way the
;;;             stairs face.
;;;
;;;  Usage:
;;;    1. APPLOAD this file (or drag it into the drawing window).
;;;    2. Type AUTODIM and follow the prompts.
;;;
;;;  Steps in side view:
;;;    AUTODIM works out for itself whether step 1's selection is a
;;;    plan or a flight of steps drawn in side view, and it only takes
;;;    the second route when the drawing really looks like steps:
;;;      * nothing curved in the selection - no arc, circle, ellipse,
;;;        spline, polyline bulge or block;
;;;      * three quarters or more of the straight segments running
;;;        square, so a sloping pool floor at the foot of the flight is
;;;        still allowed;
;;;      * two or more risers, and at least one tread per gap between
;;;        them;
;;;      * the risers forming a connected staircase across the drawing,
;;;        each starting where the one before it finished, a tread's
;;;        run further along.
;;;    A vertical as tall as the whole profile is read as the back wall
;;;    rather than a step and left out of that - which is also what
;;;    stops a rectangular plan reading as a two-step flight.  Anything
;;;    that fails the test is dimensioned as a plan, so a false alarm
;;;    is not something a plan can trip into.
;;;    What it then places: the depth of every step as a vertical dim,
;;;    all on one line clear of the right-hand side of the flight, and
;;;    the overall depth further right again.  Both in "STANDARD
;;;    INCHES".  AUTODIMSIDEPOV is still there for a flight the test
;;;    does not recognise, or to put the dims on the high side of the
;;;    steps instead of the right.
;;;
;;;  How the perimeter is found:
;;;    From the midpoint of every straight segment a test ray is cast
;;;    perpendicular to each side, out past the extents of the
;;;    highlighted geometry.  If at least one side is completely clear
;;;    of highlighted geometry the segment is on the perimeter, and its
;;;    dimension is placed on that clear side.  Because only the
;;;    highlighted stuff blocks the rays, title borders, notes and
;;;    anything else in the drawing cannot get in the way.
;;;
;;;  Dimension styles - every dimension picks its own, by what it
;;;  measures rather than by which step placed it (a style the drawing
;;;  does not have falls back to the style that was current when the
;;;  command started, and that style is restored when it finishes):
;;;    * Perimeter and stairs    -> "SIDE STANDARD"
;;;    * The floor dims chains   -> "STANDARD"
;;;    * The two overall dims    -> "STANDARD"
;;;    * ...measuring under 12"  -> "STANDARD INCHES", whichever of the
;;;                                 three it would otherwise have been
;;;    * Steps in side view      -> "STANDARD INCHES", depths and the
;;;                                 overall alike, in AUTODIM and in
;;;                                 AUTODIMSIDEPOV
;;;
;;;  One dim per size - the "Typ." rule:
;;;    A measurement that repeats around the perimeter is called out
;;;    once, with " Typ." after it, and the others are left to that
;;;    note rather than dimensioned again.  The one that carries it is
;;;    the first of its size the tool comes across, so a re-run marks
;;;    the same side or arc it marked before.
;;;      * straight sides -> from two equal ones up
;;;      * arcs, by radius -> from four equal ones up; a pair or a trio
;;;        of matching curves reads better dimensioned where each one
;;;        is, so those are left alone
;;;    Two lengths, or two radii, within a sixteenth of an inch count
;;;    as the same measurement.  The counts and the wording are
;;;    ad:*typ-lines*, ad:*typ-curves* and ad:*typ-note* at the top of
;;;    the file.
;;;
;;;  One dimension per place:
;;;    Before placing anything the tool reads every linear, aligned and
;;;    radius dimension already in model space.  A dim is skipped when
;;;    one is already there for that place - same two extension line
;;;    origins (either way round) and a dimension line within a foot of
;;;    where the new one would sit, or for a radius dim, the same
;;;    centre and the same radius.  So a second run over a plan that has
;;;    grown dimensions the new geometry only, while the overall dims,
;;;    two feet further out, are still placed even when a side of the
;;;    plan happens to measure the same thing.
;;;
;;;  Notes:
;;;    * All dims go on the current layer.
;;;    * Ellipses and splines have no one radius to call out, so the
;;;      perimeter step passes over them.
;;;    * Perimeter dims are placed at least one foot away from the
;;;      perimeter, heading outwards (or 2 x DIMTXT x DIMSCALE when
;;;      that is larger).
;;;    * Equal step widths are dimensioned once instead of once per
;;;      tread; a width dim is repeated only when the width changes.
;;;    * A dim chain breaks where a span is already dimensioned, and
;;;      where the style has to change, so a short span still lands in
;;;      inches without dragging the rest of the chain with it.
;;;    * The two floor dims lines are construction lines only - they
;;;      are erased once their dimension chain has been created.
;;;    * Answering No to the floor dims question skips straight to the
;;;      overall dims; Back at it re-opens the stairs.
;;;    * Break points closer together than 0.0001 drawing units are
;;;      merged so no zero-length dimensions are created.
;;; ======================================================================

;;; SHARED BUILD: requires CALOFIN-LIB.lsp (load via CALOFIN-LOADER.lsp).
;;; Generic helpers live there under cal: - see STANDARDS.md.
;;;

(setq *autodim-version* "v1.0")   ; announced on load; release_lisp.py
                                     ; stamps the dated twin in releases/

(vl-load-com)

;; ---------------------------------------------------------------- helpers

;; angle of a segment folded into [0, pi) so opposite directions match
(defun ad:segang (seg / a)
  (setq a (angle (car seg) (cadr seg)))
  (if (>= a pi) (- a pi) a))

;; difference between two folded angles, allowing for wrap-around
(defun ad:angdiff (a b / d)
  (setq d (abs (- a b)))
  (min d (abs (- pi d))))

;; perpendicular offset used for the automatic dims
(defun ad:dimoff ()
  (* 2.0
     (getvar "DIMTXT")
     (if (zerop (getvar "DIMSCALE")) 1.0 (getvar "DIMSCALE"))))

;; one foot expressed in the current drawing units (INSUNITS),
;; assuming inches when unitless or unknown
(defun ad:onefoot (/ u)
  (setq u (getvar "INSUNITS"))
  (cond ((= u 2) 1.0)                   ; feet
        ((= u 4) 304.8)                 ; millimetres
        ((= u 5) 30.48)                 ; centimetres
        ((= u 6) 0.3048)                ; metres
        ((= u 10) (/ 1.0 3.0))          ; yards
        (t 12.0)))                      ; inches / unitless

;; ------------------------------------------------------------- asking

;; restore a dimension style by name if the drawing has it,
;; return T when the style was set
(defun ad:setdimstyle (name)
  (if (and name (tblsearch "DIMSTYLE" name))
    (progn (command "_.-DIMSTYLE" "_Restore" name) t)))

;; make a layer current, creating it first when the drawing lacks it
(defun ad:setlayer (name)
  (if (not (tblsearch "LAYER" name))
    (entmake (list '(0 . "LAYER")
                   '(100 . "AcDbSymbolTableRecord")
                   '(100 . "AcDbLayerTableRecord")
                   (cons 2 name)
                   '(70 . 0)
                   '(62 . 7)
                   '(6 . "Continuous"))))
  (setvar "CLAYER" name))

;; ------------------------------------------------ dimension styles

;; The styles the tool asks for.  The perimeter and the stairs go in
;; ad:*style-plan*, the floor dims chains in ad:*style-floor* and the
;; two overall dims in ad:*style-over*; whichever of those it is,
;; anything measuring less than a foot goes in ad:*style-short*
;; instead, a sub-foot dim reading better in inches.
(setq ad:*style-plan*  "SIDE STANDARD"
      ad:*style-floor* "STANDARD"
      ad:*style-short* "STANDARD INCHES"
      ad:*style-over*  "STANDARD")

;; Repeated measurements are called out once and noted, rather than
;; dimensioned over and over.  ad:*typ-note* is the suffix the one dim
;; that stands for its group carries - the wording POOL.LSP already
;; uses for the same job.  The two counts are how many equal ones it
;; takes before that happens: two equal straight sides are enough,
;; while equal radii are left alone until there are more than three of
;; them, a pair or a trio of matching curves reading better dimensioned
;; where they are.
(setq ad:*typ-note*   " Typ."
      ad:*typ-lines*  2
      ad:*typ-curves* 4)

;; per-run state, all reset by ad:begin
(setq ad:*dims*      nil    ; the places that already carry a dimension
      ad:*rads*      nil    ; the arcs that already carry a radius dim
      ad:*skipped*   0      ; how many dims this run left to what was there
      ad:*curstyle*  nil    ; the dimension style in force right now
      ad:*homestyle* nil)   ; what to fall back on when a style is missing

;; T when two style names are the same one (AutoCAD folds their case)
(defun ad:samestyle (a b)
  (and a b (= (strcase a) (strcase b))))

;; make a dimension style current, skipping the work when it already
;; is.  A style the drawing does not have falls back to the one that
;; was current when the command started, so a missing "SIDE STANDARD"
;; cannot leave a later dim stranded in the style of the dim before it.
(defun ad:usestyle (name / want)
  (setq want (if (and name (tblsearch "DIMSTYLE" name)) name ad:*homestyle*))
  (if (and want (not (ad:samestyle want ad:*curstyle*)))
    (progn
      (ad:setdimstyle want)
      (setq ad:*curstyle* want))))

;; the style a dimension of this measured length belongs in
(defun ad:styfor (len base)
  (if (< len (ad:onefoot)) ad:*style-short* base))

;; ---------------------------------------- dimensions already in place

;; how close two extension line origins have to be before they count as
;; the same place - a sixteenth of an inch, in the drawing's own units
(defun ad:dupetol () (/ (ad:onefoot) 192.0))

;; how close two dimension lines have to be before dims across the same
;; two points count as the same dim.  A foot: enough that a re-run, or
;; a dim nudged by hand, is recognised, and small enough that the
;; overall dims - two feet further out - are still their own dims.
(defun ad:bandtol () (ad:onefoot))

;; every dimension in model space
(defun ad:dimss ()
  (ssget "_X" '((0 . "DIMENSION") (410 . "Model"))))

;; a linear / aligned dimension as (origin1 origin2 dimline-point) -
;; nil for any other kind (radial, angular, ordinate), which has no
;; pair of extension line origins to compare
(defun ad:dimpts (en / el)
  (setq el (entget en))
  (if (and el
           (= "DIMENSION" (cdr (assoc 0 el)))
           (assoc 13 el)
           (assoc 14 el)
           (assoc 10 el))
    (list (cdr (assoc 13 el)) (cdr (assoc 14 el)) (cdr (assoc 10 el)))))

;; note that p1-p2 now carries a dimension whose dim line runs through
;; loc, so nothing later in the same run doubles up on it
(defun ad:remember (p1 p2 loc)
  (setq ad:*dims* (cons (list p1 p2 loc) ad:*dims*)))

;; a radius dimension as (centre radius), nil for anything else.  Only
;; radius dims are read: a diameter dim writes two points on the circle
;; into 10 and 15 rather than the centre and one, and is not what this
;; tool places anyway.
(defun ad:raddimpts (en / el c)
  (setq el (entget en))
  (if (and el
           (= "DIMENSION" (cdr (assoc 0 el)))
           (assoc 70 el)
           (= 4 (logand 7 (cdr (assoc 70 el))))
           (assoc 10 el)
           (assoc 15 el))
    (progn
      (setq c (cdr (assoc 10 el)))
      (list c (distance c (cdr (assoc 15 el)))))))

;; note that the arc at centre with this radius now carries one
(defun ad:remrad (centre rad)
  (setq ad:*rads* (cons (list centre rad) ad:*rads*)))

;; T when that arc is dimensioned already - same centre, same radius
(defun ad:raddimmed-p (centre rad / tol lst q hit)
  (setq tol (ad:dupetol)
        lst ad:*rads*)
  (while (and lst (not hit))
    (setq q   (car lst)
          lst (cdr lst))
    (if (and (ad:samept (car q) centre tol)
             (<= (abs (- (cadr q) rad)) tol))
      (setq hit t)))
  hit)

;; read what the drawing already carries into ad:*dims* and ad:*rads*
(defun ad:dimscan (/ ss i en q)
  (setq ad:*dims* nil
        ad:*rads* nil
        ss        (ad:dimss)
        i         0)
  (if ss
    (repeat (sslength ss)
      (setq en (ssname ss i)
            i  (1+ i))
      (if (setq q (ad:dimpts en))
        (setq ad:*dims* (cons q ad:*dims*)))
      (if (setq q (ad:raddimpts en))
        (setq ad:*rads* (cons q ad:*rads*)))))
  ad:*dims*)

;; start a run: remember the style to fall back on and what is current,
;; zero the skip count and read the drawing's dimensions
(defun ad:begin ()
  (setq ad:*homestyle* (getvar "DIMSTYLE")
        ad:*curstyle*  (getvar "DIMSTYLE")
        ad:*skipped*   0)
  (ad:dimscan))

;; T when a and b are the same point on the plan, within tol
(defun ad:samept (a b tol)
  (and (<= (abs (- (car a) (car b))) tol)
       (<= (abs (- (cadr a) (cadr b))) tol)))

;; how far off the p1-p2 span the dimension line through loc sits,
;; signed, so two dims across the same points but on opposite sides do
;; not read as one.  Straight vector maths, not (angle ...), so a
;; rotated UCS cannot turn the answer round.
(defun ad:lineoff (p1 p2 loc / dx dy len)
  (setq dx  (- (car p2) (car p1))
        dy  (- (cadr p2) (cadr p1))
        len (sqrt (+ (* dx dx) (* dy dy))))
  (if (> len 1e-12)
    (/ (- (* dx (- (cadr loc) (cadr p1)))
          (* dy (- (car loc) (car p1))))
       len)
    0.0))

;; T when p1-p2 is already dimensioned with the dim line about where
;; loc would put it: same two origins either way round, dim line within
;; ad:bandtol.  This is the "do not add another one there" test.
(defun ad:dimmed-p (p1 p2 loc / tol band off lst q hit)
  (setq tol  (ad:dupetol)
        band (ad:bandtol)
        off  (ad:lineoff p1 p2 loc)
        lst  ad:*dims*)
  (while (and lst (not hit))
    (setq q   (car lst)
          lst (cdr lst))
    (if (and (or (and (ad:samept (car q) p1 tol)
                      (ad:samept (cadr q) p2 tol))
                 (and (ad:samept (car q) p2 tol)
                      (ad:samept (cadr q) p1 tol)))
             (<= (abs (- off (ad:lineoff p1 p2 (caddr q)))) band))
      (setq hit t)))
  hit)

;; Split records whose car is the measurement into groups of equal
;; measurement, within tol.  Order is kept both ways: a group sits
;; where its first member was found, and its members keep the order
;; they were found in - so "the one that gets the note" is the first
;; one the tool came across, every run.
(defun ad:groupsame (recs tol / out r g hit new)
  (setq out '())
  (foreach r recs
    (setq hit nil
          new '())
    (foreach g out
      (if (and (not hit) (<= (abs (- (car r) (car (car g)))) tol))
        (setq g   (append g (list r))
              hit t))
      (setq new (cons g new)))
    (if (not hit) (setq new (cons (list r) new)))
    (setq out (reverse new)))
  out)

;; count one dim left to the one already there
(defun ad:skip ()
  (setq ad:*skipped* (1+ ad:*skipped*))
  0)

;; tell the user what the run left to the dims that were already there
(defun ad:skipreport ()
  (if (> ad:*skipped* 0)
    (prompt (strcat "\n" (itoa ad:*skipped*)
                    " dimension(s) skipped - that place is dimensioned"
                    " already."))))

;; -------------------------------------------------- placing dimensions

;; place one aligned dimension - all points expected in WCS.  note is
;; appended to the measurement, "" leaving it as measured.
(defun ad:aligned (p1 p2 loc note)
  (if (= note "")
    (command "_.DIMALIGNED"
             "_non" (trans p1 0 1)
             "_non" (trans p2 0 1)
             "_non" (trans loc 0 1))
    (command "_.DIMALIGNED"
             "_non" (trans p1 0 1)
             "_non" (trans p2 0 1)
             "_T" (strcat "<>" note)
             "_non" (trans loc 0 1))))

;; place one linear dimension - dir is "_H" or "_V", points in WCS
(defun ad:lindim (p1 p2 loc dir)
  (command "_.DIMLINEAR"
           "_non" (trans p1 0 1)
           "_non" (trans p2 0 1)
           dir
           "_non" (trans loc 0 1)))

;; place one aligned dimension across p1-p2, in the style its length
;; calls for, unless that place is dimensioned already.  note is what
;; follows the measurement - "" for the measurement alone.
;; Returns 1 when a dimension was placed, 0 when it was not.
(defun ad:putaligned (p1 p2 loc base note / len)
  (setq len (distance p1 p2))
  (cond
    ((<= len 1e-8) 0)
    ((ad:dimmed-p p1 p2 loc) (ad:skip))
    (t (ad:usestyle (ad:styfor len base))
       (ad:aligned p1 p2 loc note)
       (ad:remember p1 p2 loc)
       1)))

;; the same for a horizontal ("_H") or vertical ("_V") linear dim - the
;; length that picks the style is the one the dim reads out, not the
;; distance between the two points
(defun ad:putlinear (p1 p2 loc dir base / len)
  (setq len (if (= dir "_V")
              (abs (- (cadr p1) (cadr p2)))
              (abs (- (car p1) (car p2)))))
  (cond
    ((<= len 1e-8) 0)
    ((ad:dimmed-p p1 p2 loc) (ad:skip))
    (t (ad:usestyle (ad:styfor len base))
       (ad:lindim p1 p2 loc dir)
       (ad:remember p1 p2 loc)
       1)))

;; place one radius dimension on the arc en, its leader reaching from
;; the point on it out to loc, unless that arc is dimensioned already.
;; note follows the measurement, "" leaving it as measured.
;; Returns 1 when a dimension was placed, 0 when it was not.
(defun ad:putradius (rad en on centre loc base note)
  (cond
    ((<= rad 1e-8) 0)
    ((ad:raddimmed-p centre rad) (ad:skip))
    (t (ad:usestyle (ad:styfor rad base))
       (if (= note "")
         (command "_.DIMRADIUS"
                  (list en (trans on 0 1))
                  "_non" (trans loc 0 1))
         (command "_.DIMRADIUS"
                  (list en (trans on 0 1))
                  "_T" (strcat "<>" note)
                  "_non" (trans loc 0 1)))
       (ad:remrad centre rad)
       1)))

;; one contiguous run of a chain, all of it in style sty: a first
;; aligned dim, then DIMCONTINUE through the rest.
;; Returns the number of dimensions placed.
(defun ad:putrun (pts loc sty / p prev)
  (ad:usestyle sty)
  (ad:aligned (car pts) (cadr pts) loc "")
  (ad:remember (car pts) (cadr pts) loc)
  (if (cddr pts)
    (progn
      (command "_.DIMCONTINUE")
      (setq prev (cadr pts))
      (foreach p (cddr pts)
        (command "_non" (trans p 0 1))
        (ad:remember prev p loc)
        (setq prev p))
      (command "" "")))
  (1- (length pts)))

;; place a continued dimension chain through the given WCS points.  A
;; span that is dimensioned already is left alone, and the chain breaks
;; there and wherever the style has to change - so a span under a foot
;; still lands in inches without dragging the rest of the chain with
;; it, and the pieces stay on the one dimension line through loc.
;; Returns the number of dimensions placed.
(defun ad:dimchain (pts loc base / cnt run sty a b d s dup)
  (setq cnt 0
        run nil
        sty nil)
  (while (cdr pts)
    (setq a   (car pts)
          b   (cadr pts)
          pts (cdr pts)
          d   (distance a b)
          dup (and (> d 1e-8) (ad:dimmed-p a b loc))
          s   (if (or (<= d 1e-8) dup) nil (ad:styfor d base)))
    (if dup (ad:skip))
    (if (and s run (ad:samestyle s sty))
      (setq run (cons b run))
      (progn
        (if (cdr run) (setq cnt (+ cnt (ad:putrun (reverse run) loc sty))))
        (if s
          (setq run (list b a)
                sty s)
          (setq run nil
                sty nil)))))
  (if (cdr run) (setq cnt (+ cnt (ad:putrun (reverse run) loc sty))))
  cnt)

;; every straight segment of a LINE or plan-view LWPOLYLINE as a list
;; of (p1 p2) pairs - other entity types return nil
(defun ad:segs (en / el pts blg segs n g)
  (setq el (entget en))
  (cond
    ((= "LINE" (cdr (assoc 0 el)))
     (list (list (cdr (assoc 10 el)) (cdr (assoc 11 el)))))
    ((and (= "LWPOLYLINE" (cdr (assoc 0 el)))
          (or (null (assoc 210 el))
              (equal (cdr (assoc 210 el)) '(0.0 0.0 1.0) 1e-6)))
     (setq pts '()
           blg '())
     (foreach g el
       (cond ((= 10 (car g)) (setq pts (cons (append (cdr g) '(0.0)) pts)))
             ((= 42 (car g)) (setq blg (cons (cdr g) blg)))))
     (setq pts (reverse pts)
           blg (reverse blg))
     ;; closed polylines also get their last->first segment
     (if (= 1 (logand 1 (cdr (assoc 70 el))))
       (setq pts (append pts (list (car pts)))))
     (setq segs '()
           n    0)
     (while (< (1+ n) (length pts))
       (if (or (null (nth n blg)) (equal 0.0 (nth n blg) 1e-8))
         (setq segs (cons (list (nth n pts) (nth (1+ n) pts)) segs)))
       (setq n (1+ n)))
     (reverse segs))))

;; The arc a bulged polyline segment describes, as (centre radius mid)
;; with mid the point half way round it - nil for a straight one.  The
;; bulge is tan(sweep/4), signed + for counter-clockwise, so the sweep
;; and the radius come straight back out of it and the centre sits on
;; the chord's perpendicular bisector, the signed radius putting it on
;; the correct side.
(defun ad:bulgearc (p1 p2 b / chord sweep rad cen)
  (setq chord (distance p1 p2))
  (if (and (> chord 1e-8) (> (abs b) 1e-8))
    (progn
      (setq sweep (* 4.0 (atan b))
            rad   (/ chord (* 2.0 (sin (/ sweep 2.0))))
            cen   (polar (cal:midn p1 p2)
                         (+ (angle p1 p2) (* 0.5 pi))
                         (* rad (cos (/ sweep 2.0)))))
      (list cen
            (abs rad)
            (polar cen (+ (angle cen p1) (/ sweep 2.0)) (abs rad))))))

;; every curved piece of every entity in ss, as
;; (radius entity point-on-it centre) - one per ARC and CIRCLE and one
;; per bulged segment of an LWPOLYLINE.  Radius first, so the records
;; group by size the same way the straight ones do.  Ellipses and
;; splines have no one radius to call out and are passed over.
(defun ad:arcs (ss / out i en el ty c r a1 a2 pts blg n p1 p2 arc)
  (setq out '()
        i   0)
  (if ss
    (repeat (sslength ss)
      (setq en (ssname ss i)
            i  (1+ i)
            el (entget en)
            ty (cdr (assoc 0 el)))
      (cond
        ((= ty "ARC")
         (setq c  (cdr (assoc 10 el))
               r  (cdr (assoc 40 el))
               a1 (cdr (assoc 50 el))
               a2 (cdr (assoc 51 el)))
         (if (< a2 a1) (setq a2 (+ a2 (* 2.0 pi))))
         (setq out (cons (list r en (polar c (* 0.5 (+ a1 a2)) r) c) out)))
        ((= ty "CIRCLE")
         (setq c (cdr (assoc 10 el))
               r (cdr (assoc 40 el)))
         (setq out (cons (list r en (polar c 0.0 r) c) out)))
        ((and (= ty "LWPOLYLINE")
              (or (null (assoc 210 el))
                  (equal (cdr (assoc 210 el)) '(0.0 0.0 1.0) 1e-6)))
         (setq pts '()
               blg '())
         (foreach c el
           (cond ((= 10 (car c)) (setq pts (cons (append (cdr c) '(0.0)) pts)))
                 ((= 42 (car c)) (setq blg (cons (cdr c) blg)))))
         (setq pts (reverse pts)
               blg (reverse blg))
         (if (= 1 (logand 1 (cdr (assoc 70 el))))
           (setq pts (append pts (list (car pts)))))
         (setq n 0)
         (while (< (1+ n) (length pts))
           (setq p1  (nth n pts)
                 p2  (nth (1+ n) pts)
                 arc (if (nth n blg) (ad:bulgearc p1 p2 (nth n blg))))
           (if arc
             (setq out (cons (list (cadr arc) en (caddr arc) (car arc)) out)))
           (setq n (1+ n)))))))
  (reverse out))

;; if the arc at centre with this radius lies on the perimeter, return
;; the angle from its centre out through mid to the clear side, else
;; nil.  Radially out first, then radially in, the way a straight
;; segment's two sides are tried.
(defun ad:arcang (centre mid diag eps ss / a)
  (setq a (angle centre mid))
  (cond ((ad:sideclear mid a diag eps ss) a)
        ((ad:sideclear mid (+ a pi) diag eps ss) (+ a pi))))

;; every straight segment of every entity in ss, as (p1 p2) pairs
(defun ad:allsegs (ss / i en s out)
  (setq out '()
        i   0)
  (if ss
    (repeat (sslength ss)
      (setq en (ssname ss i)
            i  (1+ i))
      (foreach s (ad:segs en)
        (if (> (distance (car s) (cadr s)) 1e-8)
          (setq out (cons s out))))))
  out)

;; how many curved pieces the selection holds: arc, circle, ellipse and
;; spline entities, the bulged segments of a polyline, and blocks,
;; whose contents cannot be read from the DXF list.  A flight of steps
;; drawn in side view has none of them.
(defun ad:curves (ss / i en el ty g n)
  (setq n 0
        i 0)
  (if ss
    (repeat (sslength ss)
      (setq en (ssname ss i)
            i  (1+ i)
            el (entget en)
            ty (cdr (assoc 0 el)))
      (cond
        ((wcmatch ty "ARC,CIRCLE,ELLIPSE,SPLINE,INSERT,POLYLINE")
         (setq n (1+ n)))
        ((= "LWPOLYLINE" ty)
         (foreach g el
           (if (and (= 42 (car g)) (> (abs (cdr g)) 1e-8))
             (setq n (1+ n))))))))
  n)

;; dxf filter for geometry that can be dimensioned / block a ray /
;; break a dim chain
(defun ad:geomfilter ()
  '((0 . "LINE,LWPOLYLINE,POLYLINE,ARC,CIRCLE,ELLIPSE,SPLINE,INSERT")))

;; everything in model space matching the geometry filter
(defun ad:geomss ()
  (ssget "_X" (append (ad:geomfilter) '((410 . "Model")))))

;; ------------------------------------------ part 1: perimeter dimensions

;; T if nothing in ss lies between pt and pt + dist along direction ang
(defun ad:sideclear (pt ang dist eps ss / lin lobj i rtn clear)
  (entmake (list '(0 . "LINE")
                 (cons 10 (polar pt ang eps))
                 (cons 11 (polar pt ang dist))))
  (setq lin   (entlast)
        lobj  (vlax-ename->vla-object lin)
        clear t
        i     0)
  (if ss
    (while (and clear (< i (sslength ss)))
      (setq rtn (vl-catch-all-apply
                  'vlax-invoke
                  (list lobj 'IntersectWith
                        (vlax-ename->vla-object (ssname ss i)) acextendnone)))
      (if (and (not (vl-catch-all-error-p rtn)) rtn)
        (setq clear nil))
      (setq i (1+ i))))
  (entdel lin)
  clear)

;; if segment p1-p2 lies on the perimeter of the highlighted geometry,
;; return the angle pointing to its clear (outside) side, else nil
(defun ad:perimang (p1 p2 diag eps ss / mid a)
  (setq mid (cal:midn p1 p2)
        a   (angle p1 p2))
  (cond ((ad:sideclear mid (+ a (* 0.5 pi)) diag eps ss) (+ a (* 0.5 pi)))
        ((ad:sideclear mid (- a (* 0.5 pi)) diag eps ss) (- a (* 0.5 pi)))))

;; every straight segment on the perimeter of ss, as
;; (length p1 p2 where-its-dim-goes).  Length first, so the records
;; group by size.
(defun ad:perimsegs (ss diag eps off / out i en seg len pa)
  (setq out '()
        i   0)
  (repeat (sslength ss)
    (setq en (ssname ss i)
          i  (1+ i))
    (foreach seg (ad:segs en)
      (setq len (distance (car seg) (cadr seg)))
      (if (and (> len 1e-8)
               (setq pa (ad:perimang (car seg) (cadr seg) diag eps ss)))
        (setq out (cons (list len (car seg) (cadr seg)
                              (polar (cal:midn (car seg) (cadr seg)) pa off))
                        out)))))
  (reverse out))

;; every arc on the perimeter of ss, as
;; (radius entity point-on-it centre where-its-dim-goes)
(defun ad:perimarcs (ss diag eps off / out rec pa)
  (setq out '())
  (foreach rec (ad:arcs ss)
    (if (setq pa (ad:arcang (cadddr rec) (caddr rec) diag eps ss))
      (setq out (cons (append rec (list (polar (caddr rec) pa off))) out))))
  (reverse out))

;; Dimension the perimeter of the highlighted geometry in ss: its
;; straight sides, then its arcs by radius.  A measurement that repeats
;; is called out once, on the first one found, with ad:*typ-note* after
;; it, and the rest are left to that note - from ad:*typ-lines* equal
;; sides up, and from ad:*typ-curves* equal radii up.  Below those
;; counts every one is dimensioned where it is.
;; Returns how many dimensions were placed.
(defun ad:dimperim (ss / box diag eps off cnt g rec)
  (setq box (cal:bbox-ss ss)
        cnt 0)
  (if box
    (progn
      (setq diag (* 2.0 (distance (car box) (cadr box)))
            eps  (* 1e-6 diag)
            ;; at least a foot away from the perimeter, heading outwards
            off  (max (ad:dimoff) (ad:onefoot)))
      ;; the straight sides
      (foreach g (ad:groupsame (ad:perimsegs ss diag eps off) (ad:dupetol))
        (if (>= (length g) ad:*typ-lines*)
          (setq rec (car g)
                cnt (+ cnt (ad:putaligned (cadr rec) (caddr rec) (cadddr rec)
                                          ad:*style-plan* ad:*typ-note*)))
          (foreach rec g
            (setq cnt (+ cnt (ad:putaligned (cadr rec) (caddr rec) (cadddr rec)
                                            ad:*style-plan* ""))))))
      ;; the arcs, by radius
      (foreach g (ad:groupsame (ad:perimarcs ss diag eps off) (ad:dupetol))
        (if (>= (length g) ad:*typ-curves*)
          (setq rec (car g)
                cnt (+ cnt (ad:putradius (car rec) (cadr rec) (caddr rec)
                                         (cadddr rec) (nth 4 rec)
                                         ad:*style-plan* ad:*typ-note*)))
          (foreach rec g
            (setq cnt (+ cnt (ad:putradius (car rec) (cadr rec) (caddr rec)
                                           (cadddr rec) (nth 4 rec)
                                           ad:*style-plan* ""))))))))
  cnt)

;; --------------------------------------------- part 2: stairs dimensions

;; ask the user to highlight the stairs.  The treads - the largest
;; group of parallel straight lines in the selection - get their widths
;; dimensioned, and the distances between them chained beside the
;; stair.  Both go in the plan style, or in inches when they measure
;; under a foot, which the gap between two treads usually does.
;; Returns the number of dimensions placed.
(defun ad:dimstairs (/ ss segs s a hit g out groups best u v off
                       tds td w lastw mid loc smax ts prev pts cnt)
  (prompt (strcat "\nHighlight the stairs (window or pick the tread"
                  " lines), then press Enter."
                  "\nStep widths and the distances between steps both"
                  " get dimensioned - anything under 12\" in"
                  " \"STANDARD INCHES\"."
                  "  Press Enter without selecting to skip."))
  (setq ss  (ssget '((0 . "LINE,LWPOLYLINE")))
        cnt 0)
  (if ss
    (progn
      (setq segs (ad:allsegs ss))
      ;; group the segments by direction - the biggest group of
      ;; parallel lines is taken as the treads
      (setq groups '())
      (foreach s segs
        (setq a   (ad:segang s)
              hit nil
              out '())
        (foreach g groups
          (if (and (not hit) (< (ad:angdiff a (car g)) 1e-3))
            (setq g   (cons (car g) (cons s (cdr g)))
                  hit t))
          (setq out (cons g out)))
        (if (not hit) (setq out (cons (list a s) out)))
        (setq groups out))
      (setq best nil)
      (foreach g groups
        (if (or (null best) (> (length (cdr g)) (length (cdr best))))
          (setq best g)))
      (if best
        (progn
          (setq a   (car best)
                u   (list (cos a) (sin a) 0.0)          ; along the treads
                v   (list (- (sin a)) (cos a) 0.0)      ; up the stair
                off (ad:dimoff)
                tds '()
                smax nil)
          ;; sort the treads up the stair and find the stair's side edge
          (foreach s (cdr best)
            (setq tds  (cons (cons (cal:dotn (cal:midn (car s) (cadr s)) v) s) tds)
                  smax (apply 'max
                              (append (if smax (list smax))
                                      (list (cal:dotn (car s) u)
                                            (cal:dotn (cadr s) u))))))
          (setq tds (vl-sort tds '(lambda (x y) (< (car x) (car y)))))
          ;; widths of the steps (repeated only when the width changes)
          (setq lastw nil)
          (foreach td tds
            (setq w (distance (cadr td) (caddr td)))
            (if (or (null lastw) (> (abs (- w lastw)) 1e-4))
              (progn
                (setq mid (cal:midn (cadr td) (caddr td))
                      loc (mapcar '(lambda (m vv) (- m (* off vv))) mid v))
                (setq cnt   (+ cnt (ad:putaligned (cadr td) (caddr td) loc
                                                  ad:*style-plan* ""))
                      lastw w))))
          ;; distances between the steps, chained beside the stair
          (setq ts   '()
                prev nil)
          (foreach td tds
            (if (or (null prev) (> (- (car td) prev) 1e-4))
              (setq ts   (cons (car td) ts)
                    prev (car td))))
          (setq ts (reverse ts))
          (if (cdr ts)
            (progn
              (setq pts (mapcar
                          '(lambda (tv)
                             (mapcar '(lambda (uu vv)
                                        (+ (* smax uu) (* tv vv)))
                                     u v))
                          ts)
                    loc (mapcar '(lambda (uu vv)
                                   (+ (* (+ smax off) uu) (* (car ts) vv)))
                                u v))
              (setq cnt (+ cnt (ad:dimchain pts loc ad:*style-plan*)))))))))
  cnt)

;; ------------------------------------------------- part 3: the floor dims

;; WCS intersection points between the line object and every object in ss
(defun ad:xpoints (lobj ss / i rtn pts res)
  (setq res '()
        i   0)
  (if ss
    (repeat (sslength ss)
      (setq rtn (vl-catch-all-apply
                  'vlax-invoke
                  (list lobj 'IntersectWith
                        (vlax-ename->vla-object (ssname ss i)) acextendnone)))
      (setq i (1+ i))
      (if (not (vl-catch-all-error-p rtn))
        (progn
          (setq pts rtn)
          (while (and pts (cddr pts))
            (setq res (cons (list (car pts) (cadr pts) (caddr pts)) res)
                  pts (cdddr pts)))))))
  res)

;; build one floor dims chain along p1->p2 (WCS): a first aligned dim
;; followed by DIMCONTINUE through every break point, breaking wherever
;; an obstacle stands in the line's way.  An end point the user did not
;; land on an object is pulled back to the last object before it, so
;; every dim runs object to object.
;; Returns the number of dimensions placed.
(defun ad:floorchain (p1 p2 loc obstacles / ssx lin lobj len dir ds d x
                                            starton endon chain prev)
  (setq ssx (if obstacles obstacles (ad:geomss)))
  (entmake (list '(0 . "LINE") (cons 10 p1) (cons 11 p2)))
  (setq lin  (entlast)
        lobj (vlax-ename->vla-object lin))
  (if (and ssx (ssmemb lin ssx)) (ssdel lin ssx))
  (setq len (distance p1 p2)
        dir (mapcar '(lambda (b c) (/ (- c b) len)) p1 p2)
        ds  '())
  ;; distance of every crossing object along the line, noting crossings
  ;; sitting right on the picked start / end points
  (foreach x (ad:xpoints lobj ssx)
    (setq d (apply '+ (mapcar '* dir (mapcar '- x p1))))
    (cond ((< (abs d) 1e-4)           (setq starton t))
          ((< (abs (- d len)) 1e-4)   (setq endon t))
          ((and (> d 1e-4) (< d (- len 1e-4))) (setq ds (cons d ds)))))
  (entdel lin)
  ;; sorted break points, near-coincident ones merged
  (setq chain (list p1)
        prev  0.0)
  (foreach d (vl-sort ds '<)
    (if (> (- d prev) 1e-4)
      (setq chain (cons (mapcar '(lambda (b v) (+ b (* d v))) p1 dir) chain)
            prev  d)))
  (setq chain (reverse (cons p2 chain)))
  ;; an end the user did not land on an object is pulled back to the
  ;; last object before it, so every dim in the chain runs object to
  ;; object and none hangs off the end into open drawing
  (if (not starton)
    (progn
      (setq chain (cdr chain))
      (prompt (strcat "\n  (start point was not on an object - the chain"
                      " starts at the first one the line crosses)"))))
  (if (and (cdr chain) (not endon))
    (progn
      (setq chain (reverse (cdr (reverse chain))))
      (prompt (strcat "\n  (end point was not on an object - the chain"
                      " stops at the last one the line crosses)"))))
  (if (cdr chain)
    (ad:dimchain chain loc ad:*style-floor*)
    0))

;; erase everything drawn after entity MARK (nil = an empty drawing) -
;; the rollback when a Back re-opens an earlier dimensioning step.  The
;; record of what is dimensioned is read again afterwards, so a dim
;; this rolled back does not go on blocking its own place.
(defun ad:eraseafter (mark / en nx)
  (setq en (if mark (entnext mark) (entnext)))
  (while en
    (setq nx (entnext en))
    (if (entget en) (entdel en))
    (setq en nx))
  (ad:dimscan))

;; prompt the user to draw one floor dims line and dimension it,
;; breaking at the given obstacles (nil = all model space geometry).
;; The three picks step back through each other with Back (Undo is
;; accepted too); with BACK non-nil, Back at the START pick returns
;; the symbol CAL-BACK so the caller can re-open its previous step.
;; Returns the dimension count, or nil when the line was skipped.
(defun ad:getfloor (tag obstacles back / p1 p2 loc n stage out)
  (setq stage 1 out nil)
  (while (null out)
    (cond
      ((= stage 1)
       (if back (initget "Back Undo") (initget ""))
       (setq p1 (getpoint (strcat "\n" tag
                                  " - pick the START point of the line to"
                                  " measure along (Enter to skip"
                                  (if back ", or Back" "") "): ")))
       (cond
         ((null p1) (prompt "\nNothing drawn - skipped.") (setq out 'skip))
         ((= (type p1) 'STR) (setq out 'CAL-BACK))
         (T (setq stage 2))))
      ((= stage 2)
       (initget "Back Undo")
       (setq p2 (getpoint p1 (strcat "\n" tag
                                     " - pick the END point [Back]: ")))
       (cond
         ((= (type p2) 'STR) (setq stage 1))
         ((or (null p2) (<= (distance p1 p2) 1e-8))
          (prompt "\nNothing drawn - skipped.")
          (setq out 'skip))
         (T (setq stage 3))))
      (T
       (initget "Back Undo")
       (setq loc (getpoint (strcat "\n" tag
                                   " - pick where the dimension chain"
                                   " should sit <on the drawn line> [Back]: ")))
       (if (= (type loc) 'STR)
         (setq stage 2)
         (progn
           (if (null loc) (setq loc (cal:midn p1 p2)))
           (setq n (ad:floorchain (trans p1 1 0) (trans p2 1 0)
                                  (trans loc 1 0) obstacles))
           (if (> n 0)
             (prompt (strcat "\n" tag ": " (itoa n) " dimension(s) placed."))
             (prompt (strcat "\n" tag ": the line did not cross two"
                             " objects - no dimensions placed.")))
           (setq out (list n)))))))
  (cond
    ((eq out 'CAL-BACK) 'CAL-BACK)
    ((eq out 'skip) nil)
    (T (car out))))

;; ---------------------------------------------- part 4: the overall dims

;; T when the boxes a and b, each (min max), overlap in plan
(defun ad:boxlap (a b)
  (and (<= (car  (car a)) (car  (cadr b)))
       (>= (car  (cadr a)) (car  (car b)))
       (<= (cadr (car a)) (cadr (cadr b)))
       (>= (cadr (cadr a)) (cadr (car b)))))

;; the extents the overall dims have to clear: the plan's own box grown
;; by every dimension sitting around it.  Dims far away - another plan
;; on the same sheet, the title block - are left out; only those within
;; a margin of the plan count as its dims.
(defun ad:dimextents (plan / box mrg near ss i en b mn mx)
  (setq box (cal:bbox-ss plan))
  (if box
    (progn
      (setq mrg  (max (* 4.0 (ad:onefoot)) (* 4.0 (ad:dimoff)))
            near (list (mapcar '(lambda (v) (- v mrg)) (car box))
                       (mapcar '(lambda (v) (+ v mrg)) (cadr box)))
            mn   (car box)
            mx   (cadr box)
            ss   (ad:dimss)
            i    0)
      (if ss
        (repeat (sslength ss)
          (setq en (ssname ss i)
                i  (1+ i)
                b  (cal:bbox-ent en))
          (if (and b (ad:boxlap b near))
            (setq mn (mapcar 'min mn (car b))
                  mx (mapcar 'max mx (cadr b))))))
      (list mn mx))))

;; the two overall dims, both in the "STANDARD" style: the plan's full
;; width about two feet above the topmost dimension around it, and its
;; full height about two feet to the left of the left-most one.  Both
;; extents are read before either dim goes in, so the first one placed
;; cannot push the second further out.
;; Returns how many were placed (0, 1 or 2 - one already there is not
;; repeated).
(defun ad:overall (plan / box out gap x0 y0 x1 y1 cnt)
  (setq cnt 0
        box (cal:bbox-ss plan))
  (if box
    (progn
      (setq out (ad:dimextents plan)
            gap (* 2.0 (ad:onefoot))
            x0  (car  (car box))
            y0  (cadr (car box))
            x1  (car  (cadr box))
            y1  (cadr (cadr box)))
      ;; overall width, sitting two feet above the topmost dim
      (setq cnt (+ cnt (ad:putlinear
                         (list x0 y1 0.0)
                         (list x1 y1 0.0)
                         (list (* 0.5 (+ x0 x1)) (+ (cadr (cadr out)) gap) 0.0)
                         "_H" ad:*style-over*)))
      ;; overall height, sitting two feet left of the left-most dim
      (setq cnt (+ cnt (ad:putlinear
                         (list x0 y0 0.0)
                         (list x0 y1 0.0)
                         (list (- (car (car out)) gap) (* 0.5 (+ y0 y1)) 0.0)
                         "_V" ad:*style-over*)))))
  cnt)

;; ------------------------------------- part 5: steps drawn in side view

;; every vertical segment in ss as (top bottom), from the top step down
;; - the risers of a flight drawn in side view
(defun ad:risers (ss / s out)
  (setq out '())
  (foreach s (ad:allsegs ss)
    (if (and (< (ad:angdiff (ad:segang s) (* 0.5 pi)) 1e-3)
             (> (abs (- (cadr (car s)) (cadr (cadr s)))) 1e-4))
      (setq out (cons (if (> (cadr (car s)) (cadr (cadr s)))
                        s
                        (list (cadr s) (car s)))
                      out))))
  (ad:topdown out))

;; risers ordered from the top step down
(defun ad:topdown (risers)
  (vl-sort risers '(lambda (a b) (> (cadr (car a)) (cadr (car b))))))

;; the nosing corners of a flight, top down: the top of the top riser,
;; then the bottom corner of every riser going down the flight
(defun ad:stepchain (risers)
  (cons (car (car risers)) (mapcar 'cadr risers)))

;; T when the risers, taken in the order given, are a connected
;; staircase: each one starts where the one before it finished, a
;; tread's run further along
(defun ad:stairlike-p (risers tol / r prev ok)
  (setq ok   t
        prev (car risers))
  (foreach r (cdr risers)
    (if (or (> (abs (- (cadr (car r)) (cadr (cadr prev)))) tol)
            (<= (abs (- (car (car r)) (car (car prev)))) tol))
      (setq ok nil))
    (setq prev r))
  ok)

;; Does the highlighted geometry look like a flight of steps drawn in
;; side view rather than a plan?  It does when
;;   * nothing in it is curved - no arc, circle, ellipse, spline,
;;     polyline bulge or block;
;;   * three quarters or more of its straight segments run square, so a
;;     sloping pool floor at the foot of the flight is still allowed;
;;   * it has two or more risers and at least one tread per gap
;;     between them;
;;   * and the risers form a connected staircase across the drawing,
;;     each starting where the one before it finished.
;; A vertical as tall as the whole profile is the back wall, not a
;; step, and is left out of that reckoning - which is also what stops a
;; rectangular plan reading as a two-step flight.
;; Returns the risers, top down, or nil.
(defun ad:stepprofile-p (ss / segs s pp vert horz nsq ymin ymax hgt
                              tol risers r)
  (setq segs (ad:allsegs ss)
        vert '()
        horz '()
        ymin nil
        ymax nil)
  (foreach s segs
    (cond ((< (ad:angdiff (ad:segang s) (* 0.5 pi)) 1e-3)
           (setq vert (cons s vert)))
          ((< (ad:angdiff (ad:segang s) 0.0) 1e-3)
           (setq horz (cons s horz))))
    (foreach pp s
      (setq ymin (if ymin (min ymin (cadr pp)) (cadr pp))
            ymax (if ymax (max ymax (cadr pp)) (cadr pp)))))
  (setq nsq (+ (length vert) (length horz))
        hgt (if ymin (- ymax ymin) 0.0))
  (if (and (> hgt 1e-8)
           (zerop (ad:curves ss))
           (>= (length vert) 2)
           (>= (length horz) 1)
           (>= (* 4 nsq) (* 3 (length segs))))
    (progn
      ;; the risers, a full-height back wall left out
      (setq tol    (max (ad:dupetol) (* 0.01 hgt))
            risers '())
      (foreach s vert
        (setq r (if (> (cadr (car s)) (cadr (cadr s)))
                  s
                  (list (cadr s) (car s))))
        (if (< (- (cadr (car r)) (cadr (cadr r))) (* 0.9 hgt))
          (setq risers (cons r risers))))
      (setq risers (vl-sort risers
                            '(lambda (a b) (< (car (car a)) (car (car b))))))
      (if (and (cdr risers)
               (>= (length horz) (1- (length risers)))
               (or (ad:stairlike-p risers tol)
                   (ad:stairlike-p (reverse risers) tol)))
        (ad:topdown risers)))))

;; Dimension a flight of steps drawn in side view: one vertical dim for
;; the depth of every step, then the overall depth one step further
;; out.  side is 1.0 to put them to the right of the profile, -1.0 to
;; put them to the left.  With stack non-nil they all sit on one line
;; clear of the whole flight; with it nil each sits just outside its
;; own step, walking down with the stairs.
;; Returns the number of dimensions placed.
(defun ad:dimsteps (chain side stack base / clear xs xdim edge loc
                                            cnt nris prev pb)
  (setq clear (max (ad:dimoff) (* 2.0 (ad:onefoot)))
        cnt   0
        nris  0
        edge  nil
        prev  (car chain))
  (if stack
    (setq xs   (mapcar 'car chain)
          xdim (+ (* side clear)
                  (if (> side 0.0) (apply 'max xs) (apply 'min xs)))
          edge xdim))
  (foreach pb (cdr chain)
    (if (> (abs (- (cadr prev) (cadr pb))) 1e-4)
      (progn
        (if (not stack)
          (setq xdim (+ (* side clear)
                        (if (> side 0.0)
                          (max (car prev) (car pb))
                          (min (car prev) (car pb))))
                edge (cond ((null edge) xdim)
                           ((> side 0.0) (max edge xdim))
                           (t (min edge xdim)))))
        (setq loc  (list xdim (* 0.5 (+ (cadr prev) (cadr pb))) 0.0)
              cnt  (+ cnt (ad:putlinear prev pb loc "_V" base))
              nris (1+ nris))))
    (setq prev pb))
  ;; the overall depth, one step further out again - counted off the
  ;; risers found, not the dims placed, so a flight that is dimensioned
  ;; already still gets its overall
  (if (> nris 1)
    (setq cnt (+ cnt (ad:putlinear
                       (last chain) (car chain)
                       (list (+ edge (* side clear))
                             (* 0.5 (+ (cadr (car chain))
                                       (cadr (last chain))))
                             0.0)
                       "_V" base))))
  cnt)

;; --------------------------------------------------------------- commands

;; AUTODIM's plan flow, steps 2 to 5: the perimeter, then the stairs,
;; then the two floor dims lines, then the two overall dims.
(defun ad:runplan (plan / nper nstair nover stage mark3 mark4 v)
  (prompt (strcat "\n=== AUTODIM step 2 of 5: perimeter ==="
                  "\nDimensioning the straight lines about the"
                  " perimeter - no input needed..."))
  (setq nper (ad:dimperim plan))
  (prompt (strcat "\n" (itoa nper) " perimeter dimension(s) placed."))
  ;; steps 3 and 4 walk back through each other: Back at the floor dims
  ;; question re-opens the stairs, erasing what they drew, and Back at
  ;; the second floor line re-opens the first
  (setq stage 3)
  (while (< stage 7)
    (cond
      ((= stage 3)
       (prompt "\n=== AUTODIM step 3 of 5: stairs ===")
       (setq mark3  (entlast)
             nstair (ad:dimstairs))
       (prompt (strcat "\n" (itoa nstair) " stair dimension(s) placed."))
       (setq stage 4))
      ((= stage 4)
       (prompt (strcat "\n=== AUTODIM step 4 of 5: floor dims ==="
                       "\nTwo lines drawn across the plan, each becoming a"
                       " dimension chain in \"" ad:*style-floor* "\" that"
                       " breaks at every highlighted object it crosses.  A"
                       " start or end point that is not on an object pulls"
                       " back to the last object before it, so every dim"
                       " runs object to object."))
       (setq v (cal:askyn "Would you like floor dims?" "Yes" T))
       (cond
         ((eq v 'CAL-BACK)
          (ad:eraseafter mark3)
          (prompt "\nStepping back to the stairs.")
          (setq stage 3))
         (v (setq stage 5))
         (T (prompt "\nNo floor dims.")
            (setq stage 7))))
      ((= stage 5)
       (setq mark4 (entlast)
             v     (ad:getfloor "Floor dims 1 of 2" plan T))
       (if (eq v 'CAL-BACK)
         (progn
           (prompt "\nStepping back to the floor dims question.")
           (setq stage 4))
         (setq stage 6)))
      (T
       (setq v (ad:getfloor "Floor dims 2 of 2" plan T))
       (if (eq v 'CAL-BACK)
         (progn
           (ad:eraseafter mark4)
           (prompt "\nStepping back one floor line.")
           (setq stage 5))
         (setq stage 7)))))
  (prompt (strcat "\n=== AUTODIM step 5 of 5: overall dims ==="
                  "\nPlacing the overall width about 2ft above the"
                  " topmost dim and the overall height about 2ft to"
                  " the left of the left-most one - no input"
                  " needed..."))
  (setq nover (ad:overall plan))
  (prompt (strcat "\n" (itoa nover) " overall dimension(s) placed."))
  (princ))

;; AUTODIM's side-view flow, for when step 1's selection turned out to
;; be a flight of steps drawn in side view: the depth of every step
;; down the right-hand side, then the overall depth further right
;; again.  Nothing else is asked for - the perimeter, stairs and floor
;; dims steps are all about a plan.
(defun ad:runsteps (risers / n)
  (prompt (strcat "\n=== AUTODIM: that is a side view of steps ==="
                  "\nDimensioning the depth of every step, to the right"
                  " of the flight in \"" ad:*style-short* "\", and the"
                  " overall depth further right again - no input"
                  " needed..."))
  (setq n (ad:dimsteps (ad:stepchain risers) 1.0 T ad:*style-short*))
  (prompt (strcat "\n" (itoa n) " step dimension(s) placed."))
  (princ))

(defun c:AUTODIM (/ *error* oldcmd olddim plan risers)
  (defun *error* (msg)
    (vl-catch-all-apply 'command-s (list "_.UNDO" "_End"))
    (if olddim
      (vl-catch-all-apply 'command-s (list "_.-DIMSTYLE" "_Restore" olddim)))
    (if oldcmd (setvar "CMDECHO" oldcmd))
    (if (and msg (not (wcmatch (strcase msg) "*BREAK*,*CANCEL*,*QUIT*,*EXIT*")))
      (prompt (strcat "\nAutoDim error: " msg)))
    (princ))
  (prompt (strcat "\n=== AUTODIM step 1: highlight the plan ==="
                  "\nHighlight everything that makes up the plan (walls"
                  " etc.), then press Enter.  Only what you highlight is"
                  " dimensioned and used to find the perimeter."
                  "\nHighlight a flight of steps drawn in side view"
                  " instead and it is recognised as one: the depth of"
                  " every step gets dimensioned rather than a plan."))
  (setq plan (ssget (ad:geomfilter)))
  (if (null plan)
    (prompt "\nNothing highlighted - AUTODIM cancelled.")
    (progn
      (setq oldcmd (getvar "CMDECHO")
            olddim (getvar "DIMSTYLE"))
      (setvar "CMDECHO" 0)
      (ad:begin)
      (command "_.UNDO" "_Begin")
      (if (setq risers (ad:stepprofile-p plan))
        (ad:runsteps risers)
        (ad:runplan plan))
      (ad:skipreport)
      (ad:usestyle olddim)
      (command "_.UNDO" "_End")
      (setvar "CMDECHO" oldcmd)
      (prompt "\nAUTODIM finished.")))
  (princ))

(defun c:STAIRDIM (/ *error* oldcmd olddim n)
  (defun *error* (msg)
    (vl-catch-all-apply 'command-s (list "_.UNDO" "_End"))
    (if olddim
      (vl-catch-all-apply 'command-s (list "_.-DIMSTYLE" "_Restore" olddim)))
    (if oldcmd (setvar "CMDECHO" oldcmd))
    (if (and msg (not (wcmatch (strcase msg) "*BREAK*,*CANCEL*,*QUIT*,*EXIT*")))
      (prompt (strcat "\nAutoDim error: " msg)))
    (princ))
  (setq oldcmd (getvar "CMDECHO")
        olddim (getvar "DIMSTYLE"))
  (setvar "CMDECHO" 0)
  (ad:begin)
  (command "_.UNDO" "_Begin")
  (setq n (ad:dimstairs))
  (prompt (strcat "\n" (itoa n) " stair dimension(s) placed."))
  (ad:skipreport)
  (ad:usestyle olddim)
  (command "_.UNDO" "_End")
  (setvar "CMDECHO" oldcmd)
  (princ))

(defun c:FLOORDIM (/ *error* oldcmd olddim)
  (defun *error* (msg)
    (vl-catch-all-apply 'command-s (list "_.UNDO" "_End"))
    (if olddim
      (vl-catch-all-apply 'command-s (list "_.-DIMSTYLE" "_Restore" olddim)))
    (if oldcmd (setvar "CMDECHO" oldcmd))
    (if (and msg (not (wcmatch (strcase msg) "*BREAK*,*CANCEL*,*QUIT*,*EXIT*")))
      (prompt (strcat "\nAutoDim error: " msg)))
    (princ))
  (setq oldcmd (getvar "CMDECHO")
        olddim (getvar "DIMSTYLE"))
  (setvar "CMDECHO" 0)
  (ad:begin)
  (command "_.UNDO" "_Begin")
  (ad:getfloor "Floor dims" nil nil)
  (ad:skipreport)
  (ad:usestyle olddim)
  (command "_.UNDO" "_End")
  (setvar "CMDECHO" oldcmd)
  (princ))

;; AUTODIMSIDEPOV - dimension steps drawn in side view (elevation):
;; every riser gets a vertical dimension placed beside its step,
;; stepping down the flight with the nosing corners as extension line
;; origins, plus one overall height dimension further out.  The dims
;; are created on layer "DIMENSION" in the "STANDARD INCHES" style to
;; match the reference drawing - a riser is under a foot anyway, so
;; that is the style the length rule asks for too.  A riser that is
;; dimensioned already is left alone, as everywhere else.
(defun c:AUTODIMSIDEPOV (/ *error* oldcmd olddim oldlay ss risers chain
                            sx cnt)
  (defun *error* (msg)
    (vl-catch-all-apply 'command-s (list "_.UNDO" "_End"))
    (if olddim
      (vl-catch-all-apply 'command-s (list "_.-DIMSTYLE" "_Restore" olddim)))
    (if oldlay (setvar "CLAYER" oldlay))
    (if oldcmd (setvar "CMDECHO" oldcmd))
    (if (and msg (not (wcmatch (strcase msg) "*BREAK*,*CANCEL*,*QUIT*,*EXIT*")))
      (prompt (strcat "\nAutoDim error: " msg)))
    (princ))
  (prompt (strcat "\nAUTODIMSIDEPOV - dimensions steps drawn in side view:"
                  " every riser gets a vertical dim beside its step, plus"
                  " the overall height."
                  "\nHighlight the side view of the steps, then press"
                  " Enter."))
  (setq ss (ssget '((0 . "LINE,LWPOLYLINE"))))
  (if (null ss)
    (prompt "\nNothing highlighted - AUTODIMSIDEPOV cancelled.")
    (progn
      (setq oldcmd (getvar "CMDECHO")
            olddim (getvar "DIMSTYLE")
            oldlay (getvar "CLAYER"))
      (setvar "CMDECHO" 0)
      (ad:begin)
      (command "_.UNDO" "_Begin")
      (ad:setlayer "DIMENSION")
      ;; told these are steps, so every vertical is taken as a riser -
      ;; no staircase test here, unlike AUTODIM's own side-view branch
      (setq risers (ad:risers ss))
      (if (null risers)
        (prompt (strcat "\nNo vertical riser lines found in the selection"
                        " - nothing dimensioned."))
        (progn
          (setq chain (ad:stepchain risers)
                ;; dims go on the high side of the steps
                sx    (if (>= (car (car chain)) (car (last chain))) 1.0 -1.0)
                cnt   (ad:dimsteps chain sx nil ad:*style-short*))
          (prompt (strcat "\n" (itoa cnt) " step dimension(s) placed."))
          (ad:skipreport)))
      (ad:usestyle olddim)
      (setvar "CLAYER" oldlay)
      (command "_.UNDO" "_End")
      (setvar "CMDECHO" oldcmd)))
  (princ))

(princ "\nAutoDim.lsp loaded.  Commands: AUTODIM (highlight plan -> perimeter + stairs + two floor dims + the two overall dims; highlight a side view of steps -> the depth of every step), STAIRDIM (dimension another stair selection), FLOORDIM (one extra floor dims chain), AUTODIMSIDEPOV (dimension steps drawn in side view).")
(princ)


;;; ======================================================================
;;; >>> BPCALLOUT.lsp
;;; ======================================================================

;;; ===================================================================
;;; BPCALLOUT.lsp  --  ring bad points and write the callout naming them
;;; -------------------------------------------------------------------
;;; For AutoCAD 2018 and later (plain AutoLISP, no external libraries).
;;;
;;; Command:  BPCALLOUT
;;;
;;; SHARED BUILD: requires CALOFIN-LIB.lsp (load via CALOFIN-LOADER.lsp).
;;; Generic helpers live there under cal: - see STANDARDS.md.
;;;
;;; Click every point that is bad, one after another, as many as you
;;; like; press Enter when done.  Each click:
;;;   * snaps to the nearest survey point within *BP-SNAP* of the pick
;;;     (an "ab_pt" INSERT on any layer, any other INSERT on the POINTS
;;;     layer, or a plain POINT on the POINTS layer - the same
;;;     classifier the rest of the toolset uses),
;;;   * draws a *BP-RADIUS* circle on the FGStep layer centered on
;;;     that point, and
;;;   * reads what the point is called from the block's "number"
;;;     attribute, the name the drawing itself carries.
;;; After the last click you place one TEXT that names them all:
;;;
;;;   "Pt.12 is bad"                            (one point)
;;;   "Pt.12 and Pt.15 are bad"                 (two)
;;;   "Pt.12, Pt.15 and Pt.20 are bad"          (three or more)
;;;
;;; A click that lands nowhere near a survey point is still ringed -
;;; exactly where you clicked - and reported as "Pt.?", so a stray
;;; shot with no block under it can be called out too.  Clicking a
;;; ringed point AGAIN un-rings it: the circle is erased and the point
;;; leaves the callout - reselect a point to undo it.
;;;
;;; Versioning: see tools/release_lisp.py at the repo root.  It reads
;;; *bpcallout-version* below and stamps a dated, REV-numbered twin of
;;; this file into releases/.
;;;
;;; Assumes drawing units are INCHES (architectural).  Adjust the
;;; constants below for other setups.
;;; ===================================================================

;; ---- configuration -------------------------------------------------
(setq *bpcallout-version* "v1.4")   ; announced on load; release_lisp.py
                                    ; reads this banner and stamps the
                                    ; dated twin in releases/ from it
(setq *BP-LAYER*       "FGStep")    ; layer the rings and the callout
                                    ; text go on - the same layer LHD
                                    ; puts its miss rings on
(setq *BP-RADIUS*      5.0)         ; ring RADIUS (5 inches); halve it
                                    ; here if a 5" diameter is wanted
(setq *BP-SNAP*        12.0)        ; a pick within this of a survey
                                    ; point rings THAT point; farther
                                    ; away, the pick itself is ringed
                                    ; and named "?"
(setq *BP-TEXT-HGT*    6.0)         ; callout text height
(setq *BP-POINT-BLOCK* "ab_pt")     ; block name whose INSERTs mark
                                    ; points wherever they sit
(setq *BP-POINT-LAYER* "POINTS")    ; layer whose POINTs/INSERTs are
                                    ; always points
(setq *BP-PT-TAG*      "number")    ; attribute tag on the point block
                                    ; naming the point, as in "Pt.17"
(setq *BP-EXACT-EPS*   0.001)       ; two picks this close land on the
                                    ; same spot - the second un-rings it

;; ---- helpers -------------------------------------------------------

;; Flat XY distance, whatever Z the inputs carry.
(defun bp:dist (a b)
  (distance (list (car a) (cadr a)) (list (car b) (cadr b))))

;; Every survey point in the drawing, as ((x y) . name) pairs.  What
;; counts as a point matches LHD's classifier: an *BP-POINT-BLOCK*
;; INSERT anywhere, any other INSERT on the *BP-POINT-LAYER* layer,
;; or a plain POINT on that layer.  A point with no readable number
;; is carried as "?" so it can still be ringed and reported.
(defun bp:collect-points (/ ss i en ed typ p nm out)
  (setq out nil
        ss  (ssget "_X" '((0 . "INSERT,POINT"))))
  (if ss
    (progn
      (setq i 0)
      (repeat (sslength ss)
        (setq en  (ssname ss i)
              ed  (entget en)
              typ (cdr (assoc 0 ed))
              p   (cdr (assoc 10 ed)))
        (cond
          ((= typ "INSERT")
           (if (or (= (strcase (cdr (assoc 2 ed)))
                      (strcase *BP-POINT-BLOCK*))
                   (= (strcase (cdr (assoc 8 ed)))
                      (strcase *BP-POINT-LAYER*)))
             (progn
               (setq nm (cal:block-number en *BP-PT-TAG*))
               (setq out (cons (cons (list (car p) (cadr p))
                                     (if (and nm (/= nm "")) nm "?"))
                               out)))))
          ((= typ "POINT")
           (if (= (strcase (cdr (assoc 8 ed)))
                  (strcase *BP-POINT-LAYER*))
             (setq out (cons (cons (list (car p) (cadr p)) "?") out)))))
        (setq i (1+ i)))))
  out)

;; The survey point nearest to pick PK, when one sits within *BP-SNAP*
;; of it; nil otherwise.  Returns the ((x y) . name) pair.
(defun bp:nearest-point (pk cands / best bd c d)
  (setq best nil bd nil)
  (foreach c cands
    (setq d (bp:dist pk (car c)))
    (if (and (<= d *BP-SNAP*) (or (null bd) (< d bd)))
      (setq best c bd d)))
  best)

;; The picked-list entry a new click lands on, when it lands on one:
;; either its snapped centre CTR is (as good as) an already-ringed
;; spot, or - for a pick with no survey point under it - the raw pick
;; PK is inside an existing ring.  Entries are (ctr name ring-ename);
;; nil when the click is somewhere new.
(defun bp:ringed-at (pk ctr picked / hit bd q d)
  (setq hit nil)
  (foreach q picked
    (if (< (bp:dist ctr (car q)) *BP-EXACT-EPS*) (setq hit q)))
  (if (null hit)
    (progn                              ; nearest ring the pick sits in
      (setq bd nil)
      (foreach q picked
        (setq d (bp:dist pk (car q)))
        (if (and (<= d *BP-RADIUS*) (or (null bd) (< d bd)))
          (setq hit q bd d)))))
  hit)

;; Remove the entry whose ring is ENT from LST, keeping the order.
(defun bp:drop-entry (ent lst / out q)
  (foreach q lst (if (not (eq (caddr q) ent)) (setq out (cons q out))))
  (reverse out))

;; The callout sentence: "Pt.12 is bad", "Pt.12 and Pt.15 are bad",
;; "Pt.12, Pt.15 and Pt.20 are bad" - commas between all but the last
;; pair, "and" before the last, is/are by count.
(defun bp:phrase (names / n s i)
  (setq n (length names))
  (cond
    ((= n 0) "")
    ((= n 1) (strcat "Pt." (car names) " is bad"))
    (T
     (setq s (strcat "Pt." (car names)) i 1)
     (while (< i (1- n))
       (setq s (strcat s ", Pt." (nth i names))
             i (1+ i)))
     (strcat s " and Pt." (nth (1- n) names) " are bad"))))

;; Ring one bad point.
(defun bp:draw-ring (ctr)
  (entmakex (list '(0 . "CIRCLE") '(100 . "AcDbEntity")
                  (cons 8 *BP-LAYER*) '(100 . "AcDbCircle")
                  (cons 10 (list (car ctr) (cadr ctr) 0.0))
                  (cons 40 *BP-RADIUS*))))

;; Write the callout text at P.
(defun bp:draw-text (p str)
  (entmakex (list '(0 . "TEXT") '(100 . "AcDbEntity")
                  (cons 8 *BP-LAYER*) '(100 . "AcDbText")
                  (cons 10 (list (car p) (cadr p) 0.0))
                  (cons 40 *BP-TEXT-HGT*)
                  (cons 1 str))))

;; ---- command -------------------------------------------------------
;; NOTE: no local here may be named after a function this routine
;; calls - an AutoLISP local SHADOWS the function of the same name for
;; the whole call, so a local called "last" turns every (last ...) in
;; the body into "no function definition: LAST" at runtime.
(defun c:BPCALLOUT (/ *error* undo-open cands pk hit ctr nm old picked names
                      txtpt phrase lastpt)
  ;; the rings and the callout are one undo group, so a run backed out
  ;; halfway takes one U rather than one per circle; the group is only
  ;; closed if it was opened (STANDARDS section 5)
  (defun *error* (msg)
    (if undo-open (command "_.UNDO" "_End"))
    (setq undo-open nil)
    (if (and msg (not (wcmatch (strcase msg) "*BREAK*,*CANCEL*,*QUIT*,*EXIT*")))
      (princ (strcat "\nBPCALLOUT error: " msg)))
    (princ))
  (command "_.UNDO" "_Begin")
  (setq undo-open T)

  (princ (strcat "\nBPCALLOUT " *bpcallout-version*))
  (setq cands (bp:collect-points))
  (if cands
    (princ (strcat "\n" (itoa (length cands)) " survey point(s) found;"
                   " a click within " (rtos *BP-SNAP* 4 0)
                   " snaps to the nearest one."))
    (princ (strcat "\nNo survey points found in the drawing - clicks"
                   " will be ringed where picked and named \"?\".")))

  (setq picked nil)
  (while (setq pk (getpoint
                    "\nClick a bad point (a ringed one un-rings it, Enter when done): "))
    (setq hit (bp:nearest-point pk cands))
    (if hit
      (setq ctr (car hit) nm (cdr hit))
      (setq ctr (list (car pk) (cadr pk)) nm "?"))
    (setq old (bp:ringed-at pk ctr picked))
    (if old
      (progn                            ; reselecting a point undoes it
        (if (and (caddr old) (entget (caddr old)))
          (entdel (caddr old)))
        (setq picked (bp:drop-entry (caddr old) picked))
        (princ (strcat "\n  Pt." (cadr old) " un-ringed.")))
      (progn
        (cal:ensure-layer *BP-LAYER* 1)
        (setq picked (cons (list ctr nm (bp:draw-ring ctr)) picked))
        (if hit
          (princ (strcat "\n  Pt." nm " ringed."))
          (princ (strcat "\n  No survey point within "
                         (rtos *BP-SNAP* 4 0)
                         " of the pick - ringed where clicked, as"
                         " Pt.?."))))))

  (if (null picked)
    (princ "\nBPCALLOUT: nothing picked - nothing drawn.")
    (progn
      (setq picked (reverse picked)             ; back to click order
            names  (mapcar 'cadr picked)
            phrase (bp:phrase names)
            lastpt (car (last picked)))
      (setq txtpt (getpoint (strcat "\nPlace the callout text <beside"
                                    " the last ring>: ")))
      (if (null txtpt)                          ; Enter: tuck it beside
        (setq txtpt (list (+ (car lastpt) (* 2.0 *BP-RADIUS*))
                          (- (cadr lastpt) (* 2.0 *BP-RADIUS*)))))
      (bp:draw-text txtpt phrase)
      (princ (strcat "\nBPCALLOUT: " (itoa (length picked))
                     " point(s) ringed on layer " *BP-LAYER*
                     ";  \"" phrase "\""))))
  (if undo-open (command "_.UNDO" "_End"))
  (setq undo-open nil)
  (princ))

(princ (strcat "\nBPCALLOUT " *bpcallout-version*
               " loaded. Command: BPCALLOUT (ring bad points and write"
               " the callout)."))
(princ)


;;; ======================================================================
;;; >>> ccprecheck.lsp
;;; ======================================================================

;;; ===================================================================
;;; CCPRECHECK.LSP - Tech drawing checklist walker
;;;
;;; Interactive AutoLISP routine that walks the "Tech Flow Chart"
;;; decision tree for pool/spa products.  Load with APPLOAD (or
;;; (load "ccprecheck.lsp")) and run the CCPRECHECK command.  The routine asks
;;; the user to answer / confirm each item along the flowchart until
;;; every branch it enters reaches its end, then prints a summary of
;;; every note and confirmation that was collected on the way.
;;;
;;; Every question after the first also offers Back (Undo is accepted
;;; as a hidden synonym), which re-asks the previous question and drops
;;; what it logged - including backing OUT of a sub-branch into the
;;; question that opened it, and changing an answer re-routes the walk.
;;; At the typed Confirm prompts Back is typed like a note: B, BACK, U
;;; or UNDO alone, any case.
;;;
;;; Flow (top level):
;;;   Product Type
;;;     +- Liner      -> Pool | Spa
;;;     +- Pool Cover -> Freeform | Rectangle
;;;     +- Spa Cover  -> Safety Cover | Hard Cover | ThermoLight Cover
;;; ===================================================================

;;; ------------------------------------------------------------------
;;; Helpers
;;; ------------------------------------------------------------------

;;; SHARED BUILD: requires CALOFIN-LIB.lsp (load via CALOFIN-LOADER.lsp).
;;; Generic helpers live there under cal: - see STANDARDS.md.
;;;

(setq *ccprecheck-version* "v1.1")   ; announced on load; release_lisp.py
                                        ; stamps the dated twin in releases/

(setq *chk:log* nil)   ; collected checklist lines for the summary

;; Record a line for the final summary.
(defun chk:log (msg)
  (setq *chk:log* (append *chk:log* (list msg)))
  msg
)

;; Keep only the first N summary lines - the rollback when a Back
;; drops what a question and its branch logged.
(defun chk:trim (n / out i)
  (setq out nil i 0)
  (foreach l *chk:log*
    (if (< i n) (setq out (cons l out)))
    (setq i (1+ i))
  )
  (setq *chk:log* (reverse out))
)

;; Print an instruction/note to the command line and log it.
(defun chk:note (msg)
  (princ (strcat "\n  >> " msg))
  (chk:log (strcat "NOTE: " msg))
  msg
)

;; Ask the user to pick one keyword out of a list.
;; kwlist  - initget-style keyword string, e.g. "Yes No"
;; prompt  - question text (keywords appended automatically)
;; back    - non-nil: also offer Back (Undo accepted too), returning
;;           the symbol CHK-BACK
;; Returns the chosen keyword string (loops until a choice is made).
(defun chk:ask (prompt kwlist back / ans)
  (while (not ans)
    (initget 1 (if back (strcat kwlist " Back Undo") kwlist))
    (setq ans (getkword (strcat "\n" prompt " ["
                                (vl-string-translate " " "/" kwlist)
                                (if back "/Back" "") "]: ")))
  )
  (if (member ans '("Back" "Undo"))
    'CHK-BACK
    (progn (chk:log (strcat prompt " -> " ans)) ans)
  )
)

;; Yes/No convenience wrapper.  Returns T for Yes, nil for No, or the
;; symbol CHK-BACK.
(defun chk:yesno (prompt back / v)
  (setq v (chk:ask prompt "Yes No" back))
  (if (eq v 'CHK-BACK) v (= v "Yes"))
)

;; Ask the user to confirm an item; optionally record a typed-in value.
;; With back non-nil, B (Back) returns the symbol CHK-BACK instead.
(defun chk:confirm (item back / val)
  (setq val (getstring T (strcat "\nConfirm " item
                                 " (type value/notes"
                                 (if back ", B = back" "")
                                 " or press Enter): ")))
  (cond
    ((and back (cal:back-word-p val)) 'CHK-BACK)
    ((= val "") (chk:log (strcat "CONFIRMED: " item)) val)
    (T (chk:log (strcat "CONFIRMED: " item " = " val)) val)
  )
)

;; Run a flowchart node as a list of stages with Back between them.
;; Each stage is (test-expr . fn): a stage whose test evaluates nil is
;; skipped, and tests are re-evaluated on every pass, so backing up and
;; changing an answer re-routes the branch.  A stage returning CHK-BACK
;; rewinds to the previous asked stage, dropping everything logged
;; since just before it.  Backing out of the FIRST asked stage returns
;; CHK-BACK to the caller when bk is non-nil (the parent then re-asks
;; the question that opened this branch); with bk nil it re-asks.
(defun chk:seq (fns bk / i n v it asked mark out)
  (setq i 0 n (length fns) asked nil out nil)
  (while (and (< i n) (not out))
    (setq it (nth i fns))
    (if (and (car it) (not (eval (car it))))
      (setq i (1+ i))                       ; branch not taken - skip
      (progn
        (setq mark (length *chk:log*)
              v    (apply (cdr it) nil))
        (cond
          ((eq v 'CHK-BACK)
           (chk:trim mark)                  ; drop the aborted stage's log
           (if asked
             (progn
               (setq i (caar asked))
               (chk:trim (cdar asked))
               (setq asked (cdr asked))
             )
             (if bk
               (setq out T)                 ; backed out of this branch
               (princ "\n  Already at the first question.")
             )
           ))
          (T
           (setq asked (cons (cons i mark) asked)
                 i     (1+ i))
          )
        )
      )
    )
  )
  (if out 'CHK-BACK nil)
)

;;; ------------------------------------------------------------------
;;; Liner branch
;;; ------------------------------------------------------------------

;; Steps? sub-flow (shared by Liner->Pool and Liner->Spa)
(defun chk:steps (/ st kind v)
  (chk:seq
    (list
      (cons nil '(lambda ()
        (setq v (chk:yesno "Steps?" T))
        (if (not (eq v 'CHK-BACK))
          (progn
            (setq st v)
            (if (not st) (chk:note "No need to show any step info"))
          )
        )
        v))
      (cons 'st '(lambda ()
        (setq v (chk:ask "Step type" "Fiberglass VinylOver" T))
        (if (= v "VinylOver") (chk:note "Show Step Attachment & Risers"))
        (if (not (eq v 'CHK-BACK)) (setq kind v))
        v))
      (cons '(and st (= kind "Fiberglass")) '(lambda ()
        (setq v (chk:confirm "the step face is either straight or radius" T))
        (if (not (eq v 'CHK-BACK))
          (chk:note "Show the location of the step always")
        )
        v))
      (cons '(and st (= kind "Fiberglass")) '(lambda ()
        (chk:confirm "the size of the step (especially for radius steps)" T)))
      (cons '(and st (= kind "VinylOver")) '(lambda ()
        (chk:confirm "sum of Step Risers equals Wall Height" T)))
      (cons '(and st (= kind "VinylOver")) '(lambda ()
        (chk:confirm "Step Back Corners" T)))
    )
    T
  )
)

(defun chk:liner-pool ()
  (chk:seq
    (list
      (cons nil '(lambda () (chk:confirm "Liner Pattern" T)))
      (cons nil '(lambda () (chk:confirm "Pool Corners" T)))
      (cons nil '(lambda () (chk:confirm "Depth / Wall Height" T)))
      (cons nil '(lambda () (chk:steps)))
    )
    T
  )
)

(defun chk:liner-spa (/ spill v)
  (chk:seq
    (list
      (cons nil '(lambda () (chk:confirm "Liner Pattern" T)))
      (cons nil '(lambda () (chk:confirm "the corners" T)))
      (cons nil '(lambda () (chk:confirm "Depth / Wall Height" T)))
      (cons nil '(lambda ()
        (setq v (chk:yesno "Spillway?" T))
        (if (not (eq v 'CHK-BACK))
          (progn
            (setq spill v)
            (if spill
              (chk:note "Show Spillway Detail confirming Bead location")
              (chk:note "Show nothing for the spillway")
            )
          )
        )
        v))
      (cons 'spill '(lambda ()
        (chk:confirm "Spillway Dimensions and location" T)))
      (cons nil '(lambda () (chk:steps)))
    )
    T
  )
)

(defun chk:liner (/ lfor v)
  (chk:seq
    (list
      (cons nil '(lambda ()
        (setq v (chk:ask "Liner for" "Pool Spa" T))
        (if (not (eq v 'CHK-BACK)) (setq lfor v))
        v))
      (cons nil '(lambda ()
        (if (= lfor "Pool") (chk:liner-pool) (chk:liner-spa))))
    )
    T
  )
)

;;; ------------------------------------------------------------------
;;; Pool Cover branch
;;; ------------------------------------------------------------------

;; Obstruction sub-flow (also referenced from Spa Cover -> Safety Cover)
(defun chk:obstruction (/ prox sec big v)
  (chk:seq
    (list
      (cons nil '(lambda ()
        (setq v (chk:ask
          "Proximity to water's edge"
          "MoreThan3ft OverlapTo3ft ZeroToOverlap InsidePerimeter" T))
        (if (not (eq v 'CHK-BACK))
          (progn
            (setq prox v)
            (cond
              ((= prox "MoreThan3ft") (chk:note "Treatment not necessary"))
              ((= prox "OverlapTo3ft") (chk:note "Avoid strap"))
              ((= prox "ZeroToOverlap")
               ;; 0" meaning the obstruction defines the pool perimeter
               (chk:note "0\" means the obstruction defines the pool perimeter"))
            )
          )
        )
        v))
      (cons '(= prox "ZeroToOverlap") '(lambda ()
        (setq v (chk:yesno "Can the cover be secured to the obstruction?" T))
        (if (not (eq v 'CHK-BACK))
          (progn
            (setq sec v)
            (if sec (chk:note "Most of the time Cable, unless stated otherwise"))
          )
        )
        v))
      (cons '(and (= prox "ZeroToOverlap") (not sec)) '(lambda ()
        (setq v (chk:yesno "Is the obstruction larger than 36\"?" T))
        (if (not (eq v 'CHK-BACK))
          (progn
            (setq big v)
            (if (not big)
              (chk:note (strcat "CutOut if it is a viable solution - "
                                "if not, then reduced overlap and/or shortened springs"))
            )
          )
        )
        v))
      (cons '(and (= prox "ZeroToOverlap") (not sec) big) '(lambda ()
        (setq v (chk:yesno "Able to go over the obstruction?" T))
        (if (not (eq v 'CHK-BACK))
          (if v
            (progn
              (chk:note "Up and Over")
              (chk:note "3x3 padding over obstacle & step riser where necessary")
            )
            (chk:note "Reduced overlap and/or shortened springs")
          )
        )
        v))
      (cons '(= prox "InsidePerimeter") '(lambda ()
        ;; obstruction resides completely inside pool perimeter
        (setq v (chk:yesno "Able to go over the obstruction?" T))
        (if (not (eq v 'CHK-BACK))
          (if v
            (progn
              (chk:note "Up and Over")
              (chk:note "3x3 padding over obstacle")
            )
            (chk:note "Boot CutOut")
          )
        )
        v))
    )
    T
  )
)

(defun chk:decking (/ mat raised canedge v)
  (chk:seq
    (list
      (cons nil '(lambda ()
        (setq v (chk:ask "Decking material" "Concrete Paver Grass Wood" T))
        (if (not (eq v 'CHK-BACK))
          (progn
            (setq mat v)
            (cond
              ((= mat "Concrete") (chk:note "Standard Anchors / Tubes"))
              ((= mat "Paver")    (chk:note "9\" Tubes / 15\" Tubes"))
              ;; grass / planter / rocks
              ((= mat "Grass")    (chk:note "Tubes / Lawn Stakes / 2x2 Stakes"))
              (T                  (chk:note "Wood Deck Anchors"))
            )
          )
        )
        v))
      (cons '(= mat "Wood") '(lambda ()
        (setq v (chk:yesno "Is the decking raised?" T))
        (if (not (eq v 'CHK-BACK))
          (progn
            (setq raised v)
            (if (not raised) (chk:note "Wood Deck Anchors"))
          )
        )
        v))
      (cons '(and (= mat "Wood") raised) '(lambda ()
        (setq v (chk:yesno "Are you able to secure the cover to the edge of the deck?" T))
        (if (not (eq v 'CHK-BACK))
          (progn
            (setq canedge v)
            (if canedge
              (chk:note "On Ground Bracket Clamps / Wood Deck Anchors")
              (chk:note "Wood Deck Anchors")
            )
          )
        )
        v))
      (cons '(and (= mat "Wood") raised (not canedge)) '(lambda ()
        (setq v (chk:ask "Strap type" "ExtendedStraps ExtensionStraps" T))
        (if (not (eq v 'CHK-BACK))
          (if (= v "ExtendedStraps")
            (chk:note "Extended Straps: attached to the pool cover, can be any length")
            (progn
              (chk:note "Extension Straps: connect to the straps on the cover")
              (chk:note "Extension Straps come in 2'-0\", 4'-0\" and 6'-0\"")
            )
          )
        )
        v))
      ;; Deck space and springs
      (cons nil '(lambda ()
        (setq v (chk:ask "Deck space (for springs)"
                         "GreaterThan18in 9to18in 6to9in LessThan4in" T))
        (if (not (eq v 'CHK-BACK))
          (cond
            ((= v "GreaterThan18in") (chk:note "Standard Springs"))
            ((= v "9to18in")         (chk:note "Short Springs"))
            ((= v "6to9in")          (chk:note "Special Deck Mount"))
            (T                       (chk:note "D-Ring"))
          )
        )
        v))
    )
    T
  )
)

(defun chk:pool-cover (/ obst v)
  (chk:seq
    (list
      (cons nil '(lambda ()
        (setq v (chk:ask "Pool shape" "Freeform Rectangle" T))
        (if (not (eq v 'CHK-BACK))
          (if (= v "Freeform")
            (chk:note "18\" overlap, 3x3 spacing unless stated otherwise")
            (chk:note "12\" overlap, 5x5 spacing unless stated otherwise")
          )
        )
        v))
      (cons nil '(lambda ()
        (setq v (chk:confirm "Overlap and Spacing" T))
        (if (not (eq v 'CHK-BACK)) (chk:note "Pad sharp corners"))
        v))
      (cons nil '(lambda ()
        (setq v (chk:yesno "Are there obstacles?" T))
        (if (not (eq v 'CHK-BACK))
          (progn
            (setq obst v)
            (if obst (chk:note "Treat obstacles accordingly"))
          )
        )
        v))
      (cons 'obst '(lambda () (chk:obstruction)))
      (cons nil '(lambda () (chk:decking)))
    )
    T
  )
)

;;; ------------------------------------------------------------------
;;; Spa Cover branch
;;; ------------------------------------------------------------------

(defun chk:spa-safety (/ obst raised attach v)
  (chk:seq
    (list
      (cons nil '(lambda ()
        (setq v (chk:yesno "Spillway?" T))
        (if (and (not (eq v 'CHK-BACK)) v)
          (chk:note "Pad & dimension the spillway")
        )
        v))
      (cons nil '(lambda ()
        (setq v (chk:yesno "Obstructions?" T))
        (if (not (eq v 'CHK-BACK))
          (progn
            (setq obst v)
            (if obst
              (chk:note "See obstruction flow in Pool Covers")
              (chk:note "No obstructions - do nothing")
            )
          )
        )
        v))
      (cons 'obst '(lambda () (chk:obstruction)))
      (cons nil '(lambda ()
        (setq v (chk:yesno "Raised?" T))
        (if (not (eq v 'CHK-BACK)) (setq raised v))
        v))
      (cons 'raised '(lambda ()
        (chk:confirm "the height of the spa (state it on the drawing)" T)))
      (cons 'raised '(lambda ()
        (setq v (chk:yesno "Attaching to pool cover?" T))
        (if (not (eq v 'CHK-BACK))
          (progn
            (setq attach v)
            (if attach (chk:note "Note: loose clips will attach to the pool cover"))
          )
        )
        v))
      (cons '(and raised (not attach)) '(lambda ()
        (setq v (chk:yesno "Drum style cover?" T))
        (if (not (eq v 'CHK-BACK))
          (if v
            (chk:note "Add drum style note")
            (chk:note "Spa might need extension straps")
          )
        )
        v))
      (cons '(not raised) '(lambda ()
        (setq v (chk:yesno "Joined wall for spa and pool?" T))
        (if (and (not (eq v 'CHK-BACK)) v) (chk:note "Pad the wall"))
        v))
    )
    T
  )
)

;; Hard cover spillway sub-flow
(defun chk:spa-hard-spillway (/ v)
  (setq v (chk:yesno "Spillway?" T))
  (cond
    ((eq v 'CHK-BACK) v)
    (v
     (chk:note "Go through gap filler and custom block rules to determine")
     (chk:note "Draw the Gap Filler / Custom Block on the spa cover on the cover layer")
     (chk:note "Make sure the inside and outside spillway dims are shown")
     (chk:note (strcat "Make sure the spillway is shown on the bottom or right hand "
                       "side; dimensions and notes go on the dimension itself"))
     (chk:note (strcat "If using a custom block, draw a 3D custom block detail off "
                       "to the side dimensioning the custom block showing LxWxH"))
     v)
    (T (chk:note "No need to show anything for the spillway") v)
  )
)

(defun chk:spa-hard (/ v)
  (chk:seq
    (list
      (cons nil '(lambda ()
        (setq v (chk:ask "Spa type" "AboveGround InGround" T))
        (if (= v "InGround")
          (progn
            (chk:note "Heavy Duty Bottom / Hold Down Kit")
            (chk:note "6\" overlap might be required")
            (chk:note "Show overlap dimension")
            (chk:note "Show water's edge / overlap if given")
          )
        )
        v))
      (cons nil '(lambda () (chk:confirm "pieces are no more than 48\"" T)))
      (cons nil '(lambda () (chk:confirm "Hinges" T)))
      (cons nil '(lambda () (chk:confirm "Spa Cover Size" T)))
      (cons nil '(lambda () (chk:spa-hard-spillway)))
    )
    T
  )
)

(defun chk:spa-thermolight (/ v)
  (setq v (chk:confirm "Cover Size is for water's edge" T))
  (if (not (eq v 'CHK-BACK))
    (progn
      (chk:note "All Velcro hinges - pieces can be up to 53\" but are typically at most 48\"")
      (chk:note "No need to worry about spillways")
      (chk:note "Cover size dimensions should be shown")
    )
  )
  v
)

(defun chk:spa-cover (/ kind v)
  (chk:seq
    (list
      (cons nil '(lambda ()
        (setq v (chk:ask "Spa cover type" "SafetyCover HardCover ThermoLight" T))
        (if (not (eq v 'CHK-BACK)) (setq kind v))
        v))
      (cons nil '(lambda ()
        (cond
          ((= kind "SafetyCover") (chk:spa-safety))
          ((= kind "HardCover")   (chk:spa-hard))
          (T                      (chk:spa-thermolight))
        )))
    )
    T
  )
)

;;; ------------------------------------------------------------------
;;; Main command
;;; ------------------------------------------------------------------

(defun c:CCPRECHECK (/ *error* product v)
  ;; a walker: it changes no setting and opens no undo group, so the
  ;; handler's whole job is to keep a cancel from printing a raw
  ;; AutoLISP message at the user (STANDARDS section 5)
  (defun *error* (msg)
    (if (and msg (not (wcmatch (strcase msg)
                               "*BREAK*,*CANCEL*,*QUIT*,*EXIT*")))
        (princ (strcat "\nCCPRECHECK error: " msg)))
    (princ))

  (setq *chk:log* nil product nil)
  (princ "\n--- Tech Flow Chart checklist ---")
  (princ "\n(after the first question, Back re-asks the previous one)")
  (chk:seq
    (list
      (cons nil '(lambda ()
        (setq v (chk:ask "Product type" "Liner PoolCover SpaCover" nil))
        (setq product v)
        v))
      (cons nil '(lambda ()
        (cond
          ((= product "Liner")     (chk:liner))
          ((= product "PoolCover") (chk:pool-cover))
          (T                       (chk:spa-cover))
        )))
    )
    nil
  )
  ;; Summary of everything answered / noted along the way
  (princ "\n\n--- Checklist summary ---")
  (foreach line *chk:log*
    (princ (strcat "\n  " line))
  )
  (princ "\n--- End of checklist ---\n")
  (princ)
)

(princ "\nCCPRECHECK.LSP loaded. Type CCPRECHECK to run the tech flow chart checklist.")
(princ)


;;; ======================================================================
;;; >>> CDCALLOUT.lsp
;;; ======================================================================

;;; ===================================================================
;;; CDCALLOUT.lsp  --  cross-dimension from Pt.## to Pt.## by number
;;; -------------------------------------------------------------------
;;; For AutoCAD 2018 and later (plain AutoLISP; needs the Visual LISP
;;; engine that ships with full AutoCAD -- LT cannot run this).
;;;
;;; Command:  CDCALLOUT
;;;
;;; SHARED BUILD: requires CALOFIN-LIB.lsp (load via CALOFIN-LOADER.lsp).
;;; Generic helpers live there under cal: - see STANDARDS.md.
;;;
;;; The dimensioning sister of BPCALLOUT.  Instead of clicking points,
;;; you name them: type the FROM point number and the TO point number,
;;; and an aligned dimension is drawn between those two survey points
;;; -- the dimension line sitting right inbetween, on the tie itself,
;;; exactly where CDCREATE puts its (nudge cdo:*offset* to push it
;;; off) -- in the "CROSS DIMENSIONS" dimension style, on the
;;; "DIMENSION" layer, ByLayer, the same convention CDCREATE and POOL
;;; use.  Rinse and repeat: it keeps asking for the next FROM number
;;; until you press Enter.  Nothing is ever clicked.
;;;
;;; Point numbers are typed the way they read in the drawing: "35",
;;; "Pt.35", "pt 35", "#35" and "035" all name the same point -- the
;;; number is matched against the "number" attribute on the survey
;;; point blocks (the same classifier BPCALLOUT and LHD use: an
;;; "ab_pt" INSERT on any layer, any other INSERT on the POINTS
;;; layer, or a plain POINT on the POINTS layer).
;;;
;;; A number that names no point in the drawing is reported and the
;;; prompt re-asks -- nothing is drawn from a typo.  Enter at the TO
;;; prompt cancels just that round.  The whole run is one undo group:
;;; a single U takes every dimension away.
;;;
;;; Going back a step follows the shared Back convention (see the root
;;; README): B/BACK/U/UNDO at the TO prompt re-asks FROM, and Back at
;;; the FROM prompt (offered once something is drawn) un-draws the
;;; last dimension.
;;;
;;; A missing "CROSS DIMENSIONS" style is NOT invented: the dims are
;;; drawn in whatever style is current and the routine says so, so a
;;; drawing started from the wrong template is obvious instead of
;;; silently producing wrong-looking dims (CDCREATE's rule, kept).
;;;
;;; Versioning: see tools/release_lisp.py at the repo root.  It reads
;;; *cdcallout-version* below and stamps a dated, REV-numbered twin of
;;; this file into releases/.
;;; ===================================================================

;; ---- configuration -------------------------------------------------
(setq *cdcallout-version* "v1.3")   ; announced on load; release_lisp.py
                                    ; reads this banner and stamps the
                                    ; dated twin in releases/ from it
(setq cdo:*style*       "CROSS DIMENSIONS") ; dimension style to use
(setq cdo:*layer*       "DIMENSION")        ; layer the dims land on
(setq cdo:*offset*      0.0)        ; distance the dimension line is
                                    ; pushed off the tie it measures,
                                    ; drawing units (0.0 = right
                                    ; inbetween, on the tie itself --
                                    ; CDCREATE's convention)
(setq *CDO-POINT-BLOCK* "ab_pt")    ; block name whose INSERTs mark
                                    ; points wherever they sit
(setq *CDO-POINT-LAYER* "POINTS")   ; layer whose POINTs/INSERTs are
                                    ; always points
(setq *CDO-PT-TAG*      "number")   ; attribute tag on the point block
                                    ; naming the point, as in "Pt.17"

;; ---- point lookup --------------------------------------------------

;; Every NAMED survey point in the drawing, as ((x y z) . name) pairs.
;; What counts as a point matches BPCALLOUT/LHD; a point whose number
;; cannot be read is left out -- it cannot be asked for by name.
(defun cdo:collect-points (/ ss i en ed typ p nm out)
  (setq out nil
        ss  (ssget "_X" '((0 . "INSERT"))))
  (if ss
    (progn
      (setq i 0)
      (repeat (sslength ss)
        (setq en (ssname ss i)
              ed (entget en)
              p  (cdr (assoc 10 ed)))
        (if (or (= (strcase (cdr (assoc 2 ed)))
                   (strcase *CDO-POINT-BLOCK*))
                (= (strcase (cdr (assoc 8 ed)))
                   (strcase *CDO-POINT-LAYER*)))
          (progn
            (setq nm (cal:block-number en *CDO-PT-TAG*))
            (if (and nm (/= nm ""))
              (setq out (cons (cons (list (car p) (cadr p) 0.0) nm)
                              out)))))
        (setq i (1+ i)))))
  (reverse out))

;; One comparable form for a point number, so "35", "Pt.35", "pt 35",
;; "#35" and "035" all meet in the middle: uppercase, spaces and
;; hashes dropped, a leading "PT" / "PT." dropped, and a value that
;; reads as a number rendered numerically (so leading zeros don't
;; matter).  Only the dot right after PT is a prefix dot - a point
;; genuinely named "40.5" keeps its decimal.
(defun cdo:canon (s / out i ch)
  (setq s (strcase s) out "" i 1)
  (while (<= i (strlen s))
    (setq ch (substr s i 1))
    (if (not (member ch '(" " "#")))
      (setq out (strcat out ch)))
    (setq i (1+ i)))
  (if (and (>= (strlen out) 2) (= (substr out 1 2) "PT"))
    (progn
      (setq out (substr out 3))
      (if (= (substr out 1 1) ".") (setq out (substr out 2)))))
  (if (distof out 2)
    (rtos (distof out 2) 2 8)
    out))

;; The survey point the typed number names, or nil.  The first match
;; wins when a drawing carries the same number twice.
(defun cdo:find-point (s cands / want found c)
  (setq want (cdo:canon s) found nil)
  (foreach c cands
    (if (and (null found) (= (cdo:canon (cdr c)) want))
      (setq found c)))
  found)

;; ---- dimension helpers (CDCREATE's conventions, kept) --------------

;; midpoint of p1->p2, pushed perpendicular to the tie by dist
;; (dist 0.0 puts the dimension line straight inbetween, on the tie)
(defun cdo:loc (p1 p2 dist / dx dy d m)
  (setq m (list (* 0.5 (+ (car  p1) (car  p2)))
                (* 0.5 (+ (cadr p1) (cadr p2)))
                (* 0.5 (+ (caddr p1) (caddr p2)))))
  (if (equal dist 0.0 1e-12)
    m
    (progn
      (setq dx (- (car  p2) (car  p1))
            dy (- (cadr p2) (cadr p1))
            d  (sqrt (+ (* dx dx) (* dy dy))))
      (if (> d 1e-9)
        (list (+ (car  m) (* dist (/ (- dy) d)))
              (+ (cadr m) (* dist (/ dx d)))
              (caddr m))
        m))))

;; make a layer current, creating it first when the drawing lacks it
(defun cdo:setlayer (name)
  (if (not (tblsearch "LAYER" name))
    (entmake (list '(0 . "LAYER")
                   '(100 . "AcDbSymbolTableRecord")
                   '(100 . "AcDbLayerTableRecord")
                   (cons 2 name)
                   '(70 . 0)
                   '(62 . 7)
                   '(6 . "Continuous"))))
  (setvar "CLAYER" name))

;; restore a dimension style by name when the drawing has it;
;; returns T when the style was set
(defun cdo:setstyle (name)
  (if (and name (tblsearch "DIMSTYLE" name))
    (progn (command "_.-DIMSTYLE" "_Restore" name) t)))

;; a copy of an entget list with every entry for group CODE dropped
(defun cdo:strip (code lst / out g)
  (foreach g lst (if (/= code (car g)) (setq out (cons g out))))
  (reverse out))

;; force a freshly drawn dimension onto the layer and style CDCALLOUT
;; promises, ByLayer -- DIMLAYER, a style-owned layer or a leftover
;; per-entity override would otherwise have the last word
(defun cdo:fixdim (en havestyle / ed code)
  (if (and en (setq ed (entget en))
           (= "DIMENSION" (cdr (assoc 0 ed))))
    (progn
      (setq ed (if (assoc 8 ed)
                 (subst (cons 8 cdo:*layer*) (assoc 8 ed) ed)
                 (append ed (list (cons 8 cdo:*layer*)))))
      (if havestyle
        (setq ed (if (assoc 3 ed)
                   (subst (cons 3 cdo:*style*) (assoc 3 ed) ed)
                   (append ed (list (cons 3 cdo:*style*))))))
      (foreach code '(62 6 370) (setq ed (cdo:strip code ed)))
      (entmod ed)
      (entupd en)
      t)))

;; ---- the command ---------------------------------------------------
;; NOTE: no local here may be named after a function this routine
;; calls - an AutoLISP local SHADOWS the function of the same name for
;; the whole call (the BPCALLOUT v1.0 lesson).
(defun c:CDCALLOUT (/ *error* olderr oce ocl oos odim grouped havestyle
                      cands s1 s2 a b pre new made d dimlist stage
                      done)

  ;; -- restore drawing state on error / Esc.  A dimension command may
  ;;    still be open, so talk to AutoCAD through command-s -- and close
  ;;    the undo group, or the next U would swallow the user's own work
  (setq olderr *error*)
  (defun *error* (m)
    (if (and odim (not (equal odim (getvar "DIMSTYLE"))))
      (vl-catch-all-apply 'command-s (list "_.-DIMSTYLE" "_Restore" odim)))
    (if ocl (setvar "CLAYER"  ocl))
    (if oos (setvar "OSMODE"  oos))
    (if oce (setvar "CMDECHO" oce))
    (if grouped (vl-catch-all-apply 'command-s (list "_.UNDO" "_End")))
    (setq *error* olderr)
    (if (and m (not (wcmatch (strcase m) "*BREAK*,*CANCEL*,*QUIT*,*EXIT*")))
      (princ (strcat "\n** Error: " m)))
    (princ))

  (vl-load-com)
  (setq oce  (getvar "CMDECHO")
        ocl  (getvar "CLAYER")
        oos  (getvar "OSMODE")
        odim (getvar "DIMSTYLE"))

  (princ (strcat "\nCDCALLOUT " *cdcallout-version*))
  (setq cands (cdo:collect-points))
  (if (null cands)
    (princ "\nNo named survey points found in the drawing -- nothing to dimension between.")
    (progn
      (princ (strcat "\n" (itoa (length cands)) " named survey point(s)"
                     " found.  Type numbers as they read in the"
                     " drawing (\"35\" or \"Pt.35\")."))
      (setvar "CMDECHO" 0)
      (setvar "OSMODE"  0)
      (command "_.UNDO" "_Begin")
      (setq grouped t)
      (cdo:setlayer cdo:*layer*)
      (setq havestyle (cdo:setstyle cdo:*style*))
      (if (not havestyle)
        (princ (strcat "\n** This drawing has no \"" cdo:*style*
                       "\" dimension style -- dims drawn in \""
                       (getvar "DIMSTYLE")
                       "\" instead.  Create the style (or start"
                       " from the standard template) and re-run.")))

      ;; -- the rinse-repeat loop, as two stages so Back can re-ask
      ;;    the previous question: FROM -> TO, per the shared Back
      ;;    convention.  B/BACK/U/UNDO at TO re-asks FROM; Back at
      ;;    FROM (offered once something is drawn) un-draws the last
      ;;    dimension.  The dimension line goes right inbetween the
      ;;    two points -- nothing to pick.
      (setq made 0 dimlist nil stage 1 done nil)
      (while (not done)
        (cond
          ;; -- FROM: the loop head
          ((= stage 1)
           (setq s1 (getstring
                      (if dimlist
                        "\nFrom point number (Enter when done) [Back]: "
                        "\nFrom point number (Enter when done): ")))
           (cond
             ((= s1 "") (setq done t))
             ((cal:back-word-p s1)
              (if dimlist
                (progn
                  (entdel (car dimlist))
                  (setq dimlist (cdr dimlist)
                        made    (1- made))
                  (princ "\nStepping back one dimension."))
                (princ "\nAlready at the first dimension.")))
             ((null (setq a (cdo:find-point s1 cands)))
              (princ (strcat "\n  No point numbered \"" s1
                             "\" in the drawing -- nothing drawn.")))
             (t (setq stage 2))))
          ;; -- TO: a good answer draws the dimension right away
          (t
           (setq s2 (getstring (strcat "\nTo point number (from Pt."
                                       (cdr a) ") [Back]: ")))
           (cond
             ((= s2 "")
              (princ "\n  No second point -- this one skipped.")
              (setq stage 1))
             ((cal:back-word-p s2) (setq stage 1))
             ((null (setq b (cdo:find-point s2 cands)))
              (princ (strcat "\n  No point numbered \"" s2
                             "\" in the drawing -- nothing drawn.")))
             ((< (distance (car a) (car b)) 1e-9)
              (princ (strcat "\n  Pt." (cdr a) " and Pt." (cdr b)
                             " sit on the same spot -- nothing to"
                             " measure.")))
             (t
              (setq pre (entlast))
              (command "_.DIMALIGNED"
                       "_non" (trans (car a) 0 1)
                       "_non" (trans (car b) 0 1)
                       "_non" (trans (cdo:loc (car a) (car b)
                                              cdo:*offset*) 0 1))
              (setq new (entlast))
              (if (and new (not (eq new pre)))
                (progn
                  (cdo:fixdim new havestyle)
                  (setq made    (1+ made)
                        dimlist (cons new dimlist)
                        d       (distance (car a) (car b)))
                  (princ (strcat "\n  Pt." (cdr a) " - Pt." (cdr b)
                                 " dimensioned (" (rtos d 4 4) ")."))))
              (setq stage 1))))))

      ;; -- put the drawing back the way it was
      (if (and odim (not (equal odim (getvar "DIMSTYLE"))))
        (cdo:setstyle odim))
      (setvar "CLAYER"  ocl)
      (setvar "OSMODE"  oos)
      (setvar "CMDECHO" oce)
      (command "_.UNDO" "_End")
      (setq grouped nil)

      (princ (strcat "\nCDCALLOUT: " (itoa made) " cross dimension"
                     (if (= made 1) "" "s") " created on layer "
                     cdo:*layer*
                     (if havestyle
                       (strcat " in style " cdo:*style* ".")
                       " (current style).")))))

  (setq *error* olderr)
  (princ))

(princ (strcat "\nCDCALLOUT " *cdcallout-version*
               " loaded. Command: CDCALLOUT (cross-dimension from"
               " Pt.## to Pt.## by number, style \"" cdo:*style*
               "\", layer \"" cdo:*layer* "\")."))
(princ)


;;; ======================================================================
;;; >>> CDCREATE.lsp
;;; ======================================================================

;;; ===================================================================
;;; CDCREATE.lsp  --  cross dimensions from every highlighted line
;;; -------------------------------------------------------------------
;;; For AutoCAD 2018 and later (plain AutoLISP; needs the Visual LISP
;;; engine that ships with full AutoCAD -- LT cannot run this).
;;;
;;; Commands:  CDCREATE       dimension every highlighted line
;;;            CDCREATEVER    print the loaded version
;;;
;;; SHARED BUILD: requires CALOFIN-LIB.lsp (load via CALOFIN-LOADER.lsp).
;;; Generic helpers live there under cal: - see STANDARDS.md.
;;;
;;;  Turns highlighted lines into cross dimensions in one pass:
;;;
;;;    1. Highlight the lines (or pre-select them before typing the
;;;       command -- a pickfirst selection is used as-is).
;;;    2. Every LINE in the selection gets an aligned dimension along
;;;       it, measuring end to end, with the dimension line sitting on
;;;       the line itself and the text slid along it, about 80% of the
;;;       way toward the right-hand end -- the bottom end on a line
;;;       standing near vertical -- rather than sitting centred.
;;;    3. Each new dimension is put in the "CROSS DIMENSIONS" dimension
;;;       style and on the "DIMENSION" layer, ByLayer, with no
;;;       per-entity colour / linetype / lineweight override -- the
;;;       same convention POOL uses for the cross dims it draws.
;;;    4. A line whose two ends already carry a dimension is left
;;;       alone -- no second dim on top of the first, and the line
;;;       stays put so you can see what was skipped.  Two coincident
;;;       lines in one selection count as the same tie.
;;;    5. The line each dimension was made from is erased, so the tie
;;;       measurement is left as a dimension and nothing else.  Only
;;;       lines that really did get a dimension are erased, and the
;;;       report says how many went and off which layers (they are
;;;       normally POOL or POINTS).  Set cdc:*erase* to nil to keep
;;;       them.
;;;
;;;  The whole run is one undo group: a single U puts the lines back
;;;  and takes the dimensions away.
;;;
;;;  Usage
;;;    Command: CDCREATE
;;;    Command: CDCREATEVER      prints the version
;;;
;;;  Tunables (setq them after loading if a drawing needs different
;;;  names, e.g. in a startup file):
;;;    cdc:*style*   dimension style to use   ("CROSS DIMENSIONS")
;;;    cdc:*layer*   layer to create dims on  ("DIMENSION")
;;;    cdc:*offset*  distance the dimension line is pushed off the
;;;                  line it measures, drawing units (0.0 = on it)
;;;    cdc:*erase*   T to erase each dimensioned line, nil to keep it
;;;    cdc:*skipdimmed*  T to leave a tie that is dimensioned already,
;;;                  nil to dimension it again anyway
;;;    cdc:*dupetol* how close two extension line origins have to be to
;;;                  count as the same point; nil = a sixteenth of an
;;;                  inch in the drawing's own units
;;;    cdc:*textpos* where the text sits along the dimension, 0.0 at the
;;;                  far end, 0.5 centred, 1.0 at the right/bottom end
;;;    cdc:*vertang* how near vertical (degrees) a line has to stand
;;;                  before the text goes to its bottom end instead of
;;;                  its right-hand one
;;;
;;;  Notes
;;;    * Only LINE entities are dimensioned.  Anything else in the
;;;      selection (polylines, arcs, text, blocks, ...) is counted and
;;;      reported, not dimensioned -- explode a polyline first if its
;;;      segments need cross dims.
;;;    * Zero-length lines are skipped; they have nothing to measure.
;;;    * "Dimensioned already" means SOME dimension in model space
;;;      carries those same two extension line origins, either way
;;;      round -- whatever its style, layer, or where its dimension
;;;      line sits.  A dim of the same tie pushed out to one side still
;;;      counts as that tie being dimensioned.
;;;    * The "DIMENSION" layer is created when the drawing lacks it,
;;;      and thawed / unlocked / switched back on when it is there but
;;;      not usable -- a run onto a frozen layer would otherwise look
;;;      like the command did nothing.
;;;      A missing "CROSS DIMENSIONS" style is NOT invented: the dims
;;;      are drawn in whatever style is current and the routine says so,
;;;      so a drawing started from the wrong template is obvious
;;;      instead of silently producing wrong-looking dims.
;;;    * The dimension style, current layer, CMDECHO and OSMODE in
;;;      force before the command are restored afterwards, on a clean
;;;      finish, an error, or Esc.
;;; ===================================================================

(setq *cdcreate-version* "v1.2")   ; announced on load; release_lisp.py
                                   ; reads this banner and stamps the
                                   ; dated twin in releases/ from it

(setq cdc:*style*  "CROSS DIMENSIONS")
(setq cdc:*layer*  "DIMENSION")
(setq cdc:*offset* 0.0)
(setq cdc:*erase*  t)
(setq cdc:*textpos* 0.8)
(setq cdc:*vertang* 15.0)
(setq cdc:*skipdimmed* t)
(setq cdc:*dupetol* nil)           ; nil = 1/16" in the drawing's units

;;; -------------------- helpers ------------------------------------

;; restore a dimension style by name when the drawing has it;
;; returns T when the style was set
(defun cdc:setstyle (name)
  (if (and name (tblsearch "DIMSTYLE" name))
    (progn (command "_.-DIMSTYLE" "_Restore" name) t)))

;; DIMSTYLE is read-only to setvar, so it goes back through a command --
;; and only when the style really did move: a run that never found
;; "CROSS DIMENSIONS" should not leave a pointless -DIMSTYLE Restore in
;; the drawing's command history.  command-s, so the same call is legal
;; from inside the error handler.
(defun cdc:restyle (odim)
  (if (and odim (tblsearch "DIMSTYLE" odim)
           (not (equal odim (getvar "DIMSTYLE"))))
    (vl-catch-all-apply 'command-s
                        (list "_.-DIMSTYLE" "_Restore" odim))))

;; the two endpoints of a LINE, in WCS (the entity's own OCS may be
;; tilted, so go through the entity coordinate system)
(defun cdc:ends (en / ed)
  (setq ed (entget en))
  (list (trans (cdr (assoc 10 ed)) en 0)
        (trans (cdr (assoc 11 ed)) en 0)))

;; the point f of the way from p1 to p2 (f 0.5 = midpoint), pushed
;; perpendicular to the line by dist -- dist 0.0 leaves it on the line.
;; Everything CDCREATE places sits on this one line, so the dimension
;; line and its text can never drift onto opposite sides of it.
(defun cdc:loc (p1 p2 f dist / dx dy d b)
  (setq dx (- (car  p2) (car  p1))
        dy (- (cadr p2) (cadr p1))
        b  (list (+ (car   p1) (* f dx))
                 (+ (cadr  p1) (* f dy))
                 (+ (caddr p1) (* f (- (caddr p2) (caddr p1))))))
  (if (equal dist 0.0 1e-12)
    b
    (progn
      (setq d (sqrt (+ (* dx dx) (* dy dy))))
      (if (> d 1e-9)
        (list (+ (car  b) (* dist (/ (- dy) d)))
              (+ (cadr b) (* dist (/ dx d)))
              (caddr b))
        b))))

(defun cdc:d2r (a) (* pi (/ a 180.0)))

;; T when the text belongs at the p2 end rather than the p1 end: the
;; right-hand end, or -- for a line standing within cdc:*vertang* of
;; vertical, where "right-hand" is a coin toss a hair of drafting noise
;; could flip -- the bottom end
(defun cdc:top2 (p1 p2 / dx dy a)
  (setq dx (abs (- (car  p2) (car  p1)))
        dy (abs (- (cadr p2) (cadr p1)))
        a  (cdc:d2r cdc:*vertang*))
  (if (<= (* dx (cos a)) (* dy (sin a)))
    (< (cadr p2) (cadr p1))               ; standing up: the lower end
    (> (car  p2) (car  p1))))             ; lying over: the right end

;; cdc:*textpos* measured from the far end toward the end the text
;; belongs at, expressed as a fraction of p1->p2 so it can go straight
;; into cdc:loc whichever way round the line was drawn
(defun cdc:textfrac (p1 p2)
  (if (cdc:top2 p1 p2) cdc:*textpos* (- 1.0 cdc:*textpos*)))

;; a copy of an entget list with every entry for group CODE dropped
(defun cdc:strip (code lst / out)
  (foreach g lst (if (/= code (car g)) (setq out (cons g out))))
  (reverse out))

;; force a freshly drawn dimension onto the layer and style CDCREATE
;; promises, ByLayer -- DIMLAYER, a style-owned layer or a leftover
;; per-entity override would otherwise have the last word
(defun cdc:fixdim (en havestyle / ed)
  (if (and en (setq ed (entget en))
           (= "DIMENSION" (cdr (assoc 0 ed))))
    (progn
      (setq ed (if (assoc 8 ed)
                 (subst (cons 8 cdc:*layer*) (assoc 8 ed) ed)
                 (append ed (list (cons 8 cdc:*layer*)))))
      (if havestyle
        (setq ed (if (assoc 3 ed)
                   (subst (cons 3 cdc:*style*) (assoc 3 ed) ed)
                   (append ed (list (cons 3 cdc:*style*))))))
      (foreach code '(62 6 370) (setq ed (cdc:strip code ed)))
      (entmod ed)
      (entupd en)
      t)))

;; one foot expressed in the current drawing units (INSUNITS), so the
;; tolerances below mean the same thing whatever the drawing works in
(defun cdc:onefoot (/ u)
  (setq u (getvar "INSUNITS"))
  (cond ((= u 2) 1.0)                   ; feet
        ((= u 4) 304.8)                 ; millimetres
        ((= u 5) 30.48)                 ; centimetres
        ((= u 6) 0.3048)                ; metres
        ((= u 10) (/ 1.0 3.0))          ; yards
        (t 12.0)))                      ; inches / unitless

;; how close two extension line origins have to be before they count as
;; the same point - a sixteenth of an inch, in the drawing's own units,
;; unless cdc:*dupetol* says otherwise
(defun cdc:dupetol ()
  (if cdc:*dupetol* cdc:*dupetol* (/ (cdc:onefoot) 192.0)))

;; T when a and b are the same point on the plan, within tol.  Compared
;; flat: a survey point carries an elevation, the dimension that
;; measures to it does not, and that difference must not read as two
;; different places.
(defun cdc:samept (a b tol)
  (and (<= (abs (- (car  a) (car  b))) tol)
       (<= (abs (- (cadr a) (cadr b))) tol)))

;; the pairs of extension line origins every dimension in model space
;; already carries.  A radial, angular or ordinate dim has no such pair
;; and is passed over.
(defun cdc:dimscan ( / ss i ed out)
  (setq out nil
        ss  (ssget "_X" '((0 . "DIMENSION") (410 . "Model")))
        i   0)
  (if ss
    (while (< i (sslength ss))
      (setq ed (entget (ssname ss i))
            i  (1+ i))
      (if (and (assoc 13 ed) (assoc 14 ed))
        (setq out (cons (list (cdr (assoc 13 ed)) (cdr (assoc 14 ed)))
                        out)))))
  out)

;; T when p1-p2 is one of the pairs in LST, either way round: the
;; "that tie is dimensioned already, leave it alone" test.  Where the
;; existing dim line sits is deliberately not part of it -- a dim of
;; this tie pushed off to one side is still a dim of this tie.
(defun cdc:dimmed-p (p1 p2 lst / tol q hit)
  (setq tol (cdc:dupetol))
  (while (and lst (not hit))
    (setq q   (car lst)
          lst (cdr lst))
    (if (or (and (cdc:samept (car q) p1 tol) (cdc:samept (cadr q) p2 tol))
            (and (cdc:samept (car q) p2 tol) (cdc:samept (cadr q) p1 tol)))
      (setq hit t)))
  hit)

;; "POOL, POINTS" from a list of layer names
(defun cdc:names (lst / out)
  (foreach n lst
    (setq out (if out (strcat out ", " n) n)))
  (if out out ""))

;;; -------------------- the command --------------------------------

(defun c:CDCREATE ( / *error* olderr odim
                      ss i en ed typ ends pairs skipped plines dimmed
                      already havestyle undo-open pre new made gone lays
                      p1 p2 )

  ;; -- restore drawing state on error / Esc.  The user's settings come
  ;;    back FIRST so nothing below can skip them; a dimension command
  ;;    may still be open, so AutoCAD is talked to through command-s --
  ;;    and the undo group is closed, or the next U would swallow the
  ;;    user's own work
  (setq olderr *error*)
  (defun *error* (m)
    (cal:sysrestore)
    (cdc:restyle odim)
    (if undo-open
      (vl-catch-all-apply 'command-s (list "_.UNDO" "_End")))
    (setq *error* olderr)
    (if (and m (not (wcmatch (strcase m)
                             "*BREAK*,*CANCEL*,*QUIT*,*EXIT*")))
      (princ (strcat "\nCDCREATE error: " m)))
    (princ))

  (vl-load-com)
  (cal:syssave '("OSMODE" "CMDECHO" "CLAYER"))
  (setq odim (getvar "DIMSTYLE"))

  ;; -- 1. the highlighted lines: a pickfirst selection if there is
  ;;       one, otherwise ask for it
  (setq ss (ssget "_I"))
  (if (null ss)
    (progn
      (princ "\nHighlight the lines to cross-dimension: ")
      (setq ss (ssget))))

  (if (null ss)
    (princ "\nNothing highlighted -- nothing to dimension.")
    (progn
      ;; -- 2. keep the lines, count what was ignored.  What the
      ;;       drawing already carries is read once, up front, and each
      ;;       tie kept is added to it -- so two coincident lines in one
      ;;       selection are the same tie, dimensioned once
      (setq i 0 pairs nil skipped 0 plines 0 already 0
            dimmed (if cdc:*skipdimmed* (cdc:dimscan)))
      (while (< i (sslength ss))
        (setq en  (ssname ss i)
              ed  (entget en)
              typ (cdr (assoc 0 ed)))
        (cond
          ((not (= "LINE" typ))
             (setq skipped (1+ skipped))
             (if (member typ '("LWPOLYLINE" "POLYLINE"))
               (setq plines (1+ plines))))
          (t
             (setq ends (cdc:ends en)
                   p1   (car  ends)
                   p2   (cadr ends))
             (cond
               ((<= (distance p1 p2) 1e-9)        ; nothing to measure
                  (setq skipped (1+ skipped)))
               ((and cdc:*skipdimmed* (cdc:dimmed-p p1 p2 dimmed))
                  (setq already (1+ already)))
               (t
                  (setq pairs  (cons (list en p1 p2 (cdr (assoc 8 ed)))
                                     pairs)
                        dimmed (cons (list p1 p2) dimmed))))))
        (setq i (1+ i)))
      (setq pairs (reverse pairs))

      (if (null pairs)
        (princ (if (> already 0)
                 (strcat "\n" (itoa already) " tie"
                         (if (= already 1) " is" "s are")
                         " dimensioned already -- nothing new to draw.")
                 "\nNo lines in the selection -- nothing to dimension."))
        (progn
          ;; -- 3. layer and style, all of it inside one undo group
          (setvar "CMDECHO" 0)
          (setvar "OSMODE"  0)
          (command "_.UNDO" "_Begin")
          (setq undo-open t)
          (setvar "CLAYER" (cal:ensure-layer cdc:*layer* 7))
          (setq havestyle (cdc:setstyle cdc:*style*))
          (if (not havestyle)
            (princ (strcat "\n** This drawing has no \"" cdc:*style*
                           "\" dimension style -- dims drawn in \""
                           (getvar "DIMSTYLE")
                           "\" instead.  Create the style (or start"
                           " from the standard template) and re-run.")))

          ;; -- 4. one aligned dim per line, on the line, and then the
          ;;       line itself goes: the tie is the dimension now
          (setq made 0 gone 0 lays nil)
          (foreach pr pairs
            (setq en  (car    pr)
                  p1  (cadr   pr)
                  p2  (caddr  pr)
                  pre (entlast))
            (command "_.DIMALIGNED"
                     "_non" (trans p1 0 1)
                     "_non" (trans p2 0 1)
                     "_non" (trans (cdc:loc p1 p2 0.5 cdc:*offset*) 0 1))
            (setq new (entlast))
            (if (and new (not (eq new pre)))
              (progn
                ;; slide the text down the dimension line, out of the
                ;; middle -- DIMTEDIT moves the text alone, and the move
                ;; is along the dimension line, so the line itself does
                ;; not shift whatever DIMTMOVE says
                (if (not (equal cdc:*textpos* 0.5 1e-6))
                  (command "_.DIMTEDIT" new
                           "_non" (trans (cdc:loc p1 p2
                                                  (cdc:textfrac p1 p2)
                                                  cdc:*offset*)
                                         0 1)))
                (cdc:fixdim new havestyle)
                (setq made (1+ made))
                ;; only a line that really did get its dimension is
                ;; erased -- a dim AutoCAD refused to draw leaves its
                ;; line in the drawing to be dealt with
                (if (and cdc:*erase* (entget en))
                  (progn (entdel en)
                         (setq gone (1+ gone))
                         (if (not (member (cadddr pr) lays))
                           (setq lays (cons (cadddr pr) lays))))))))

          ;; -- 5. put the drawing back the way it was
          (cdc:restyle odim)
          (command "_.UNDO" "_End")
          (setq undo-open nil)

          (princ (strcat "\n" (itoa made) " cross dimension"
                         (if (= made 1) "" "s") " created on layer "
                         cdc:*layer*
                         (if havestyle
                           (strcat " in style " cdc:*style* ".")
                           " (current style).")))
          (if (> gone 0)
            (princ (strcat "\n" (itoa gone) " dimensioned line"
                           (if (= gone 1) "" "s") " erased (layer"
                           (if (= 1 (length lays)) " " "s ")
                           (cdc:names (reverse lays)) ").")))
          (if (> already 0)
            (princ (strcat "\n" (itoa already) " line"
                           (if (= already 1) "" "s")
                           " left alone -- those two points carry a"
                           " dimension already.")))
          (if (> skipped 0)
            (princ (strcat "\n" (itoa skipped)
                           " selected object(s) were not lines and were"
                           " left alone."
                           (if (> plines 0)
                             " Explode a polyline to cross-dim its segments."
                             ""))))))))

  ;; every path out of the command drops the snapshot, the quiet ones
  ;; included: a run that found nothing to do and kept its snapshot
  ;; would hand it to the NEXT run, which would then put the user's
  ;; settings back to what they were two commands ago
  (cal:sysrestore)
  (setq *error* olderr)
  (princ))

(defun c:CDCREATEVER ()
  (princ (strcat "\nCDCREATE " *cdcreate-version*))
  (princ))

(princ (strcat "\nCDCREATE " *cdcreate-version*
               " loaded -- dimension highlighted lines as cross dims"
               " (style \"" cdc:*style* "\", layer \"" cdc:*layer* "\")."))
(princ)


;;; ======================================================================
;;; >>> check_drawing.lsp
;;; ======================================================================

;;; ------------------------------------------------------------------
;;;  check_drawing.lsp — CHECK: attachment QA for AutoCAD drawings
;;;
;;;  Adds the CHECK command (alias DIMARCCHECK). After asking you to
;;;  highlight the drawing, it runs two audits over the selection:
;;;
;;;  1. Dimensions (linear / aligned / rotated): both definition
;;;     points must lie on an object of some kind (line, arc, circle,
;;;     polyline, ellipse, spline). A dimension with a stray
;;;     definition point gets:
;;;       - a construction line (XLINE) drawn through its two dimmed
;;;         points on layer CHECK-CONSTRUCTION (yellow),
;;;       - the stray point shifted onto the closest point of the
;;;         closest object,
;;;       - its color changed to red so you can see it was shifted.
;;;
;;;  2. Arcs: each arc endpoint must sit at the END of another object.
;;;       - On an object but not at its end -> endpoint moved to the
;;;         closest end of that object.
;;;       - Not on anything -> endpoint moved to the closest endpoint
;;;         of any object in the selection (or, when every nearby
;;;         object is closed, the closest point on the closest one).
;;;     A moved arc is re-fitted through its fixed end, its old
;;;     midpoint and the new end, then recolored magenta.
;;;
;;;  Everything runs inside one UNDO group; a single U reverts every
;;;  change CHECK made. Tunables are just below.
;;; ------------------------------------------------------------------

;;; SHARED BUILD: requires CALOFIN-LIB.lsp (load via CALOFIN-LOADER.lsp).
;;; Generic helpers live there under cal: - see STANDARDS.md.
;;;

(setq *checkdrawing-version* "v1.0")   ; announced on load; release_lisp.py
                                          ; stamps the dated twin in releases/

(vl-load-com)

;; --- tunables ------------------------------------------------------
(setq *cfchk-tol*          1.0e-4)  ; max gap (drawing units) that still counts as attached
(setq *cfchk-dim-color*    1)       ; red: dimensions whose points were shifted
(setq *cfchk-arc-color*    6)       ; magenta: arcs whose endpoints were snapped
(setq *cfchk-constr-layer* "CHECK-CONSTRUCTION")
(setq *cfchk-constr-color* 2)       ; yellow

;; entity types dimensions and arc ends may attach to
(setq *cfchk-curve-types*
      '("LINE" "ARC" "CIRCLE" "ELLIPSE" "LWPOLYLINE" "POLYLINE" "SPLINE"))

;; --- small helpers -------------------------------------------------

(defun cfchk:set-color (ent color / ed old)
  (setq ed  (entget ent)
        old (assoc 62 ed))
  (entmod (if old
            (subst (cons 62 color) old ed)
            (append ed (list (cons 62 color)))))
  (entupd ent))

(defun cfchk:make-xline (p1 p2 / len)
  ;; infinite construction line through p1-p2 on the check layer
  (setq len (distance p1 p2))
  (if (> len 1e-8)
    (entmake (list '(0 . "XLINE")
                   '(100 . "AcDbEntity")
                   (cons 8 *cfchk-constr-layer*)
                   '(100 . "AcDbXline")
                   (cons 10 p1)
                   (cons 11 (mapcar '(lambda (x) (/ x len)) (mapcar '- p2 p1)))))))

(defun cfchk:closest-on (ent pt / res)
  ;; closest point on ent to pt; nil when ent is not curve-like
  (setq res (vl-catch-all-apply 'vlax-curve-getClosestPointTo (list ent pt)))
  (if (vl-catch-all-error-p res) nil res))

(defun cfchk:nearest-curve (pt exclude cands / best bestd cp d)
  ;; (ent closest-point distance) for the candidate closest to pt
  (foreach e cands
    (if (and (not (eq e exclude)) (setq cp (cfchk:closest-on e pt)))
      (progn
        (setq d (distance pt cp))
        (if (or (null bestd) (< d bestd))
          (setq bestd d
                best  (list e cp d))))))
  best)

(defun cfchk:curve-ends (ent / cl sp ep)
  ;; the curve's two endpoints; nil when closed (or not a curve)
  (setq cl (vl-catch-all-apply 'vlax-curve-isClosed (list ent)))
  (if (or (vl-catch-all-error-p cl) cl)
    nil
    (progn
      (setq sp (vl-catch-all-apply 'vlax-curve-getStartPoint (list ent))
            ep (vl-catch-all-apply 'vlax-curve-getEndPoint (list ent)))
      (if (or (vl-catch-all-error-p sp) (vl-catch-all-error-p ep))
        nil
        (list sp ep)))))

(defun cfchk:closest-of (pt pts / best bestd d)
  (foreach q pts
    (setq d (distance pt q))
    (if (or (null bestd) (< d bestd)) (setq bestd d best q)))
  best)

(defun cfchk:nearest-end (pt exclude cands / best bestd d)
  ;; closest endpoint over every open candidate curve
  (foreach e cands
    (if (not (eq e exclude))
      (foreach q (cfchk:curve-ends e)
        (setq d (distance pt q))
        (if (or (null bestd) (< d bestd)) (setq bestd d best q)))))
  best)

;; --- geometry ------------------------------------------------------

(defun cfchk:planar-arc-p (ed / n)
  ;; only arcs drawn in the world XY plane are handled
  (setq n (cdr (assoc 210 ed)))
  (or (null n)
      (and (< (abs (car n)) 1e-9)
           (< (abs (cadr n)) 1e-9)
           (> (caddr n) 0.0))))

(defun cfchk:rebuild-arc (ent which fixed mid target / c r a1 a2 am tmp ed)
  ;; re-fit the arc through its fixed end, its old midpoint and the
  ;; target point; returns T on success
  (if (and (> (distance target fixed) 1e-8)
           (setq c (cal:circumcenter fixed mid target)))
    (progn
      (setq r  (distance c target)
            a1 (angle c (if (eq which 'start) target fixed))
            a2 (angle c (if (eq which 'start) fixed target))
            am (angle c mid))
      ;; ARC entities always sweep counter-clockwise from start to
      ;; end; keep the sweep that contains the old midpoint
      (if (> (cal:angnorm (- am a1)) (cal:angnorm (- a2 a1)))
        (setq tmp a1
              a1  a2
              a2  tmp))
      (setq ed (entget ent))
      (foreach pair (list (cons 10 c) (cons 40 r) (cons 50 a1) (cons 51 a2))
        (setq ed (subst pair (assoc (car pair) ed) ed)))
      (if (entmod ed)
        (progn (entupd ent) T)))))

;; --- audit 1: dimension attachment ---------------------------------

(defun cfchk:fix-defpoint (ent gcode cands / ed pt near)
  ;; shift one definition point onto the closest object when it is
  ;; not already on one; returns the shift distance, nil if untouched
  (setq ed (entget ent)
        pt (cdr (assoc gcode ed)))
  (if pt
    (progn
      (setq near (cfchk:nearest-curve pt nil cands))
      (if (and near (> (caddr near) *cfchk-tol*))
        (if (entmod (subst (cons gcode (cadr near)) (assoc gcode ed) ed))
          (caddr near))))))

(defun cfchk:check-dim (ent cands / ed dtype p13 p14 d1 d2)
  (setq ed    (entget ent)
        dtype (logand 7 (cdr (assoc 70 ed))))
  (if (member dtype '(0 1))                 ; rotated/linear or aligned
    (progn
      (setq p13 (cdr (assoc 13 ed))         ; the two dimmed points
            p14 (cdr (assoc 14 ed))
            d1  (cfchk:fix-defpoint ent 13 cands)
            d2  (cfchk:fix-defpoint ent 14 cands))
      (if (or d1 d2)
        (progn
          (cfchk:make-xline p13 p14)        ; through the ORIGINAL points
          (cfchk:set-color ent *cfchk-dim-color*)
          (entupd ent)
          (princ (strcat "\n  Dimension " (cdr (assoc 5 ed)) ":"
                         (if d1 (strcat " point 1 shifted " (rtos d1 2 4)) "")
                         (if d2 (strcat " point 2 shifted " (rtos d2 2 4)) "")
                         " onto nearest object; recolored red."))
          'fixed)
        'ok))
    'skipped))

;; --- audit 2: arc endpoint attachment ------------------------------

(defun cfchk:fix-arc-end (ent which cands / p other mid near ends target)
  ;; returns the snap distance when the endpoint was moved, else nil
  (setq mid   (vlax-curve-getPointAtDist
                ent
                (/ (vlax-curve-getDistAtParam ent (vlax-curve-getEndParam ent)) 2.0))
        p     (if (eq which 'start)
                (vlax-curve-getStartPoint ent)
                (vlax-curve-getEndPoint ent))
        other (if (eq which 'start)
                (vlax-curve-getEndPoint ent)
                (vlax-curve-getStartPoint ent))
        near  (cfchk:nearest-curve p ent cands))
  (cond
    ((null near) nil)                       ; nothing to attach to at all
    ((<= (caddr near) *cfchk-tol*)          ; endpoint sits on an object...
     (setq ends (cfchk:curve-ends (car near)))
     ;; never snap onto the arc's own other endpoint
     (setq ends (vl-remove-if '(lambda (q) (< (distance q other) 1e-8)) ends))
     (cond
       ((null ends) nil)                    ; closed curve: no ends to demand
       ((vl-some '(lambda (q) (<= (distance p q) *cfchk-tol*)) ends)
        nil)                                ; ...and at one of its ends: OK
       (t                                   ; ...but mid-object: closest end of that object
        (setq target (cfchk:closest-of p ends))
        (if (cfchk:rebuild-arc ent which other mid target)
          (distance p target)))))
    (t                                      ; floating: closest end anywhere,
     (setq target (cfchk:nearest-end p ent cands))
     (if (or (null target) (< (distance target other) 1e-8))
       (setq target (cadr near)))           ; else closest point on closest object
     (if (cfchk:rebuild-arc ent which other mid target)
       (distance p target)))))

(defun cfchk:check-arc (ent cands / ed d1 d2)
  (setq ed (entget ent))
  (if (cfchk:planar-arc-p ed)
    (progn
      (setq d1 (cfchk:fix-arc-end ent 'start cands)
            d2 (cfchk:fix-arc-end ent 'end cands))
      (if (or d1 d2)
        (progn
          (cfchk:set-color ent *cfchk-arc-color*)
          (princ (strcat "\n  Arc " (cdr (assoc 5 ed)) ":"
                         (if d1 (strcat " start snapped " (rtos d1 2 4)) "")
                         (if d2 (strcat " end snapped " (rtos d2 2 4)) "")
                         " to nearest object end; recolored magenta."))
          'fixed)
        'ok))
    'skipped))

;; --- command -------------------------------------------------------

(defun c:CHECK ( / *error* oldecho undo-open ss i e et cands dims arcs res
                   ndf ndo nds naf nao nas)
  (defun *error* (msg)
    (if undo-open
      (progn (setvar "CMDECHO" 0) (command "_.UNDO" "_End")))
    (if oldecho (setvar "CMDECHO" oldecho))
    (if (and msg (not (wcmatch (strcase msg) "*BREAK*,*CANCEL*,*QUIT*,*EXIT*")))
      (princ (strcat "\nCHECK error: " msg)))
    (princ))

  (prompt "\nHighlight the drawing to CHECK: ")
  (setq ss (ssget))
  (cond
    ((null ss)
     (prompt "\nNothing selected - CHECK cancelled."))
    (t
     (setq cands nil dims nil arcs nil i 0
           ndf 0 ndo 0 nds 0 naf 0 nao 0 nas 0)
     (repeat (sslength ss)
       (setq e  (ssname ss i)
             i  (1+ i)
             et (cdr (assoc 0 (entget e))))
       (if (= et "DIMENSION") (setq dims (cons e dims)))
       (if (= et "ARC") (setq arcs (cons e arcs)))
       (if (member et *cfchk-curve-types*) (setq cands (cons e cands))))
     (setq dims  (reverse dims)
           arcs  (reverse arcs)
           cands (reverse cands))
     (cond
       ((and (null dims) (null arcs))
        (prompt "\nSelection holds no dimensions or arcs - nothing to check."))
       ((null cands)
        (prompt "\nSelection holds no lines/arcs/curves to attach to - nothing to check against."))
       (t
        (setq oldecho (getvar "CMDECHO"))
        (setvar "CMDECHO" 0)
        (command "_.UNDO" "_Begin")
        (setq undo-open T)
        (cal:ensure-layer *cfchk-constr-layer* *cfchk-constr-color*)
        (foreach e dims
          (setq res (cfchk:check-dim e cands))
          (cond ((eq res 'fixed)   (setq ndf (1+ ndf)))
                ((eq res 'skipped) (setq nds (1+ nds)))
                (t                 (setq ndo (1+ ndo)))))
        (foreach e arcs
          (setq res (cfchk:check-arc e cands))
          (cond ((eq res 'fixed)   (setq naf (1+ naf)))
                ((eq res 'skipped) (setq nas (1+ nas)))
                (t                 (setq nao (1+ nao)))))
        (command "_.UNDO" "_End")
        (setq undo-open nil)
        (setvar "CMDECHO" oldecho)
        (princ (strcat "\n--- CHECK complete (attachment tolerance "
                       (rtos *cfchk-tol* 2 6) ") ---"
                       "\nDimensions: " (itoa (+ ndf ndo)) " checked, "
                       (itoa ndf) " shifted onto nearest object (red)"
                       (if (> nds 0)
                         (strcat ", " (itoa nds) " unsupported type skipped")
                         "")
                       "\nArcs: " (itoa (+ naf nao)) " checked, "
                       (itoa naf) " with endpoint(s) snapped (magenta)"
                       (if (> nas 0)
                         (strcat ", " (itoa nas) " non-planar skipped")
                         "")
                       (if (> ndf 0)
                         (strcat "\nConstruction lines through the shifted dimensions' points are on layer "
                                 *cfchk-constr-layer* ".")
                         "")
                       "\nOne UNDO reverts everything CHECK changed."))))))
  (princ))

(defun c:DIMARCCHECK () (c:CHECK))

(princ "\ncheck_drawing.lsp loaded - type CHECK to audit dimension & arc attachment.")
(princ)


;;; ======================================================================
;;; >>> CONSTELLATION.lsp
;;; ======================================================================

;;; ======================================================================
;;; CONSTELLATION.lsp  --  points placed from the dims between them
;;; ----------------------------------------------------------------------
;;; For AutoCAD 2018 and later (plain AutoLISP, no external libraries).
;;;
;;; Commands:  CONSTELLATION     place labelled points from their cross dims
;;;            CONSTELLATIONVER  print the loaded version
;;;
;;; SHARED BUILD: requires CALOFIN-LIB.lsp (load via CALOFIN-LOADER.lsp).
;;; Generic helpers live there under cal: - see STANDARDS.md.
;;;
;;; The job this exists for: a site sheet that gives distances BETWEEN
;;; points and never says where any of them is.  A tape run corner to
;;; corner, corner to skimmer, skimmer to light -- fourteen numbers and
;;; no origin.  Every other calofin importer wants coordinates (XYPLOT
;;; is handed X and Y; ABCDEF is handed offsets off a baseline).  This
;;; one is handed only the web of distances and has to work the
;;; positions out.
;;;
;;; THE RUN, in order:
;;;
;;;   1. THE SPACE.  A rectangle of known X and Y that the points are
;;;      allowed to sit in -- the yard, the deck, the envelope the pool
;;;      has to land inside.  It is asked first because it is also what
;;;      sets the SCALE of the first guess: without it the solver has no
;;;      idea whether this is a 12 foot spa or a 60 foot pool.
;;;
;;;   2. HOW MANY POINTS, labelled A, B, C ... up to Z.
;;;
;;;   3. THE STARTING LAYOUT, drawn on screen before a single dim is
;;;      asked for: the points evenly spaced round the oval inscribed in
;;;      the space, running CLOCKWISE FROM THE TOP LEFT.  Nothing about
;;;      it is a measurement - it is there so the operator can see which
;;;      letter is which before naming a pair.  It is erased again the
;;;      moment the real positions are known.
;;;
;;;   4. THE CROSS DIMS.  Every pair -- A-B, A-C, A-D ... -- is on
;;;      offer and NONE is compulsory.  A field sheet almost never
;;;      carries all of them; the point is to let the operator enter
;;;      the ones it does carry, in whatever order they are written
;;;      down.  What IS required is two dims on every point, because a
;;;      point with one dim sits anywhere on a circle and a point with
;;;      none sits anywhere at all.
;;;
;;;   5. THE ARCS.  A run of points that lies on ONE radius, named
;;;      CLOCKWISE -- A-C, or ABC spelled out, or the wrap Z-B meaning
;;;      Z A B.  Cross dims say how far apart things are and nothing
;;;      about how the wall between them curves, so a radius end can be
;;;      measured perfectly and still come out as a flat chord.  To the
;;;      solver an arc is simply one more point, its centre, a dim of R
;;;      away from every point on it -- and it pins what the dims leave
;;;      loose.
;;;
;;;   6. THE SOLVE, then the drawing: an ab_pt survey point per letter,
;;;      an aligned dimension per dim given, the space itself, and an
;;;      outline that bends round any arc declared.
;;;
;;;   7. DOES IT LOOK RIGHT?  A number typed wrong is the ordinary case,
;;;      not an exception: nobody can tell 24'-6" was meant to be 24'-9"
;;;      from the chart, and anybody can tell from the drawing.  So the
;;;      drawing is the check.  A No asks whether the dims, the arcs or
;;;      both need changing, takes the corrected value, takes the wrong
;;;      drawing away and puts the right one down, round as many times
;;;      as it takes.
;;;
;;; WHAT THE SOLVER DOES.  The dims are almost never exactly consistent
;;; -- a tape reads a sixteenth long, a corner is measured to the
;;; coping instead of the wall -- so there is usually NO layout that
;;; satisfies all of them.  What is computed is the layout that misses
;;; by as little as possible, and the report says how far each dim
;;; ended up from what was given.  A dim that will not come into line
;;; is a dim to go back and re-measure, which is the most useful thing
;;; this command can tell anyone -- and it is only worth saying if the
;;; fit is exact when the dims ARE consistent, which is why the solve
;;; runs in two stages: sweeps to find the right answer, then damped
;;; Gauss-Newton to land on it exactly.  See both stages below.
;;;
;;; TWO THINGS THE DISTANCES CANNOT SETTLE, and how they are settled:
;;;
;;;   WHICH WAY ROUND.  A constellation and its mirror image satisfy
;;;     exactly the same distances.  The operator was shown A, B, C
;;;     running clockwise, so the mirror that reads clockwise is drawn.
;;;
;;;   WHICH WAY UP.  Distances are rotation-blind too, so the result is
;;;     turned to sit inside the space -- and among the angles that fit,
;;;     to land as near as it can to the oval that was previewed, so the
;;;     letters stay roughly where they were shown.
;;;
;;; All geometry is created in inches (1 drawing unit = 1 inch).
;;; ======================================================================

(vl-load-com)

;; Version banner, shown on load and at the top of every run's report.
(setq *constellation-version* "v1.2")

;;; ----------------------------------------------------------------------
;;;  Tunables
;;; ----------------------------------------------------------------------

(setq cst:*space-layer*   "CONSTELLATION-SPACE")   ; the rectangle asked for
(setq cst:*guide-layer*   "CONSTELLATION-GUIDE")   ; the starting oval, erased
(setq cst:*outline-layer* "CONSTELLATION")         ; the ring through A B C ...
(setq cst:*dim-layer*     "DIMENSION")             ; as AUTODIM and WCALST
(setq cst:*point-layer*   "POINTS")                ; as ABCDEF and XYPLOT

;; ABCDEF's survey block, so ABHD / CABHD / ABFIND / LHD / BPCALLOUT
;; read this import the same as any other.
(setq cst:*point-block* "ab_pt")
(setq cst:*point-tag*   "number")

;; Single-letter labels, so 26 is the ceiling.  3 is the floor: two
;; points share one dim and neither of them has the two that a
;; placement needs.
(setq cst:*letters*  "ABCDEFGHIJKLMNOPQRSTUVWXYZ")
(setq cst:*minpts*   3)
(setq cst:*maxpts*   26)
(setq cst:*defcount* 4)

;; The solve runs in two stages (see "The solve" below).  Sweeps only
;; have to get the layout into the right BASIN now, which they do in a
;; few dozen; the fit itself is finished by Levenberg-Marquardt.
(setq cst:*sweeps* 120)
(setq cst:*tol*    1.0e-6)      ; drawing units of movement, per sweep

;; The fit.  Iterations are the outer Levenberg-Marquardt steps and
;; tries the damping retries inside one of them; *lm-done* is the sum
;; of squared misses below which there is nothing left to gain (about a
;; ten-millionth of an inch, RMS).
(setq cst:*lm-iters*  40)
(setq cst:*lm-tries*   8)
(setq cst:*lm-lam*  1.0e-3)     ; starting damping
(setq cst:*lm-lammin* 1.0e-12)
(setq cst:*lm-done* 1.0e-14)

;; Starts tried, best kept.  A stress minimum is LOCAL, and a
;; constellation that starts folded can stay folded, so the oval is not
;; the only thing tried.
(setq cst:*squash* 0.35)        ; second start: the oval flattened
(setq cst:*shake*  0.30)        ; third start: the oval scattered, as a
                                ; share of the smaller space dimension

;; The turn-to-fit sweep: whole circle at cst:*rot-coarse* steps, then
;; cst:*rot-passes* refining passes, each one grid spacing either side
;; of the last winner.
(setq cst:*rot-coarse* 360)
(setq cst:*rot-fine*   40)
(setq cst:*rot-passes* 3)

;; A dim that ends up further than this from what was given is starred
;; in the report -- at a sixteenth of an inch nobody re-measures, at a
;; quarter of an inch something is wrong with the sheet.
(setq cst:*flag* 0.25)

;; Drawing sizes, as shares of the smaller side of the space.
(setq cst:*texth*   0.025)      ; label / attribute height
(setq cst:*dotr*    0.008)      ; preview marker radius
(setq cst:*dimoff*  0.060)      ; how far a perimeter dim stands off

;;; ----------------------------------------------------------------------
;;;  Ask layer  --  the STANDARDS section 4 helpers
;;;
;;;  Copies of CALOFIN-LIB.lsp's cal: originals under this file's own
;;;  prefix, so it loads alone with APPLOAD; in the shared/ twin they
;;;  are gone and every call site reads cal: instead (STANDARDS section
;;;  6).  Bodies identical to the library's.
;;;
;;;  askkw takes the bracket text SHOWN third, like the library's.  The
;;;  only keyword question this tool asks is the Yes/No at the end, so
;;;  askkw is here for askyn to call and has no other call site whose
;;;  bracket could drift from its keywords.  Back is signalled by the
;;;  sentinel symbol these helpers return, which the twin renames along
;;;  with them -- so every call site tests for it by name and neither
;;;  tier needs a special case.
;;; ----------------------------------------------------------------------

;;; ----------------------------------------------------------------------
;;;  Settings, undo, layers  --  the STANDARDS section 5 skeleton
;;;
;;;  Library copies again, gone in the shared/ twin -- all but
;;;  cst:sysvars, which is this file's own list of what it changes.
;;;
;;;  OSMODE is deliberately NOT in the snapshot: this command feeds no
;;;  points to any AutoCAD command (every entity here is entmade), so
;;;  there is no moment where a stray snap could grab the wrong
;;;  geometry, and the operator's own snaps stay live at the one point
;;;  they are asked for.  Nothing to zero is nothing to restore.
;;; ----------------------------------------------------------------------


;; Every entity drawn as the starting-layout preview, so the error
;; handler can take it away too -- an Esc part way through the chart
;; must not leave the legend sitting in the drawing waiting for a U.
(setq cst:*preview* nil)

;; And everything drawn as the RESULT, for the same reason and for one
;; more: the run ends by asking whether the drawing looks right, and a
;; No has to take it away again before the corrected one goes down.
(setq cst:*drawn* nil)

(defun cst:sysvars () '("CMDECHO"))

;;; ----------------------------------------------------------------------
;;;  2-D vector helpers  --  the CALOFIN-LIB set again, copied here for
;;;  the standalone build and gone in the shared/ twin
;;; ----------------------------------------------------------------------

;;; ----------------------------------------------------------------------
;;;  The letters
;;;
;;;  Points are named, not numbered, because the operator says "A to C"
;;;  out loud and writes it on the sheet the same way.  The index a
;;;  letter carries is its 0-based position, which is also its place in
;;;  the clockwise ring.
;;; ----------------------------------------------------------------------

(defun cst:letter (i) (substr cst:*letters* (1+ i) 1))

;; The 0-based index of the single letter C, or nil when C is not one.
(defun cst:index (c / p)
  (if (= 1 (strlen c))
    (setq p (vl-string-search (strcase c) cst:*letters*)))
  p)

;; The name a pair of points is known by, always low letter first, so
;; "C-A" and "A-C" are the same entry and not two.
(defun cst:key (i j)
  (strcat (cst:letter (min i j)) "-" (cst:letter (max i j))))

;;; ----------------------------------------------------------------------
;;;  The chart of dims given
;;;
;;;  One entry per dim the operator has: ("A-C" 0 2 168.0) -- the name
;;;  first so plain assoc finds it, then the two indices, then the
;;;  measurement.  Absent means not measured; there is no
;;;  present-but-nil entry to tell apart from a missing one (the
;;;  three-state rule of STANDARDS section 7.1 is about a FORM store,
;;;  and this chart is not one).
;;;
;;;  Newest first, because Back undoes the last thing typed -- so
;;;  putdim always removes any older entry for the pair before consing
;;;  the new one on, and re-answering a pair moves it to the front
;;;  rather than leaving it where it was.
;;; ----------------------------------------------------------------------

(defun cst:deldim (k chart)
  (vl-remove-if '(lambda (e) (= (car e) k)) chart))

(defun cst:putdim (i j v chart / k)
  (setq k     (cst:key i j)
        chart (cst:deldim k chart))
  (cons (list k (min i j) (max i j) v) chart))

;; Every pair of N points, in reading order: A-B, A-C ... A-Z, B-C ...
(defun cst:pairs (n / out i j)
  (setq out nil i 0)
  (while (< i n)
    (setq j (1+ i))
    (while (< j n)
      (setq out (cons (list i j) out)
            j   (1+ j)))
    (setq i (1+ i)))
  (reverse out))

;; How many dims touch point I.
(defun cst:degree (i chart / d e)
  (setq d 0)
  (foreach e chart
    (if (or (= i (cadr e)) (= i (caddr e))) (setq d (1+ d))))
  d)

;; For each point, the dims leading away from it as (other distance).
;; Built once and handed to the solver, which would otherwise search
;; the whole chart for every point on every sweep.
;;
;; Every arc adds ONE MORE POINT to the layout -- its centre, index n
;; for the first arc stored, n+1 for the next -- with a dim of R to
;; each point on the arc.  That is all an arc IS to the solver: another
;; point whose distances happen to be equal, which is exactly the shape
;; the sweep already knows how to settle.  The centres carry no letter
;; and are never drawn as points.
(defun cst:adjacency (n chart arcs / rows e k c i)
  (setq rows nil)
  (repeat (+ n (length arcs)) (setq rows (cons nil rows)))
  (foreach e chart
    (setq rows (cst:setnth rows (cadr e)
                 (cons (list (caddr e) (cadddr e)) (nth (cadr e) rows))))
    (setq rows (cst:setnth rows (caddr e)
                 (cons (list (cadr e) (cadddr e)) (nth (caddr e) rows)))))
  (setq k n)
  (foreach c arcs
    (foreach i (cadr c)
      (setq rows (cst:setnth rows i
                   (cons (list k (caddr c)) (nth i rows))))
      (setq rows (cst:setnth rows k
                   (cons (list i (caddr c)) (nth k rows)))))
    (setq k (1+ k)))
  rows)

(defun cst:setnth (lst i val / k out x)
  (setq k 0 out nil)
  (foreach x lst
    (setq out (cons (if (= k i) val x) out)
          k   (1+ k)))
  (reverse out))

;;; ----------------------------------------------------------------------
;;;  Arcs
;;;
;;;  A run of points that lies on ONE radius.  Cross dims say how far
;;;  apart things are and nothing about how the wall between them
;;;  curves, so a pool with a radius end can have its points measured
;;;  perfectly and still come out as a straight-sided polygon.  An arc
;;;  says the wall is a radius, pins the points that sit on it, and is
;;;  drawn as a real arc rather than a chord.
;;;
;;;  Named CLOCKWISE, the way the letters were handed out, so a run
;;;  that crosses the end of the alphabet is unambiguous: on a
;;;  twenty-six point job Z-B is Z A B, never B all the way back round
;;;  to Z.  Two letters are a FROM and a TO with the run between them
;;;  filled in; three or more are taken as named.
;;;
;;;  Stored newest first, like the chart, so Back undoes the last one
;;;  given: (name indices radius bows-out).
;;; ----------------------------------------------------------------------

;; "A-B-C-D" -- the name a run is known by.
(defun cst:runname (idx / out k)
  (setq out "")
  (foreach k idx
    (setq out (strcat out (if (= out "") "" "-") (cst:letter k))))
  out)

;; The points S names.  Two letters are filled in clockwise between
;; them; three or more are taken as typed.  nil for anything that is
;; not at least two of this job's points.
(defun cst:parserun (s n / ls out i)
  (setq ls (cst:letters-in s n))
  (cond ((null ls) nil)
        ((< (length ls) 2) nil)
        ((> (length ls) 2) ls)
        (t (setq out (list (car ls)) i (car ls))
           (while (/= i (cadr ls))
             (setq i   (rem (1+ i) n)
                   out (cons i out)))
           (reverse out))))

(defun cst:delarc (k arcs)
  (vl-remove-if '(lambda (a) (= (car a) k)) arcs))

(defun cst:putarc (idx r bow arcs / k)
  (setq k    (cst:runname idx)
        arcs (cst:delarc k arcs))
  (cons (list k idx r bow) arcs))

;; The arcs paired with the index their centre takes in the layout --
;; n for the first arc stored, n+1 for the next -- and turned back into
;; the order they were given in, which is the order to report them in.
;; cst:adjacency hands the centres out walking the SAME stored list, so
;; the two cannot disagree about which centre belongs to which arc.
(defun cst:arcrows (n arcs / k out a)
  (setq k n out nil)
  (foreach a arcs
    (setq out (cons (cons k a) out)
          k   (1+ k)))
  out)

;;; ----------------------------------------------------------------------
;;;  Is there enough to go on?
;;;
;;;  Two separate failures, and they need separate words because the
;;;  fix is different.  A THIN point has fewer than two dims: it sits
;;;  anywhere on a circle (one dim) or anywhere at all (none), and the
;;;  answer is to measure it twice.  A CUT-OFF point has its two dims
;;;  but they only reach other cut-off points: that island is placed
;;;  perfectly well relative to itself and floats free of everything
;;;  else, and the answer is one dim bridging the two groups.
;;; ----------------------------------------------------------------------

(defun cst:thin (n chart / out i)
  (setq out nil i 0)
  (repeat n
    (if (< (cst:degree i chart) 2) (setq out (cons i out)))
    (setq i (1+ i)))
  (reverse out))

;; The points reachable from A by following dims.
(defun cst:reach (adj / seen frontier nxt i e)
  (setq seen '(0) frontier '(0))
  (while frontier
    (setq nxt nil)
    (foreach i frontier
      (foreach e (nth i adj)
        (if (not (member (car e) seen))
          (setq seen (cons (car e) seen)
                nxt  (cons (car e) nxt)))))
    (setq frontier nxt))
  seen)

(defun cst:cutoff (n adj / seen out i)
  (setq seen (cst:reach adj) out nil i 0)
  (repeat n
    (if (not (member i seen)) (setq out (cons i out)))
    (setq i (1+ i)))
  (reverse out))

;; "A, C and F" -- the way the report names a set of points.
(defun cst:namelist (idx / out n i k)
  (setq out "" n (length idx) i 0)
  (foreach k idx
    (setq out (strcat out
                      (cond ((= i 0) "")
                            ((= i (1- n)) (if (= n 2) " and " ", and "))
                            (t ", "))
                      (cst:letter k))
          i   (1+ i)))
  out)

;;; ----------------------------------------------------------------------
;;;  The starting layout
;;;
;;;  Evenly spaced round the oval inscribed in the space, CLOCKWISE
;;;  FROM THE TOP LEFT.  Top left on an oval is 135 degrees, and
;;;  clockwise means each step SUBTRACTS its share of a full turn --
;;;  the sign that makes A B C D land top-left, top-right,
;;;  bottom-right, bottom-left on a four-point job, which is the order
;;;  a pool's corners are called out in.
;;;
;;;  Coordinates are relative to the space's lower-left corner, so the
;;;  base point is added once, at the moment something is drawn.
;;; ----------------------------------------------------------------------

(defun cst:oval (n w h / a b out i ang)
  (setq a (* 0.5 w) b (* 0.5 h) out nil i 0)
  (repeat n
    (setq ang (- (* 0.75 pi) (/ (* 2.0 pi i) n))
          out (cons (list (+ a (* a (cos ang))) (+ b (* b (sin ang)))) out)
          i   (1+ i)))
  (reverse out))

;; The oval flattened: a different aspect ratio to fall out of, for a
;; shape the round start folds.  It squashes about y = 0 rather than
;; about the oval's own centre, which moves the whole start down the
;; page as well -- harmless, because the solve is translation-blind and
;; the answer is re-placed in the space at the end either way.
(defun cst:squash (pts f)
  (mapcar '(lambda (p) (list (car p) (* f (cadr p)))) pts))

;; The oval scattered.  Pseudo-random but DETERMINISTIC -- the golden
;; angle, not a random number generator -- so the same job run twice
;; gives the same drawing.
(defun cst:shake (pts amt / out i p a)
  (setq out nil i 0)
  (foreach p pts
    (setq a   (* 2.399963229728653 (1+ i))
          out (cons (list (+ (car p) (* amt (cos a)))
                          (+ (cadr p) (* amt (sin a))))
                    out)
          i   (1+ i)))
  (reverse out))

;; Where an arc's centre starts.  A run of THREE or more points has
;; only one centre that can be R from all of them, so the solver finds
;; it wherever it starts.  A run of TWO has two, mirror images across
;; the chord, and nothing in the distances chooses between them -- so
;; the answer to the bow question does.  Clockwise labelling puts the
;; inside of the shape to the RIGHT of the direction of travel, so an
;; arc that bows OUT of the shape has its centre to the right of
;; first-to-last.
(defun cst:arcstart (pts arc / p q r m c half h v side)
  (setq p    (nth (car (cadr arc)) pts)
        q    (nth (last (cadr arc)) pts)
        r    (caddr arc)
        m    (cal:mid p q)
        c    (distance p q)
        half (* 0.5 c)
        ;; a chord longer than the diameter has no such arc at all; the
        ;; centre starts on the chord and the report shows the radius it
        ;; had to settle for
        h    (if (> r half) (sqrt (- (* r r) (* half half))) 0.0)
        v    (cal:unit (cal:v- q p)))
  (if v
    (progn
      (setq side (if (cadddr arc)
                   (list (cadr v) (- (car v)))      ; right of travel
                   (list (- (cadr v)) (car v))))    ; left of travel
      (cal:v+ m (cal:v* side h)))
    (cal:v+ m (list 0.0 r))))

;; A starting layout plus one starting centre per arc, in the order the
;; arcs are stored -- the order cst:adjacency hands the indices out in.
(defun cst:withcentres (pts arcs / out c)
  (setq out nil)
  (foreach c arcs
    (setq out (cons (cst:arcstart pts c) out)))
  (append pts (reverse out)))

;; Put every arc centre back where the SETTLED points say it belongs.
;;
;; cst:arcstart has to guess from the starting oval, which is not the
;; shape -- so the side it picks can be the wrong one, and a centre that
;; starts on the wrong side of its chord stays there: the fit converges
;; happily to a centre that is R from the two ends and nowhere near the
;; middle.  Every failure a random-shape sweep of this solver turned up
;; was that, and only that.
;;
;; Once the sweeps have settled the LABELLED points, the guess is not
;; needed: three points on a circle have exactly one centre, so it is
;; computed rather than chosen.  A two-point arc has no third point and
;; no unique centre, so it keeps the operator's bow answer -- but taken
;; against the settled shape now, not against the oval.
(defun cst:reseed (pts n arcs / out a idx c k)
  (setq out (cal:sublist pts 0 n))
  (foreach a (cst:arcrows n arcs)
    (setq idx (caddr a)
          k   (length idx)
          c   (if (>= k 3)
                (cal:circumcenter (nth (car idx) out)
                                  (nth (nth (/ k 2) idx) out)
                                  (nth (last idx) out))))
    (if (null c) (setq c (cst:arcstart out (cdr a))))
    (setq out (append out (list (cal:2d c)))))
  out)

;;; ----------------------------------------------------------------------
;;;  The solve, stage 1: sweeps, to find the right answer
;;;
;;;  WEIGHTED STRESS MAJORIZATION -- the Guttman transform.  One sweep
;;;  moves every point to the AVERAGE of where each dim touching it
;;;  wants it to be: dim A-C of 168 wants A to sit 168 from wherever C
;;;  currently is, along the line the two currently make.  Averaging is
;;;  what makes the sweep safe -- the total error can never rise -- so
;;;  a sweep can be trusted from any start at all.
;;;
;;;  POOL's pool:relaxn sweeps its constraints ONE AT A TIME instead,
;;;  each pulling its two points a share of the way.  That is right for
;;;  a quad with six constraints on four points.  It is wrong here: a
;;;  26-point job carries up to 325 dims and a point can be in 25 of
;;;  them, so a sequential sweep spends its time undoing what the
;;;  previous constraint just did.
;;;
;;;  What sweeps are BAD at is the last few decimal places.  They
;;;  converge linearly, at a rate set by how loosely the chart ties the
;;;  points together, and a chart that is only just rigid -- a ring with
;;;  a couple of diagonals, which is a very ordinary field sheet -- can
;;;  need many thousands of them.  Stopping at a fixed cap looks like it
;;;  works: every dim comes back close, and the report blames the tape
;;;  whose dim came back least close.  That is the worst failure this
;;;  command could have, because it sends someone out to re-measure a
;;;  tape that was right.  Measured, on ring-plus-two-diagonals charts:
;;;  400 sweeps left a given dim 0.19in out on data that has an exact
;;;  answer, and getting it to a thousandth took 14,440.
;;;
;;;  So sweeps are no longer asked to finish the job.  They are asked
;;;  only to get into the right basin -- which they do in a few dozen,
;;;  and which is the thing they are uniquely good at -- and stage 2
;;;  finishes it.
;;;
;;;  Dims are weighted equally.  A tape reading is a tape reading; there
;;;  is nothing on a field sheet that says one of them is better than
;;;  another, so nothing here pretends there is.
;;; ----------------------------------------------------------------------

;; Where two points sitting exactly on top of each other should push
;; apart.  Any direction will do, but it has to be the SAME direction
;; every run, so it comes off the indices rather than a random number.
(defun cst:spread (i j / a)
  (setq a (* 2.399963229728653 (+ 1.0 (float i) (* 31.0 (float j)))))
  (list (cos a) (sin a)))

;; One sweep.  PTS in, PTS out; nothing is changed in place, so every
;; point moves against the SAME starting layout rather than against
;; whatever the points before it in the list have already become.
(defun cst:sweep (pts adj / out i p num den e q d el u)
  (setq out nil i 0)
  (foreach p pts
    (setq num '(0.0 0.0) den 0.0)
    (foreach e (nth i adj)
      (setq q  (nth (car e) pts)
            d  (cadr e)
            el (distance p q)
            u  (if (> el 1.0e-9)
                 (cal:v* (cal:v- p q) (/ 1.0 el))
                 (cst:spread i (car e)))
            num (cal:v+ num (cal:v+ q (cal:v* u d)))
            den (+ den 1.0)))
    (setq out (cons (if (> den 0.0) (cal:v* num (/ 1.0 den)) p) out)
          i   (1+ i)))
  (reverse out))

;; How far the furthest point moved between two layouts.
(defun cst:maxmove (a b / m i p)
  (setq m 0.0 i 0)
  (foreach p a
    (setq m (max m (distance p (nth i b)))
          i (1+ i)))
  m)

;; Sweep until nothing moves, or until the cap.  Either way this is
;; only the first stage: cst:lm finishes from wherever it stops.
(defun cst:settle (pts adj / k moved new)
  (setq k 0 moved nil)
  (while (and (< k cst:*sweeps*) (or (null moved) (> moved cst:*tol*)))
    (setq new   (cst:sweep pts adj)
          moved (cst:maxmove pts new)
          pts   new
          k     (1+ k)))
  pts)

;; Root-mean-square miss, in drawing units: how far the layout's own
;; distances sit from the ones the operator gave, averaged over
;; everything given -- every cross dim, and every arc radius, since a
;; radius is a distance to the centre and is measured the same way.
;; This is the number the whole solve is minimizing and the one the
;; report leads with.
(defun cst:rms (pts chart arcs n / s c e d a i)
  (setq s 0.0 c 0)
  (foreach e chart
    (setq d (- (distance (nth (cadr e) pts) (nth (caddr e) pts)) (cadddr e))
          s (+ s (* d d))
          c (1+ c)))
  (foreach a (cst:arcrows n arcs)
    (foreach i (caddr a)
      (setq d (- (distance (nth i pts) (nth (car a) pts)) (cadddr a))
            s (+ s (* d d))
            c (1+ c))))
  (if (> c 0) (sqrt (/ s c)) 0.0))

;;; ----------------------------------------------------------------------
;;;  The solve, stage 2: Levenberg-Marquardt, to find it EXACTLY
;;;
;;;  The same problem, written as what it is: least squares over the
;;;  residuals r = (distance drawn) - (distance given).  Each residual
;;;  touches only the four numbers that are its two points' x and y, and
;;;  its slope in each is just the unit vector along the line -- so the
;;;  normal equations are cheap to build and the step is a linear solve.
;;;  Near the answer this doubles the number of correct digits every
;;;  iteration, where a sweep adds a fixed small fraction of one; the
;;;  fourteen thousand sweeps above become seven iterations.
;;;
;;;  It is DAMPED (that is the Marquardt half) and could not work
;;;  otherwise: a constellation is free to slide and to spin, so three
;;;  directions change nothing at all and the undamped normal equations
;;;  are singular no matter how good the dims are.  The damping also
;;;  keeps the step honest far from the answer -- a step that does not
;;;  reduce the total miss is thrown away and retried with more damping,
;;;  so this stage can never make the fit worse than the sweeps left it.
;;;
;;;  Arcs need nothing of their own here.  An arc centre is a point like
;;;  any other and its radius is a distance like any other, so it lands
;;;  in the residual list beside the cross dims and is fitted with them.
;;; ----------------------------------------------------------------------

;; Every distance the layout is held to, as (i j d): one per cross dim,
;; and one per point on an arc holding it R from that arc's centre.
(defun cst:constraints (n chart arcs / out e a i)
  (setq out nil)
  (foreach e chart
    (setq out (cons (list (cadr e) (caddr e) (cadddr e)) out)))
  (foreach a (cst:arcrows n arcs)
    (foreach i (caddr a)
      (setq out (cons (list i (car a) (cadddr a)) out))))
  (reverse out))

;; Sum of squared misses -- the number the fit is minimizing.  (The
;; report leads with the RMS, which is this over the count, rooted.)
(defun cst:sqstress (pts cl / s e d)
  (setq s 0.0)
  (foreach e cl
    (setq d (- (distance (nth (car e) pts) (nth (cadr e) pts)) (caddr e))
          s (+ s (* d d))))
  s)

;; Add V to column K of the sparse row AL.
(defun cst:acc (al k v / p)
  (if (setq p (assoc k al))
    (subst (cons k (+ (cdr p) v)) p al)
    (cons (cons k v) al)))

;; The row of the damped normal equations for one unknown -- the C-th
;; coordinate (0 = x, 1 = y) of point I -- with its right-hand side
;; appended, so a row is (a0 a1 ... a<m-1> rhs).
;;
;; It is built as an (column . value) alist and flattened once at the
;; end.  The row is nearly all zeros: the only unknowns it touches are
;; point I's own two and, for each dim on point I, that neighbour's
;; two.  Accumulating straight into a 52-wide list of zeros would walk
;; it once per entry, which is what would make this too slow to use.
(defun cst:normrow (i c pts adjrow lam m / al rhs e j d p q vx vy len
                                           ux uy g col out hit)
  (setq al nil rhs 0.0 p (nth i pts))
  (foreach e adjrow
    (setq j   (car e)
          d   (cadr e)
          q   (nth j pts)
          vx  (- (car p) (car q))
          vy  (- (cadr p) (cadr q))
          len (sqrt (+ (* vx vx) (* vy vy))))
    ;; two points on top of each other have no direction to differ in;
    ;; the sweeps push them apart, so there is nothing to do here
    (if (> len 1.0e-12)
      (progn
        (setq ux  (/ vx len)
              uy  (/ vy len)
              g   (if (= c 0) ux uy)          ; slope of r in this coord
              rhs (- rhs (* g (- len d))))
        (setq al (cst:acc al (* 2 i)          (* g ux))
              al (cst:acc al (1+ (* 2 i))     (* g uy))
              al (cst:acc al (* 2 j)          (- (* g ux)))
              al (cst:acc al (1+ (* 2 j))     (- (* g uy)))))))
  ;; Marquardt damping, on the diagonal
  (setq col (+ (* 2 i) c)
        hit (assoc col al)
        al  (cst:acc al col (* lam (+ 1.0 (if hit (cdr hit) 0.0)))))
  (setq out nil col (1- m))
  (while (>= col 0)
    (setq hit (assoc col al)
          out (cons (if hit (cdr hit) 0.0) out)
          col (1- col)))
  (append out (list rhs)))

(defun cst:normeq (pts adj lam / rows i m p)
  (setq m (* 2 (length pts)) rows nil i 0)
  (foreach p pts
    (setq rows (cons (cst:normrow i 0 pts (nth i adj) lam m) rows)
          rows (cons (cst:normrow i 1 pts (nth i adj) lam m) rows)
          i    (1+ i)))
  (reverse rows))

(defun cst:butlast (lst) (reverse (cdr (reverse lst))))

(defun cst:dotlists (a b / s)
  (setq s 0.0)
  (while (and a b)
    (setq s (+ s (* (car a) (car b)))
          a (cdr a)
          b (cdr b)))
  s)

;; Solve the system whose augmented rows are ROWS, by Gaussian
;; elimination with partial pivoting.  Returns the solution as a list,
;; or nil when the system is singular (the caller answers that with
;; more damping).
;;
;; Every step walks whole rows with mapcar and drops the column it has
;; just eliminated, so nothing ever indexes into a row: AutoLISP has no
;; arrays, and an nth into a 52-wide row inside a triple loop is the
;; difference between this being usable and not.
(defun cst:linsolve (rows / m k left best bestv rest row f out xs co cs sum)
  (setq m (length rows) k 0 left rows out nil)
  (while (< k m)
    (setq best nil bestv -1.0)
    (foreach row left
      (if (> (abs (car row)) bestv)
        (setq bestv (abs (car row)) best row)))
    (if (< bestv 1.0e-12)
      (setq k m out nil left nil)              ; singular
      (progn
        (setq rest nil)
        (foreach row left
          (if (not (eq row best))
            (progn
              (setq f    (/ (car row) (car best))
                    rest (cons (cdr (mapcar '(lambda (a b) (- a (* f b)))
                                            row best))
                               rest)))))
        (setq out  (cons best out)
              left (reverse rest)
              k    (1+ k)))))
  ;; OUT holds the pivot rows shortest first, which is the LAST unknown
  ;; first; XS then grows in increasing index order, so the leftover
  ;; coefficients of a row pair off with it directly.
  (if out
    (progn
      (setq xs nil)
      (foreach row out
        (setq co  (cdr row)
              cs  (cst:butlast co)
              sum (cst:dotlists cs xs)
              xs  (cons (/ (- (last co) sum) (car row)) xs)))
      xs)))

(defun cst:addstep (pts step / out i p)
  (setq out nil i 0)
  (foreach p pts
    (setq out (cons (list (+ (car p) (nth (* 2 i) step))
                          (+ (cadr p) (nth (1+ (* 2 i)) step)))
                    out)
          i   (1+ i)))
  (reverse out))

;; Polish PTS until the misses stop shrinking.  A step is only kept when
;; it really does reduce the total miss, so this can never hand back a
;; worse layout than it was given.
(defun cst:lm (pts adj cl / lam it s taken pass rows step trial s2)
  (setq lam cst:*lm-lam*
        s   (cst:sqstress pts cl)
        it  0)
  (while (and (< it cst:*lm-iters*) (> s cst:*lm-done*))
    (setq taken nil pass 0)
    (while (and (not taken) (< pass cst:*lm-tries*))
      (setq rows (cst:normeq pts adj lam)
            step (cst:linsolve rows))
      (if step
        (progn
          (setq trial (cst:addstep pts step)
                s2    (cst:sqstress trial cl))
          (if (< s2 s)
            (setq pts   trial
                  s     s2
                  lam   (max (* lam 0.1) cst:*lm-lammin*)
                  taken T)
            (setq lam (* lam 10.0))))
        (setq lam (* lam 10.0)))
      (setq pass (1+ pass)))
    ;; nothing left to win: more damping is only shrinking the step
    (setq it (if taken (1+ it) cst:*lm-iters*)))
  pts)

;; One start taken all the way through.  DIMSFIRST picks between the two
;; orders the stages can run in, and they are BOTH tried because
;; neither wins every job:
;;
;;   nil  arcs in from the off - the centres are seeded off the starting
;;        oval and settle with everything else.
;;   T    the dims settle ALONE first, and the arcs join a shape that
;;        already exists.  An arc centre is only a guess until there is
;;        a shape for it to be the centre of, and a guess that starts on
;;        the wrong side of its chord drags real points after it.
;;
;; Returns n labelled points followed by one centre per arc.
(defun cst:polish (start adj adj0 arcs n cl dimsfirst / p)
  (if dimsfirst
    (setq p (cst:withcentres (cst:settle start adj0) arcs))
    (setq p (cst:settle (cst:withcentres start arcs) adj)))
  (setq p (cst:reseed p n arcs)         ; put the centres where they go
        p (cst:settle p adj))           ; let that settle
  (cst:lm p adj cl))                    ; then land on it exactly

;; The layout that misses by least, over every start and both stagings.
;; The oval alone is a good start and usually the only one that matters;
;; the other two are here because a stress minimum is local and a folded
;; start stays folded.  With no arc declared the two stagings are the
;; same run, so only one of them is made.
(defun cst:solve (n w h chart arcs / adj adj0 cl starts best bestr p r q)
  (setq adj    (cst:adjacency n chart arcs)
        adj0   (if arcs (cst:adjacency n chart nil) adj)
        cl     (cst:constraints n chart arcs)
        starts (list (cst:oval n w h)
                     (cst:squash (cst:oval n w h) cst:*squash*)
                     (cst:shake (cst:oval n w h)
                                (* cst:*shake* (min w h))))
        best   nil
        bestr  nil)
  (foreach q starts
    (setq p (cst:polish q adj adj0 arcs n cl nil)
          r (cst:rms p chart arcs n))
    (if (or (null bestr) (< r bestr))
      (setq best p bestr r))
    (if arcs
      (progn
        (setq p (cst:polish q adj adj0 arcs n cl T)
              r (cst:rms p chart arcs n))
        (if (< r bestr) (setq best p bestr r)))))
  best)

;;; ----------------------------------------------------------------------
;;;  Which way round, which way up
;;;
;;;  Distances say nothing about either, so both are settled against
;;;  what the operator was actually shown.
;;;
;;;  N is the LABELLED point count throughout here, and the layout
;;;  handed in is longer than that -- the arc centres ride along on the
;;;  end.  Every decision below is taken from the first N and then
;;;  applied to all of them: an arc centre can legitimately sit a long
;;;  way outside the space (a shallow radius puts it further out than
;;;  the pool is long), and letting it into the bounding box or the
;;;  chirality test would drag the fit around for a point that is never
;;;  drawn.
;;; ----------------------------------------------------------------------

(defun cst:centroid (pts / sx sy n p)
  (setq sx 0.0 sy 0.0 n (length pts))
  (foreach p pts (setq sx (+ sx (car p)) sy (+ sy (cadr p))))
  (list (/ sx n) (/ sy n)))

(defun cst:centred (pts n / c)
  (setq c (cst:centroid (cal:sublist pts 0 n)))
  (mapcar '(lambda (p) (cal:v- p c)) pts))

;; Twice the signed area of the ring A-B-C-...-A.  Positive is
;; counter-clockwise in a Y-up drawing, negative is clockwise.
(defun cst:area2 (pts / s n i p q)
  (setq s 0.0 n (length pts) i 0)
  (repeat n
    (setq p (nth i pts)
          q (nth (rem (1+ i) n) pts)
          s (+ s (- (* (car p) (cadr q)) (* (car q) (cadr p))))
          i (1+ i)))
  s)

;; A constellation and its mirror image satisfy exactly the same
;; distances, so the solve can land on either.  The operator was shown
;; A, B, C running clockwise; the one that reads clockwise is drawn.
;; (Points that came out collinear have no handedness to fix, and the
;; strict > leaves them alone.)
(defun cst:unmirror (pts n)
  (if (> (cst:area2 (cal:sublist pts 0 n)) 0.0)
    (mapcar '(lambda (p) (list (- (car p)) (cadr p))) pts)
    pts))

(defun cst:spin (pts a / c s)
  (setq c (cos a) s (sin a))
  (mapcar '(lambda (p) (list (- (* (car p) c) (* (cadr p) s))
                             (+ (* (car p) s) (* (cadr p) c))))
          pts))

;; (xlo ylo xhi yhi)
(defun cst:bbox (pts / xl yl xh yh p)
  (setq p  (car pts)
        xl (car p) xh (car p) yl (cadr p) yh (cadr p))
  (foreach p pts
    (setq xl (min xl (car p)) xh (max xh (car p))
          yl (min yl (cadr p)) yh (max yh (cadr p))))
  (list xl yl xh yh))

;; How far outside a W x H space this layout reaches, in drawing units,
;; the two axes added.  Zero means it fits.
(defun cst:overflow (pts w h / bb)
  (setq bb (cst:bbox pts))
  (+ (max 0.0 (- (- (caddr bb) (car bb)) w))
     (max 0.0 (- (- (cadddr bb) (cadr bb)) h))))

;; Sum of squared distances point-for-point between two layouts.
(defun cst:sqdev (pts ref / s i p)
  (setq s 0.0 i 0)
  (foreach p pts
    (setq s (+ s (cal:d2 p (nth i ref)))
          i (1+ i)))
  s)

;; The best angle in [LO HI], sampled STEPS ways.  Two things are
;; wanted of it and they are RANKED, not blended: first it must keep
;; the points inside the space; second, among the angles that do
;; equally well at that, it must land as near as it can to the oval
;; that was previewed, so the letters stay roughly where the operator
;; last saw them.  Returns (angle overflow deviation).
(defun cst:scanrot (pts ref w h n lo hi steps
                    / k a rot lab ov dev best bov bdev)
  (setq k 0 best lo bov nil bdev nil)
  (repeat (1+ steps)
    (setq a   (+ lo (/ (* (- hi lo) k) steps))
          rot (cst:spin pts a)
          lab (cal:sublist rot 0 n)
          ov  (cst:overflow lab w h)
          dev (cst:sqdev lab ref))
    (if (or (null bov)
            (< ov (- bov 1.0e-9))
            (and (< ov (+ bov 1.0e-9)) (< dev bdev)))
      (setq best a bov ov bdev dev))
    (setq k (1+ k)))
  (list best bov bdev))

;; Turn the solved layout to sit in the space: a whole-circle sweep,
;; then a fine pass one coarse step either side of the winner, because
;; a long thin constellation in a tight space can have a window of
;; angles that fit only a fraction of a degree wide.
(defun cst:bestrot (pts ref w h n / best span)
  (setq best (car (cst:scanrot pts ref w h n
                               0.0 (* 2.0 pi) cst:*rot-coarse*))
        span (/ (* 2.0 pi) cst:*rot-coarse*))
  ;; each pass samples one grid spacing either side of the last winner,
  ;; which is where the true best has to be, and its own spacing becomes
  ;; the next window -- so the angle tightens by cst:*rot-fine*/2 a pass
  ;; and the points land on their solved distances rather than a
  ;; degree-grid approximation of them
  (repeat cst:*rot-passes*
    (setq best (car (cst:scanrot pts ref w h n (- best span) (+ best span)
                                 cst:*rot-fine*))
          span (/ (* 2.0 span) cst:*rot-fine*)))
  best)

;; Drop the finished layout into the space, its bounding box centred in
;; the rectangle.  Centring the BOX rather than the centroid is what
;; keeps a lopsided constellation off the edges.
(defun cst:place (pts base w h n / bb dx dy)
  (setq bb (cst:bbox (cal:sublist pts 0 n))
        dx (- (+ (car base) (* 0.5 (- w (- (caddr bb) (car bb)))))
              (car bb))
        dy (- (+ (cadr base) (* 0.5 (- h (- (cadddr bb) (cadr bb)))))
              (cadr bb)))
  (mapcar '(lambda (p) (list (+ (car p) dx) (+ (cadr p) dy))) pts))

;;; ----------------------------------------------------------------------
;;;  Drawing
;;; ----------------------------------------------------------------------

(defun cst:texth (w h) (max 0.5 (* cst:*texth* (min w h))))
(defun cst:dotr  (w h) (max 0.1 (* cst:*dotr*  (min w h))))
(defun cst:dimoff (w h) (* cst:*dimoff* (min w h)))

;; entmake and hand back the ename, so the preview can erase what it
;; drew.  (cal:mtext does the same dance for the same reason -- entmake
;; returns the entity list, not a name.)
(defun cst:made (ok) (if ok (entlast)))

(defun cst:circle (p r lay)
  (entmakex (list '(0 . "CIRCLE") '(100 . "AcDbEntity") (cons 8 lay)
                  '(100 . "AcDbCircle")
                  (list 10 (car p) (cadr p) 0.0) (cons 40 r))))

;; Closed polyline through the points given, in order.  BULGES is one
;; number per vertex or nil for a straight run; a bulge bends the
;; segment LEAVING that vertex, which is where AutoCAD keeps it.
(defun cst:poly (pts bulges lay / dxf i p)
  (setq dxf (list '(0 . "LWPOLYLINE") '(100 . "AcDbEntity") (cons 8 lay)
                  '(100 . "AcDbPolyline") (cons 90 (length pts)) '(70 . 1))
        i   0)
  (foreach p pts
    (setq dxf (append dxf (list (cons 10 (cal:2d p))))
          dxf (if (and bulges (/= 0.0 (nth i bulges)))
                (append dxf (list (cons 42 (nth i bulges))))
                dxf)
          i   (1+ i)))
  (entmakex dxf))

(defun cst:box (base w h lay)
  (cst:poly (list base
                  (cal:v+ base (list w 0.0))
                  (cal:v+ base (list w h))
                  (cal:v+ base (list 0.0 h)))
            nil lay))

;; The bulge that carries one outline segment round an arc: the tangent
;; of a quarter of the angle the segment subtends at the centre, signed
;; the way the segment travels.  A clockwise ring gives a negative
;; angle and so a negative bulge, which is AutoCAD's own convention --
;; the sign falls out of the geometry rather than being asserted.
(defun cst:bulge (p q c)
  (cal:tan (* 0.25 (cal:signed-dang (angle c p) (angle c q)))))

;; One bulge per outline vertex: zero everywhere, except where a
;; declared arc covers a segment between two points that really are
;; NEIGHBOURS in the ring.  A run named out of ring order still
;; constrains the solve -- it is the same circle -- but there is no
;; outline segment for it to bend, so it bends none.
(defun cst:bulges (pts n arcs / out a idx c i j nx)
  (setq out nil)
  (repeat n (setq out (cons 0.0 out)))
  (foreach a (cst:arcrows n arcs)
    (setq c   (nth (car a) pts)
          idx (caddr a)
          i   0)
    (while (< (1+ i) (length idx))
      (setq j  (nth i idx)
            nx (nth (1+ i) idx))
      (if (= nx (rem (1+ j) n))
        (setq out (cst:setnth out j
                    (cst:bulge (nth j pts) (nth nx pts) c))))
      (setq i (1+ i))))
  out)

;; An ALIGNED dimension between P1 and P2, its dimension line through
;; LOC.  Built by entmake, like XYPLOT's, so the layer on it is the
;; layer asked for and DIMLAYER cannot pull it somewhere else.  Group
;; 70 is 1 (aligned) + 32 (the dimension owns a block).
;;
;; There is deliberately NO group 1 text override: the dimension
;; MEASURES the geometry that was drawn.  So a dimension that disagrees
;; with its own line in the report below is a point the dims could not
;; place where the tape said, showing up on the sheet instead of only
;; in a log nobody keeps.
(defun cst:dim (p1 p2 loc lay)
  (entmakex (list '(0 . "DIMENSION") '(100 . "AcDbEntity") (cons 8 lay)
                  '(100 . "AcDbDimension")
                  (list 10 (car loc) (cadr loc) 0.0)
                  (list 11 (car loc) (cadr loc) 0.0)
                  '(70 . 33) '(1 . "")
                  '(100 . "AcDbAlignedDimension")
                  (list 13 (car p1) (cadr p1) 0.0)
                  (list 14 (car p2) (cadr p2) 0.0))))

;; The ab_pt survey block, built if this drawing has never seen one.
;; (ABCDEF's definition, made the same way, so a drawing can hold
;; imports from both commands without a clash.)
(defun cst:ensure-block ( / sty)
  (if (not (tblsearch "BLOCK" cst:*point-block*))
    (progn
      (setq sty (if (tblsearch "STYLE" "STANDARD")
                  "STANDARD"
                  (getvar "TEXTSTYLE")))
      (entmake (list '(0 . "BLOCK") '(100 . "AcDbEntity") '(8 . "0")
                     '(100 . "AcDbBlockBegin")
                     (cons 2 cst:*point-block*) '(70 . 2)
                     '(10 0.0 0.0 0.0)
                     (cons 3 cst:*point-block*) '(1 . "")))
      (entmake '((0 . "POINT") (100 . "AcDbEntity") (8 . "0")
                 (100 . "AcDbPoint") (10 0.0 0.0 0.0)))
      (entmake (list '(0 . "ATTDEF") '(100 . "AcDbEntity") '(8 . "0")
                     '(100 . "AcDbText") '(10 1.0 -2.0 0.0) '(40 . 1.0)
                     '(1 . "0") (cons 7 sty)
                     '(100 . "AcDbAttributeDefinition")
                     '(3 . "Type_Point_Number")
                     (cons 2 cst:*point-tag*) '(70 . 4)))
      (entmake '((0 . "ENDBLK") (100 . "AcDbEntity") (8 . "0")
                 (100 . "AcDbBlockEnd")))
      (princ (strcat "\n  block \"" cst:*point-block*
                     "\" was not in this drawing - created it."))))
  (tblsearch "BLOCK" cst:*point-block*))

(defun cst:insert-pt (pt name th)
  (entmake (list '(0 . "INSERT") '(100 . "AcDbEntity")
                 (cons 8 cst:*point-layer*)
                 '(100 . "AcDbBlockReference") '(66 . 1)
                 (cons 2 cst:*point-block*)
                 (list 10 (car pt) (cadr pt) 0.0)
                 (cons 41 th) (cons 42 th) (cons 43 th)))
  (entmake (list '(0 . "ATTRIB") '(100 . "AcDbEntity")
                 (cons 8 cst:*point-layer*) '(100 . "AcDbText")
                 (list 10 (+ (car pt) th) (- (cadr pt) (* 2.0 th)) 0.0)
                 (cons 40 th) (cons 1 name) '(100 . "AcDbAttribute")
                 (cons 2 cst:*point-tag*) '(70 . 0)))
  (entmake (list '(0 . "SEQEND") '(100 . "AcDbEntity")
                 (cons 8 cst:*point-layer*))))

;;; ----------------------------------------------------------------------
;;;  The preview
;;;
;;;  Drawn before a single dim is asked for, and erased again the moment
;;;  the real positions are known.  It is not a measurement and it is
;;;  not a guess at the answer -- it is the legend, so the operator can
;;;  see which letter is which before naming a pair.
;;;
;;;  NOTHING permanent is drawn until the run finishes.  The space
;;;  rectangle is part of the preview too and gets drawn again at the
;;;  end, so a run that is backed out of or cancelled leaves the drawing
;;;  exactly as it found it.
;;; ----------------------------------------------------------------------

(defun cst:preview (n w h base / pts i p r th lab)
  (cst:unpreview)
  (cal:ensure-layer cst:*space-layer* 8)
  (cal:ensure-layer cst:*guide-layer* 4)
  (setq r   (cst:dotr w h)
        th  (cst:texth w h)
        i   0
        pts (cst:oval n w h)
        cst:*preview* (list (cst:box base w h cst:*space-layer*)))
  (foreach p pts
    (setq p   (cal:v+ base p)
          cst:*preview* (cons (cst:circle p r cst:*guide-layer*)
                              cst:*preview*)
          lab (cst:made (cal:text (list (+ (car p) r) (+ (cadr p) r))
                                  th (cst:letter i) cst:*guide-layer*))
          cst:*preview* (if lab (cons lab cst:*preview*) cst:*preview*)
          i   (1+ i)))
  (princ (strcat "\n  A to " (cst:letter (1- n))
                 " are shown clockwise from the top left, evenly spaced"))
  (princ "\n  round the space.  Where they really go is what the dims say.")
  (princ))

;; Safe to call at any time, including twice: an ename already gone has
;; no entget, and the list is emptied as it is swept.  The guard is not
;; decoration -- entdel TOGGLES, so a second sweep without it would put
;; everything back.
(defun cst:unpreview ( / e)
  (foreach e cst:*preview* (if (and e (entget e)) (entdel e)))
  (setq cst:*preview* nil))

;; Everything made since MARK, in creation order.  Walking forward from
;; a mark rather than collecting enames as they are made is what catches
;; the attribute and the SEQEND of an ab_pt block: those are buffered
;; until the sequence closes and do not reliably hand a name back, and a
;; redraw that missed them would leave the old labels behind.  (XYPLOT's
;; xyp:new-points walks the same way, for the same reason.)
(defun cst:since (mark / e out)
  (setq e (if mark (entnext mark) (entnext)) out nil)
  (while e
    (setq out (cons e out)
          e   (entnext e)))
  (reverse out))

(defun cst:undraw ( / e)
  (foreach e cst:*drawn* (if (and e (entget e)) (entdel e)))
  (setq cst:*drawn* nil))

;;; ----------------------------------------------------------------------
;;;  The questions
;;; ----------------------------------------------------------------------

(defun cst:banner ()
  (princ (strcat "\n\nCONSTELLATION " *constellation-version*
                 " - points placed from the dims between them."))
  (princ "\n  The space is a rectangle of known X and Y that the points")
  (princ "\n  have to sit in; the base point is its lower-left corner.")
  (princ))

;; How many points.  Three is the floor: two points share one dim and
;; neither of them then has the two a placement needs.  Twenty-six is
;; the ceiling because the labels are single letters.
(defun cst:askcount ( / v)
  (initget 6 "Back Undo")
  (setq v (getint (strcat "\nHow many points? [Back] <"
                          (itoa cst:*defcount*) ">: ")))
  (cond ((member v '("Back" "Undo")) 'CAL-BACK)
        ((null v) cst:*defcount*)
        ((or (< v cst:*minpts*) (> v cst:*maxpts*))
         (princ (strcat "\n  Between " (itoa cst:*minpts*) " and "
                        (itoa cst:*maxpts*) " points - they are labelled A to "
                        (cst:letter (1- cst:*maxpts*)) "."))
         (cst:askcount))
        (t v)))

(defun cst:askbase ( / v)
  (initget "Back Undo")
  (setq v (getpoint "\nInsertion base point [Back] <0,0>: "))
  (cond ((member v '("Back" "Undo")) 'CAL-BACK)
        ((null v) '(0.0 0.0))
        (t (cal:2d v))))

;; Every point letter in S, in the order typed.  Anything that is not
;; a letter is a separator and ignored, so "AC", "A-C", "a c" and
;; "A,C" all read the same.  nil when a letter names a point this job
;; does not have, or names one twice -- a wrong letter is a typo to be
;; told about, not a character to be quietly dropped.
(defun cst:letters-in (s n / i c k out bad)
  (setq out nil bad nil i 1)
  (repeat (strlen s)
    (setq c (substr s i 1)
          k (cst:index c))
    (if (not (null k))
      (if (or (>= k n) (member k out))
        (setq bad T)
        (setq out (cons k out))))
    (setq i (1+ i)))
  (if (not bad) (reverse out)))

;; The pair S names, low letter first.  nil unless exactly two points
;; are named.
(defun cst:parsepair (s n / ls)
  (setq ls (cst:letters-in s n))
  (if (= 2 (length ls))
    (list (min (car ls) (cadr ls)) (max (car ls) (cadr ls)))))

;; The first pair still blank, as its name; nil when the chart is full.
(defun cst:nextpair (order chart / found k p)
  (foreach p order
    (if (null found)
      (progn
        (setq k (cst:key (car p) (cadr p)))
        (if (not (assoc k chart)) (setq found k)))))
  found)

;; Which pair to dimension.  Typed, not a keyword list: a 26-point job
;; has 325 pair names and initget cannot carry them, so Back and Done
;; are typed words too and the prompt says so.
(defun cst:askpair (n dflt / s)
  (setq s (cal:trim (getstring (strcat "\n  Pair to dimension <" dflt
                                       "> (B = back, D = done): "))))
  (cond ((= s "") (cst:parsepair dflt n))
        ((cal:back-word-p s) 'CAL-BACK)
        ((member (strcase s) '("D" "DONE")) 'CST-DONE)
        ((cst:parsepair s n))
        (t (princ (strcat "\n    \"" s "\" is not a pair of these points -"
                          " two different letters"))
           (princ (strcat "\n    between A and " (cst:letter (1- n))
                          ", like " (cst:key 0 1) "."))
           (cst:askpair n dflt))))

(defun cst:charthelp (n order top)
  (if top
    (progn
      (princ (strcat "\n\n  Cross dims.  " (itoa n) " points make "
                     (itoa (length order)) " possible pairs and not one of"))
      (princ "\n  them is compulsory - give the ones the sheet carries, in")
      (princ "\n  whatever order they are written down."))
    (princ "\n\n  Cross dims - name the pair whose number was wrong:"))
  (princ "\n    Enter    takes the pair shown, so Enter over and over")
  (princ "\n             walks the whole chart in order")
  (princ "\n    A-C      jumps straight to that pair (AC and a c read too),")
  (princ "\n             and a pair given twice keeps the second answer")
  (princ "\n    D        done, no more dims")
  (princ "\n    B        undo the dim just given")
  (princ (strcat "\n  Every point needs at least two dims before the chart"
                 " will close.")))

(defun cst:saythin (short chart / i d)
  (princ "\n    Not yet - these points cannot be placed:")
  (foreach i short
    (setq d (cst:degree i chart))
    (princ (strcat "\n      " (cst:letter i) " has " (itoa d)
                   (if (= 1 d) " dim" " dims"))))
  (princ "\n    Every point needs two: with one dim a point sits anywhere")
  (princ "\n    on a circle, and with none, anywhere at all."))

(defun cst:saycut (cut)
  (princ (strcat "\n    Not yet - " (cst:namelist cut)
                 (if (= 1 (length cut)) " is" " are")
                 " only dimensioned to each other,"))
  (princ "\n    so that group is placed perfectly well against itself and")
  (princ "\n    floats free of A's.  One dim across the gap ties them")
  (princ "\n    together."))

;;; ----------------------------------------------------------------------
;;;  The arc list
;;; ----------------------------------------------------------------------

(defun cst:archelp (n top)
  (if top
    (progn
      (princ "\n\n  Arcs.  If a run of points lies on ONE radius, say so.")
      (princ "\n  Cross dims say how far apart things are and nothing about")
      (princ "\n  how the wall between them curves, so a radius end can be")
      (princ "\n  measured perfectly and still come out as a flat chord.")
      (princ "\n  An arc pins those points and is drawn as a real arc."))
    (princ "\n\n  Arcs - name the run whose radius was wrong:"))
  (princ "\n  Name the run CLOCKWISE, the way the letters were handed out:")
  (princ "\n    A-C      from A clockwise to C, so A B C")
  (princ "\n    ABC      the same run, spelled out")
  (princ (strcat "\n    " (cst:letter (1- n)) "-B      wraps round the end: "
                 (cst:letter (1- n)) " A B, not B all the way back to "
                 (cst:letter (1- n))))
  (princ "\n    Enter    done, no arcs (or no more)")
  (princ "\n    B        undo the arc just given"))

;; Which points the arc runs through.  Typed, like the pair prompt and
;; for the same reason, so Back and Done are typed words too.
(defun cst:askrun (n / str ls)
  (setq str (cal:trim
              (getstring (strcat "\n  Points on the arc <Enter = done>"
                                 " (B = back): "))))
  (cond ((= str "") 'CST-DONE)
        ((cal:back-word-p str) 'CAL-BACK)
        ((member (strcase str) '("D" "DONE")) 'CST-DONE)
        ((cst:parserun str n))
        (t (princ (strcat "\n    \"" str "\" is not a run of these points"
                          " - two or more different"))
           (princ (strcat "\n    letters between A and "
                          (cst:letter (1- n)) ", like "
                          (cst:letter 0) "-" (cst:letter 2) "."))
           (cst:askrun n))))

;; The arcs.  Returns the list, or CAL-BACK when Back is pressed with
;; nothing in it yet and there is a question behind to go back to.
(defun cst:askarcs (n arcs top / done ls r bow k nm)
  (cst:archelp n top)
  (setq done nil)
  (while (not done)
    (setq ls (cst:askrun n))
    (cond
      ((eq ls 'CAL-BACK)
       (cond
         (arcs
          (setq k    (car (car arcs))
                arcs (cdr arcs))
          (princ (strcat "\n    Stepping back one arc - " k
                         " is off the list again.")))
         (top (setq done T arcs 'CAL-BACK))
         (t (princ "\n    Already at the first arc."))))
      ((eq ls 'CST-DONE) (setq done T))
      (t
       (setq nm (cst:runname ls)
             r  (cal:askdist 'REQ (strcat "  Radius for " nm) nil T))
       (if (not (eq r 'CAL-BACK))
         (progn
           ;; three points on a circle of known R fix its centre
           ;; outright; two leave two centres, mirror images across the
           ;; chord, and only the operator knows which wall this is
           (setq bow (if (= 2 (length ls))
                       (cal:askyn (strcat "  Does " nm
                                          " bow out from the shape?")
                                  "Yes" T)
                       T))
           (if (not (eq bow 'CAL-BACK))
             (progn
               (setq arcs (cst:putarc ls r bow arcs))
               (princ (strcat "\n    " nm " on R" (rtos r)
                              (if bow "" ", bowing in") "   ("
                              (itoa (length arcs))
                              (if (= 1 (length arcs)) " arc)"
                                  " arcs)"))))))))))
  arcs)

;; The cross-dim chart.  Returns the chart, or CAL-BACK when Back is
;; pressed with nothing in it yet.
;;
;; TOP is T on the way through the questions, where Back out of an empty
;; chart means going back a QUESTION, and where a chart that fills up
;; closes itself so the walk needs no final D.  It is nil on a FIX pass,
;; re-entered from "does it look right": there is no earlier question to
;; reach, and a full chart must NOT close itself or there would be no
;; way in to change the number that was wrong.
(defun cst:askchart (n chart arcs top / order done nxt pr v k short cut)
  (setq order (cst:pairs n) done nil)
  (cst:charthelp n order top)
  (while (not done)
    (setq nxt (cst:nextpair order chart))
    (if (and (null nxt) top)
      (progn (princ "\n  Every pair is given.")
             (setq pr 'CST-DONE))
      (setq pr (cst:askpair n (if nxt nxt (cst:key 0 1)))))
    (cond
      ((eq pr 'CAL-BACK)
       (cond
         (chart
          (setq k     (car (car chart))
                chart (cdr chart))
          (princ (strcat "\n    Stepping back one dimension - " k
                         " is blank again.")))
         (top (setq done T chart 'CAL-BACK))
         (t (princ "\n    Already at the first dimension."))))
      ((eq pr 'CST-DONE)
       (setq short (cst:thin n chart)
             cut   (if short nil
                     (cst:cutoff n (cst:adjacency n chart arcs))))
       (cond (short (cst:saythin short chart))
             (cut   (cst:saycut cut))
             (t     (setq done T))))
      (t
       (setq v (cal:askdist 'REQ (strcat "  " (cst:key (car pr) (cadr pr)))
                            nil T))
       (if (not (eq v 'CAL-BACK))
         (progn
           (setq chart (cst:putdim (car pr) (cadr pr) v chart))
           (princ (strcat "\n    " (cst:key (car pr) (cadr pr)) " = "
                          (rtos v) "   (" (itoa (length chart)) " of "
                          (itoa (length order)) " given)")))))))
  chart)

;; The whole chain, with Back.  Returns (w h n base chart arcs outline).
;; The first question offers no Back (STANDARDS section 3), so there is
;; no way out of here but forward or Esc -- and Esc lands in the
;; command's *error* handler, which sweeps the preview and closes the
;; undo group.
(defun cst:ask ( / step w h n base chart arcs outline v)
  (setq step 1 chart nil arcs nil outline T)
  (while (< step 8)
    (cond
      ((= step 1)
       (setq w (cal:askdist 'REQ "Space width (X)" nil nil)
             step 2))
      ((= step 2)
       (setq v (cal:askdist 'REQ "Space height (Y)" nil T))
       (if (eq v 'CAL-BACK) (setq step 1) (setq h v step 3)))
      ((= step 3)
       (setq v (cst:askcount))
       (if (eq v 'CAL-BACK) (setq step 2) (setq n v step 4)))
      ((= step 4)
       (setq v (cst:askbase))
       (if (eq v 'CAL-BACK) (setq step 3) (setq base v step 5)))
      ((= step 5)
       (cst:preview n w h base)
       (setq v (cst:askchart n chart arcs T))
       (if (eq v 'CAL-BACK)
         (progn (cst:unpreview) (setq step 4))
         (setq chart v step 6)))
      ((= step 6)
       (setq v (cst:askarcs n arcs T))
       (if (eq v 'CAL-BACK) (setq step 5) (setq arcs v step 7)))
      ((= step 7)
       (setq v (cal:askyn "Draw the outline through the points in order?"
                          "Yes" T))
       (if (eq v 'CAL-BACK) (setq step 6) (setq outline v step 8)))))
  (list w h n base chart arcs outline))

;;; ----------------------------------------------------------------------
;;;  Placing the dims, and the ring
;;; ----------------------------------------------------------------------

;; Neighbours in the label ring - A-B, B-C ... and the wrap Z-A.
(defun cst:neighbours (i j n)
  (or (= 1 (abs (- i j)))
      (and (= 0 (min i j)) (= (1- n) (max i j)))))

;; One aligned dimension per dim given.  A dim between two points that
;; are NEIGHBOURS in the label ring is a perimeter dim and stands off
;; outside the shape, clear of the points; every other one is a cross
;; dim and runs straight down the chord it measures, which is how a
;; cross dim is drawn on a pool sheet.
(defun cst:drawdims (pts n chart w h / ctr off e p q m v loc)
  (setq ctr (cst:centroid pts)
        off (cst:dimoff w h))
  (foreach e chart
    (setq p   (nth (cadr e) pts)
          q   (nth (caddr e) pts)
          m   (cal:mid p q)
          loc (if (cst:neighbours (cadr e) (caddr e) n)
                (progn
                  (setq v (cal:unit (cal:v- m ctr)))
                  (if v (cal:v+ m (cal:v* v off)) m))
                m))
    (cst:dim p q loc cst:*dim-layer*)))

;; Everything the run puts in the drawing, in one place so that a No to
;; "does it look right" can take it all away again and put the corrected
;; version down.  The layers and the block are made BEFORE the mark:
;; they are not part of the drawing to be swept and a redraw must not
;; keep re-announcing them.
(defun cst:draw (pts n w h base chart arcs outline / mark th i p)
  (cal:ensure-layer cst:*space-layer* 8)
  (cal:ensure-layer cst:*point-layer* 2)
  (cal:ensure-layer cst:*dim-layer* 2)
  (if outline (cal:ensure-layer cst:*outline-layer* 3))
  (cst:ensure-block)
  (setq mark (entlast)
        th   (cst:texth w h)
        i    0)
  (cst:box base w h cst:*space-layer*)
  (foreach p (cal:sublist pts 0 n)
    (cst:insert-pt p (cst:letter i) th)
    (setq i (1+ i)))
  (cst:drawdims pts n chart w h)
  (if outline
    (cst:poly (cal:sublist pts 0 n) (cst:bulges pts n arcs)
              cst:*outline-layer*))
  (setq cst:*drawn* (cst:since mark)))

;; Does the ring A-B-C-...-A cross itself?  Worth saying if it does:
;; the letters were handed out clockwise, so a crossing means the dims
;; put the points in a different order than the sheet named them -
;; usually two letters swapped.
(defun cst:crossing-p (pts / n i j hit a b c d)
  (setq n (length pts) i 0 hit nil)
  (while (and (< i n) (not hit))
    (setq a (nth i pts)
          b (nth (rem (1+ i) n) pts)
          j (1+ i))
    (while (and (< j n) (not hit))
      (setq c (nth j pts)
            d (nth (rem (1+ j) n) pts))
      ;; edges sharing an end always meet; only edges sharing nothing
      ;; can really cross
      (if (and (/= (rem (1+ i) n) j) (/= (rem (1+ j) n) i))
        (if (inters a b c d T) (setq hit T)))
      (setq j (1+ j)))
    (setq i (1+ i)))
  hit)

;;; ----------------------------------------------------------------------
;;;  Which dim is the wrong one
;;;
;;;  Least squares SPREADS a bad tape.  One dim read three inches long
;;;  does not come out three inches wrong -- the fit gives a little on
;;;  every dim that touches those two points, so ten dims each end up a
;;;  bit out and the report stars all ten and names none.  That is the
;;;  arithmetic working correctly and the answer being no use.
;;;
;;;  The test that finds the culprit is to leave the worst dim out and
;;;  solve again.  If everything else then comes into line, that one dim
;;;  was carrying the error by itself.  (ABCDEF makes the same argument
;;;  about dropping its fourth tape.)
;;;
;;;  It is only asked when there is something to explain AND something
;;;  to spare: below the flag nothing is wrong, and a chart with no
;;;  redundancy has no second opinion to offer -- drop a dim there and
;;;  the error simply moves somewhere else.  The answer changes nothing
;;;  that is drawn: the layout on the sheet still honours every dim the
;;;  operator gave.
;;; ----------------------------------------------------------------------

;; The dim this layout misses by most, as (entry miss).
(defun cst:worstdim (pts chart / e d best bestd)
  (setq best nil bestd 0.0)
  (foreach e chart
    (setq d (abs (- (distance (nth (cadr e) pts) (nth (caddr e) pts))
                    (cadddr e))))
    (if (or (null best) (> d bestd)) (setq best e bestd d)))
  (list best bestd))

;; How well the rest of the chart settles without BAD -- nil when it
;; does not settle, or when the chart cannot spare the dim.
(defun cst:culprit (n w h chart arcs bad / rest pts r)
  (setq rest (cst:deldim (car bad) chart))
  (if (and rest
           (null (cst:thin n rest))
           (null (cst:cutoff n (cst:adjacency n rest arcs))))
    (progn
      (setq pts (cst:solve n w h rest arcs)
            r   (max (cadr (cst:worstdim pts rest))
                     (cst:worstarc pts n arcs)))
      (if (< r cst:*flag*) r))))

;;; ----------------------------------------------------------------------
;;;  The report
;;; ----------------------------------------------------------------------

(defun cst:indices (n / out i)
  (setq out nil i 0)
  (repeat n (setq out (cons i out) i (1+ i)))
  (reverse out))

;; One line per dim: what was given, what the drawing came out at, and
;; the difference.  A line starred here is a line to go back and
;; re-measure - which of them, when several are starred, is the
;; leave-one-out test's job above.
(defun cst:report (pts n w h base chart arcs / order p k drawn off)
  (princ (strcat "\n\nCONSTELLATION " *constellation-version*))
  (princ (strcat "\n  Space   " (rtos w) " x " (rtos h)
                 ", base point " (rtos (car base)) "," (rtos (cadr base))))
  (princ (strcat "\n  Points  " (cst:namelist (cst:indices n))))
  (setq order (cst:pairs n))
  (princ (strcat "\n  Dims    " (itoa (length chart)) " given of "
                 (itoa (length order)) " possible"))
  (if arcs
    (princ (strcat "\n  Arcs    " (itoa (length arcs)) " given")))
  (princ (strcat "\n\n  " (cal:pad "pair" 8) (cal:pad "given" 15)
                 (cal:pad "drawn" 15) "off by"))
  (foreach p order
    (setq k (assoc (cst:key (car p) (cadr p)) chart))
    (if k
      (progn
        (setq drawn (distance (nth (cadr k) pts) (nth (caddr k) pts))
              off   (abs (- drawn (cadddr k))))
        (princ (strcat "\n  " (cal:pad (car k) 8)
                       (cal:pad (rtos (cadddr k)) 15)
                       (cal:pad (rtos drawn) 15)
                       (rtos off)
                       (if (> off cst:*flag*) "   **" ""))))))
  (princ))

;; The radius an arc actually came out at (the mean of its members'
;; distances to the fitted centre) and how far the worst of them sits
;; from the R given, as (drawn miss).
(defun cst:arcmeas (pts a / i d s c worst)
  (setq s 0.0 c 0 worst 0.0)
  (foreach i (caddr a)
    (setq d     (distance (nth i pts) (nth (car a) pts))
          s     (+ s d)
          c     (1+ c)
          worst (max worst (abs (- d (cadddr a))))))
  (list (if (> c 0) (/ s c) 0.0) worst))

;; The worst any arc radius came out.
(defun cst:worstarc (pts n arcs / a worst)
  (setq worst 0.0)
  (foreach a (cst:arcrows n arcs)
    (setq worst (max worst (cadr (cst:arcmeas pts a)))))
  worst)

(defun cst:arcreport (pts n arcs / a m)
  (if arcs
    (progn
      (princ (strcat "\n\n  " (cal:pad "arc" 16) (cal:pad "R given" 15)
                     (cal:pad "R drawn" 15) "off by"))
      (foreach a (cst:arcrows n arcs)
        (setq m (cst:arcmeas pts a))
        (princ (strcat "\n  " (cal:pad (cadr a) 16)
                       (cal:pad (rtos (cadddr a)) 15)
                       (cal:pad (rtos (car m)) 15)
                       (rtos (cadr m))
                       (if (> (cadr m) cst:*flag*) "   **" ""))))))
  (princ))

;;; ----------------------------------------------------------------------
;;;  The command
;;; ----------------------------------------------------------------------

(defun c:CONSTELLATION ( / *error* undo-open q w h n base chart arcs
                           outline sol ref ang pts wd worst blame rms
                           over cross happy fix v)
  (defun *error* (msg)
    ;; user settings come back FIRST so nothing below can skip them
    (cal:sysrestore)
    ;; and the legend goes with them: a cancel part way through the
    ;; chart must not leave the starting oval in the drawing
    (cst:unpreview)
    (if undo-open (setq undo-open (cal:undoend)))
    (if (and msg (not (cal:error-cancel-p msg)))
      (princ (strcat "\nCONSTELLATION error: " msg)))
    (princ))
  (cal:syssave (cst:sysvars))
  (setvar "CMDECHO" 0)
  (setq undo-open (cal:undobegin))
  (cst:banner)
  (setq q       (cst:ask)
        w       (nth 0 q)
        h       (nth 1 q)
        n       (nth 2 q)
        base    (nth 3 q)
        chart   (nth 4 q)
        arcs    (nth 5 q)
        outline (nth 6 q))
  ;; the legend has done its job now that the real positions are coming
  (cst:unpreview)
  ;; ---- solve, draw, and ask whether it is right -------------------------
  ;; Round the loop again on a No.  A number typed wrong is the ordinary
  ;; case, not an exception: the operator cannot tell 24'-6" was meant to
  ;; be 24'-9" from the chart, but they can tell at a glance from the
  ;; drawing.  So the drawing IS the check, and it comes away again
  ;; before the corrected one goes down.
  (setq happy nil)
  (while (not happy)
    (princ "\n\n  Working the positions out...")
    ;; the shape the dims and arcs want, then the two things distances
    ;; cannot say: which way round (clockwise, as previewed) and which
    ;; way up (turned to sit in the space, and among the angles that do,
    ;; nearest the oval)
    (setq sol (cst:unmirror
                (cst:centred (cst:solve n w h chart arcs) n) n)
          ref (cst:centred (cst:oval n w h) n)
          ang (cst:bestrot sol ref w h n)
          pts (cst:place (cst:spin sol ang) base w h n))
    (cst:draw pts n w h base chart arcs outline)
    (setq cross (if outline (cst:crossing-p (cal:sublist pts 0 n))))
    (cst:report pts n w h base chart arcs)
    (cst:arcreport pts n arcs)
    (setq wd    (cst:worstdim pts chart)
          worst (max (cadr wd) (cst:worstarc pts n arcs))
          rms   (cst:rms pts chart arcs n)
          over  (cst:overflow (cal:sublist pts 0 n) w h)
          blame (if (> worst cst:*flag*)
                  (cst:culprit n w h chart arcs (car wd))))
    (princ (strcat "\n\n  Worst miss " (rtos worst) ", RMS " (rtos rms)
                   " over " (itoa (length chart))
                   (if (= 1 (length chart)) " dim" " dims")
                   (if arcs
                     (strcat " and " (itoa (length arcs))
                             (if (= 1 (length arcs)) " arc." " arcs."))
                     ".")))
    (if (> worst cst:*flag*)
      (progn
        (princ "\n  ** The starred lines cannot all be true at once.")
        (if blame
          (progn
            (princ (strcat "\n  ** Leave " (car (car wd)) " out and every"
                           " other dim settles to within " (rtos blame)
                           ","))
            (princ (strcat "\n  ** so " (car (car wd)) " is the one to"
                           " re-measure - the rest are only wrong"))
            (princ "\n  ** because the fit shared its error out among them.")
            (princ (strcat "\n  ** Nothing was dropped: the layout drawn"
                           " still honours every dim given.")))
          ;; no ONE reading accounts for the others, and there are two
          ;; ways that happens.  Saying only "re-measure them" would be
          ;; picking one of them without evidence - and the remedy is
          ;; the same either way, so say both and name it.
          (progn
            (princ "\n  ** No single one of them explains the rest, so")
            (princ "\n  ** either more than one reading is out, or the")
            (princ "\n  ** chart does not pin the shape down tightly")
            (princ "\n  ** enough for the fit to be sure which layout the")
            (princ "\n  ** dims meant.  More cross dims settle either."))))
      (princ (strcat "\n  Nothing missed by more than " (rtos cst:*flag*)
                     " - nothing here needs re-measuring.")))
    (if (> over 1.0e-6)
      (progn
        (princ (strcat "\n  ** The constellation runs " (rtos over)
                       " past the space across its two axes."))
        (princ "\n  ** It is drawn centred in the space and overhanging it."))
      (princ "\n  Every point landed inside the space."))
    (if cross
      (progn
        (princ "\n  ** The outline crosses itself, so A, B, C ... is not the")
        (princ "\n  ** order the dims put the points in - two letters are")
        (princ "\n  ** most likely swapped on the sheet.")))
    (princ (strcat "\n  " (itoa n) " points on layer " cst:*point-layer*
                   " as \"" cst:*point-block* "\" blocks, so ABHD and"))
    (princ "\n  CABHD will fit a perimeter through them as they stand.")
    ;; ---- does it look right? -------------------------------------------
    ;; No default that Enter takes by accident would be safe here: the
    ;; whole point of the question is that it be looked at.  Yes is the
    ;; shown default because a run that went well is the common one.
    (if (cal:askyn "\nDoes the drawing look right?" "Yes" nil)
      (setq happy T)
      (progn
        (cst:undraw)
        (setq fix (cal:askkw "What needs changing?" "Dims Arcs Both"
                             "Dims/Arcs/Both" "Dims" nil))
        (if (member fix '("Dims" "Both"))
          (progn
            (setq v (cst:askchart n chart arcs nil))
            (if (not (eq v 'CAL-BACK)) (setq chart v))))
        (if (member fix '("Arcs" "Both"))
          (progn
            (setq v (cst:askarcs n arcs nil))
            (if (not (eq v 'CAL-BACK)) (setq arcs v)))))))
  (setq undo-open (cal:undoend))
  (cal:sysrestore)
  (princ))

;; Print the loaded version.
(defun c:CONSTELLATIONVER ()
  (princ (strcat "\nCONSTELLATION " *constellation-version*
                 " (CONSTELLATION.lsp)"))
  (princ))

(princ (strcat "\nCONSTELLATION.lsp " *constellation-version*
               " loaded.  Type CONSTELLATION to place points from"
               " their cross dims."))
(princ)


;;; ======================================================================
;;; >>> CORNERSTP.lsp
;;; ======================================================================

;;; ======================================================================
;;; CORNERSTP.lsp
;;; ----------------------------------------------------------------------
;;; Corner step layout routine for swimming-pool corners.
;;; Written for AutoCAD 2018 (plain AutoLISP + ActiveX for dim styles).
;;;
;;; LOAD:     APPLOAD this file (or drag it into the drawing window).
;;; COMMAND:  CORNERSTP
;;;
;;; WHAT IT DOES
;;;   Draws a run of parallel corner steps (tread edges) fanning out from
;;;   a pool corner toward the pool.  Step treads (the plan-view spacing
;;;   of each step) are always held exactly; step widths are held to
;;;   within the width tolerance of the wall opening (1/8" by default).
;;;   The step DEPTH, by contrast, is the vertical drop of a step - it is
;;;   only asked for by the optional side profile at the end of the run.
;;;   A BENCH can ride along one of the two walls (inside out only): you
;;;   say which wall, its offset off that wall, and which step it is
;;;   attached to, and every step past that tread runs to the bench's
;;;   front edge instead of the wall it stands in for.
;;;
;;; WORKFLOW
;;;   1.  Select the two walls that form the corner.  Walls may be LINEs
;;;       or straight segments of a POLYLINE.  A corner diagonal
;;;       (chamfer) or a fillet ARC may be included in the same
;;;       selection.  If more than two straight walls are selected you
;;;       are asked to pick the two you mean.
;;;   2.  If the two walls intersect at a point, that intersection is
;;;       the starting point.
;;;   3.  Choose the draw direction [Inside out/Outside in]:
;;;         INSIDE OUT (default) - steps are built from the corner out
;;;         toward the pool from given step treads and step widths.
;;;         OUTSIDE IN - the furthest (outermost) step is placed first
;;;         from its given width, bounded to the provided walls, and
;;;         the remaining steps walk back in toward the corner.
;;;
;;;   INSIDE OUT:
;;;   4a. If a diagonal/arc was selected, you are asked whether step
;;;       treads are measured from the Middle of the diagonal/arc or
;;;       from the True corner.  The true corner is found by extending
;;;       the two walls surrounding the diagonal/arc to their apparent
;;;       intersection.
;;;   4b. If a diagonal was selected you are also asked whether the
;;;       treads run Parallel to the diagonal, or perpendicular to the
;;;       bisector of the TRUE ANGLE the walls make (equal angle from
;;;       both walls).  With no diagonal the true-angle bisector is
;;;       always used.  Step treads are measured from the starting
;;;       point toward the pool, square to the treads, so all steps are
;;;       parallel to each other either way.
;;;   4c. For each step you are prompted for the step tread, then the
;;;       step width:
;;;         - The step tread is ALWAYS held exactly.
;;;         - If the wall opening at that distance is within the width
;;;           tolerance of the requested width, the step is trimmed to
;;;           the walls.
;;;         - Otherwise the requested width is held, centered between
;;;           the two walls so the step runs EQUALLY past (or equally
;;;           short of) both walls, and the step breaks away from the
;;;           walls to hold the given dimensions.
;;;         - Enter at the width prompt fits that one step to the walls.
;;;
;;;   OUTSIDE IN:
;;;   5a. If a diagonal was selected you are asked whether the steps
;;;       run Parallel to the diagonal, or with their endpoints
;;;       Equidistant from the true corner (square to the true-angle
;;;       bisector).  With no diagonal, equidistant is always used.
;;;   5b. You give the width of the furthest (outermost) step.  That
;;;       step is bounded to the provided walls, so its width alone
;;;       places it - it is just the starting point.  Each following
;;;       step asks for a step tread (walking back in toward the
;;;       corner), then a step width, under the same rules as inside
;;;       out.  Drawing stops if the corner is reached.
;;;
;;;   6.  You are asked whether to dimension the steps [Yes/No].  If
;;;       Yes, aligned dimensions are added:
;;;         - Step treads are chained along the bisector out from the
;;;           starting point, in dim style "STANDARD INCHES".
;;;         - Step widths are the full width of each tread edge, placed
;;;           just outside the corner and nested so the wider (deeper)
;;;           steps sit progressively further out, in dim style
;;;           "SIDE STANDARD".
;;;       If a style is missing the current style is used and a note is
;;;       printed.
;;;   7.  Inside out you may add a BENCH along one of the walls
;;;       [Yes/No]: pick the wall it sits against, give its offset off
;;;       that wall (its depth), then the step it is attached to.
;;;       Steps up to that one meet the wall as usual; the bench's
;;;       front edge starts on that tread and runs to the far end of
;;;       its wall, capped there, and every later step is bounded by
;;;       the front edge instead of the wall - a fitted width now runs
;;;       wall to bench.  When dimensioning is on the bench's length
;;;       and offset are dimensioned too.
;;;   8.  Enter at a step tread prompt means no more steps are
;;;       required.  Back at a step tread prompt steps back one step:
;;;       it removes the step just drawn (its lines and its dimensions)
;;;       so a mistyped number does not cost the whole run (Undo, the
;;;       old keyword, is still accepted).  Same repeats the previous
;;;       step tread.  Side (riser) lines are drawn between successive step
;;;       ends whenever the walls do not already close that edge.
;;;   9.  When at least one step was drawn you may add a SIDE PROFILE.
;;;       If Yes, you give the step depths (the vertical drops), top
;;;       step first - one per step PLUS one more for the drop after
;;;       the last tread, so 3 steps take 4 depths.  Enter repeats the
;;;       previous drop, Back (or Undo) steps back.  Then pick the top
;;;       of the first tread: the flight always runs DOWN AND TO THE
;;;       LEFT from there, so there is no side to pick.  See "The side
;;;       profile" below for what is drawn and how it is dimensioned.
;;;     10. Finally, BEAD THE STEPS.  Every tread is beaded - that is the
;;;       assumption - so the only thing asked is which steps carry the
;;;       bead along their side walls: All of them, or Some, given by
;;;       step number.  AUTOBEAD does the work on its own rules (2"
;;;       toward the side you click, onto its Bead Track layer), so
;;;       AUTOBEAD.lsp has to be loaded; when it is not, the run says
;;;       so and finishes without beading.  The beads are their own
;;;       undo group - AutoCAD does not nest them - so one U undoes
;;;       the beads and the next undoes the steps.
;;;
;;; THE SIDE PROFILE
;;;   The flight is drawn as an alternating drop/tread silhouette in
;;;   world X/Y, always descending to the LEFT of the picked top of the
;;;   first tread and ending on the last depth - so the steps rise to
;;;   the right, the way the shop's own elevations read.
;;;   The dims climb with them, up and to the right, on the high side:
;;;     * every depth is a dim of its own, standing the same distance
;;;       right of the corner its drop lands on, so they step out with
;;;       the flight instead of stacking in one chain;
;;;     * the overall depth sits further out again;
;;;     * the treads carry no dims - the depths and the overall say it.
;;;   How far out the fan sits is *CS-PROFILE-DIMGAP* - the gap on top
;;;   of the clearance the geometry needs.  Raise it to open the dims
;;;   out further, lower it to tuck them in.
;;;   Each one is a VERTICAL LINEAR dim bound to the two step corners
;;;   that bracket the drop.  Those corners run diagonally to each
;;;   other, so binding the diagonal (rather than dimensioning the
;;;   riser line) keeps the extension lines hooked to the geometry
;;;   while the dim still reads the drop, not the slope.  The offset
;;;   clears the widest tread in the flight, which is what keeps both
;;;   extension lines running forward, out of the steps.
;;;
;;; OPTIONAL SETTINGS (set these before running the command)
;;;   *CS-WIDTH-TOL*      step width tolerance in drawing units.  When
;;;                       nil (the default) it is 1/8" converted through
;;;                       the drawing's INSUNITS setting.
;;;   *CS-DEPTH-DIMSTYLE* dim style for step-tread dims (also used by
;;;                       the side-profile dims).
;;;   *CS-WIDTH-DIMSTYLE* dim style for step-width dims.
;;;   *CS-DIM-LAYER*      layer for the dimensions.  When nil (the
;;;                       default) the current layer is used.
;;;   *CS-PROFILE-DIMGAP* how far the side profile's dims stand off the
;;;                       flight, on top of the clearance the geometry
;;;                       needs.  nil (the default) is four text
;;;                       heights or three quarters of a tread,
;;;                       whichever is more, so the fan keeps its
;;;                       proportions whether or not the drawing has a
;;;                       dim scale set up.  It also sets how much
;;;                       further out again the overall depth sits.
;;;
;;; NOTES
;;;   - Geometry is assumed to be drawn in plan view.  The routine warns
;;;     when the current UCS is not World, when selected geometry is not
;;;     flat, and when the current layer is off/frozen/locked.
;;;   - Steps are drawn as LINEs on the current layer.
;;;   - DIMSCALE (or the annotation scale for annotative styles) sets
;;;     the dimension size; grab a dimension line to slide it if it
;;;     lands awkwardly.
;;;   - One U / UNDO reverses the whole command; a bead run added at
;;;     the end is its own group, so it takes a U of its own.
;;;   - A form (the Calofin palette / LAZFORM) can pre-answer the
;;;     questions - the step COUNT included, which the prompts only
;;;     ever learn from Enter - by leaving (key . value) pairs in
;;;     *CS-FORM*; see "form answers" below.  Selections and point
;;;     picks are always made by hand.
;;; ======================================================================

;; Settings - only defined if not already set, so the two routines that
;; share them stay in sync no matter which file loads first.
;;; SHARED BUILD: requires CALOFIN-LIB.lsp (load via CALOFIN-LOADER.lsp).
;;; Generic helpers live there under cal: - see STANDARDS.md.
;;;

(if (not (boundp '*cs-width-tol*))      (setq *cs-width-tol* nil))
(if (not (boundp '*cs-dim-layer*))      (setq *cs-dim-layer* nil))
(if (not (boundp '*cs-depth-dimstyle*)) (setq *cs-depth-dimstyle* "STANDARD INCHES"))
(if (not (boundp '*cs-width-dimstyle*)) (setq *cs-width-dimstyle* "SIDE STANDARD"))
;; How far the side profile's dims stand off the flight, on top of the
;; clearance the geometry itself needs.  nil = four text heights, which
;; is what the shop's own elevations read like; raise it to open the
;; fan out further, lower it to tuck the dims in.
(if (not (boundp '*cs-profile-dimgap*)) (setq *cs-profile-dimgap* nil))

(vl-load-com) ; ActiveX is used to set styles (handles names with spaces)

(setq *cs-version* "v3.3") ; printed on load and at command start so a
                           ; stale APPLOADed copy is easy to spot

;;; ------------------------- vector helpers ----------------------------

(defun cs-dot (a b) (+ (* (car a) (car b)) (* (cadr a) (cadr b))))

(defun cs-vec (a b) (list (- (car b) (car a)) (- (cadr b) (cadr a)) 0.0))

(defun cs-add (p v) (list (+ (car p) (car v)) (+ (cadr p) (cadr v)) 0.0))

(defun cs-scl (v s) (list (* (car v) s) (* (cadr v) s) 0.0))

(defun cs-len (v) (sqrt (cs-dot v v)))

(defun cs-unit (v / l)
  (if (> (setq l (cs-len v)) 1e-10) (cs-scl v (/ 1.0 l))))

(defun cs-perp90 (v) (list (- (cadr v)) (car v) 0.0))

(defun cs-mid2 (a b) (list (* 0.5 (+ (car a) (car b)))
                           (* 0.5 (+ (cadr a) (cadr b)))
                           0.0))

;; perpendicular distance from point P to the infinite line through A-B
(defun cs-ptline (p a b / d)
  (setq d (cs-unit (cs-vec a b)))
  (if d
    (abs (- (* (car d) (- (cadr p) (cadr a)))
            (* (cadr d) (- (car p) (car a)))))
    (distance p a)))

;; distance from point P to the SEGMENT A-B
(defun cs-ptseg (p a b / d l2 t2)
  (setq d  (cs-vec a b)
        l2 (cs-dot d d))
  (if (< l2 1e-20)
    (distance p a)
    (progn
      (setq t2 (/ (cs-dot (cs-vec a p) d) l2))
      (cond ((< t2 0.0) (distance p a))
            ((> t2 1.0) (distance p b))
            (T (distance p (cs-add a (cs-scl d t2))))))))

;; how far point P lies beyond the ends of segment A-B (0.0 when on it)
(defun cs-beyond (p a b / d l t2)
  (setq d (cs-vec a b)
        l (cs-len d))
  (if (< l 1e-10)
    (distance p a)
    (progn
      (setq t2 (/ (cs-dot (cs-vec a p) d) (* l l)))
      (cond ((< t2 0.0) (* (- t2) l))
            ((> t2 1.0) (* (- t2 1.0) l))
            (T 0.0)))))

;; endpoint of wall/segment record LN farther from PT
(defun cs-far (ln pt)
  (if (> (distance (car ln) pt) (distance (cadr ln) pt)) (car ln) (cadr ln)))

;; point on a circle: center C, radius R, angle A
(defun cs-arcpt (c r a)
  (list (+ (car c) (* r (cos a))) (+ (cadr c) (* r (sin a))) 0.0))

;; T when angle A lies on the counterclockwise span A1 -> A2
(defun cs-inspan (a a1 a2 / e)
  (setq e (- a2 a1))
  (if (< e 0.0) (setq e (+ e pi pi)))
  (setq a (- a a1))
  (if (< a 0.0) (setq a (+ a pi pi)))
  (<= a (+ e 1e-9)))

;;; --------------------- geometry from entities ------------------------

;; Normalized arc record (center radius startang endang) in WCS, always
;; counterclockwise with endang > startang.  Built from the curve's own
;; start/mid/end points so mirrored arcs and OCS offsets are handled.
(defun cs-arcdata (en / ed c r sp ep mp a1 a2 sw)
  (setq ed (entget en)
        c  (trans (cdr (assoc 10 ed)) en 0)
        r  (cdr (assoc 40 ed))
        sp (vlax-curve-getstartpoint en)
        ep (vlax-curve-getendpoint en)
        mp (vlax-curve-getpointatdist
             en (* 0.5 (vlax-curve-getdistatparam
                         en (vlax-curve-getendparam en))))
        a1 (angle c sp)
        a2 (angle c ep))
  (if (not (cs-inspan (angle c mp) a1 a2))   ; wrong way round
    (setq sw a1 a1 a2 a2 sw))
  (if (< a2 a1) (setq a2 (+ a2 pi pi)))
  (list c r a1 a2))

;; Normalized arc record for a polyline bulge segment P1 -> P2
(defun cs-bulgearc (p1 p2 b / th l r h nrm cen a1 a2)
  (setq th  (* 4.0 (atan b))                  ; signed included angle
        l   (distance p1 p2)
        r   (abs (/ l (* 2.0 (sin (/ th 2.0)))))
        h   (* r (cos (/ (abs th) 2.0)))
        nrm (cs-unit (cs-perp90 (cs-vec p1 p2)))
        cen (cs-add (cs-mid2 p1 p2)
                    (cs-scl nrm (if (> b 0.0) h (- h)))))
  (if (> b 0.0)
    (setq a1 (angle cen p1) a2 (angle cen p2))
    (setq a1 (angle cen p2) a2 (angle cen p1)))
  (if (< a2 a1) (setq a2 (+ a2 pi pi)))
  (list cen r a1 a2))

;; Segments of a POLYLINE as records (p1 p2 bulge ename index).
;; Points are brought to WCS.  Handles LWPOLYLINE and old 2D POLYLINE.
(defun cs-plsegs (en / ed el cl vs bs i m out v1 v2 b sub pr)
  (setq ed (entget en)
        el (cond ((cdr (assoc 38 ed))) (0.0))
        cl (= 1 (logand 1 (cond ((cdr (assoc 70 ed))) (0)))))
  (if (= "LWPOLYLINE" (cdr (assoc 0 ed)))
    (foreach pr ed                              ; walk 10/42 pairs in order
      (cond
        ((= 10 (car pr))
         (setq vs (cons (trans (list (car (cdr pr)) (cadr (cdr pr)) el) en 0) vs)
               bs (cons 0.0 bs)))
        ((= 42 (car pr))
         (if bs (setq bs (cons (cdr pr) (cdr bs)))))))
    (progn                                      ; heavy 2D polyline
      (setq sub (entnext en))
      (while (and sub (= "VERTEX" (cdr (assoc 0 (entget sub)))))
        (setq ed  (entget sub)
              vs  (cons (trans (cdr (assoc 10 ed)) en 0) vs)
              bs  (cons (cond ((cdr (assoc 42 ed))) (0.0)) bs)
              sub (entnext sub)))))
  (setq vs (reverse vs) bs (reverse bs) m (length vs) i 0)
  (while (< i (if cl m (1- m)))
    (setq v1 (nth i vs)
          v2 (nth (rem (1+ i) m) vs)
          b  (nth i bs))
    (if (> (distance v1 v2) 1e-10)
      (setq out (cons (list v1 v2 b en i) out)))
    (setq i (1+ i)))
  (reverse out))

;; nearest record in SEGS to point PT
(defun cs-nearseg (segs pt / best bd d s)
  (foreach s segs
    (setq d (cs-ptseg pt (car s) (cadr s)))
    (if (or (null best) (< d bd)) (setq best s bd d)))
  best)


;;; --------------------------- bead helpers -----------------------------

;; The step numbers typed at a prompt - "1 3 4", "1,3,4" and "1, 3 and 4"
;; all read the same.  Anything that is not a digit separates.
(defun cs-numlist (str / out tok i c)
  (setq out '() tok "" i 0)
  (while (<= i (strlen str))
    (setq c (if (< i (strlen str)) (substr str (1+ i) 1) " "))
    (if (and (>= (ascii c) 48) (<= (ascii c) 57))
      (setq tok (strcat tok c))
      (progn
        (if (/= tok "") (setq out (cons (atoi tok) out)))
        (setq tok "")))
    (setq i (1+ i)))
  (reverse out))

;; The tread line of every step that was committed, as
;; (step-number . ename).  A step's log record carries its entities
;; first and its step number at index 6, and the only LINE among
;; those entities is its tread - any dimension beside it is a DIMENSION.
(defun cs-treadents (log / out rec e ln)
  (setq out '())
  (foreach rec log
    (setq ln nil)
    ;; ...-since lists newest first, and a step draws its tread before
    ;; any side line or dimension, so the LAST line seen is the tread
    (foreach e (car rec)
      (if (and e (entget e)
               (= "LINE" (cdr (assoc 0 (entget e)))))
        (setq ln e)))
    (if ln (setq out (cons (cons (nth 6 rec) ln) out))))
  ;; the log runs newest first, so consing through it already leaves
  ;; the pairs in step order - lowest first, the way they were drawn
  out)

;; The side (riser) lines the run drew: every LINE in the log that is
;; not its step's tread.  CORNERSTP closes a step edge with one only
;; when the walls do not already close it, so most runs have none.
(defun cs-sideents (log / out rec e ln lines)
  (setq out '())
  (foreach rec log
    (setq lines '() ln nil)
    (foreach e (car rec)
      (if (and e (entget e)
               (= "LINE" (cdr (assoc 0 (entget e)))))
        (setq lines (cons e lines) ln e)))    ; ln ends on the tread
    (foreach e lines
      (if (not (eq e ln)) (setq out (cons e out)))))
  out)

;; The step numbers on offer, as "1, 2, 3" - so the numbers prompt can
;; be answered without scrolling back through the run.
(defun cs-numsay (pairs / out pr)
  (setq out "")
  (foreach pr pairs
    (setq out (strcat out (if (= out "") "" ", ") (itoa (car pr)))))
  out)

;; Midpoint (WCS) of a LINE entity.
(defun cs-entmid (e / ed)
  (setq ed (entget e))
  (cs-mid2 (cdr (assoc 10 ed)) (cdr (assoc 11 ed))))

;;; ------------------------- setting helpers ----------------------------

;; 1/8" expressed in the drawing's units (INSUNITS); inches if unitless
(defun cs-autotol ( / iu)
  (setq iu (getvar "INSUNITS"))
  (cond ((= iu 1) 0.125)            ; inches
        ((= iu 2) (/ 0.125 12.0))   ; feet
        ((= iu 4) 3.175)            ; millimeters
        ((= iu 5) 0.3175)           ; centimeters
        ((= iu 6) 0.003175)         ; meters
        (T        0.125)))          ; unitless - assume inches

(defun cs-tolerance ( )
  (if (numberp *cs-width-tol*) *cs-width-tol* (cs-autotol)))

;; annotation text height in drawing units; DIMSCALE is 0 for
;; annotative dim styles, where the annotation scale governs instead
(defun cs-txth ( / h s)
  (setq h (getvar "DIMTXT")
        s (getvar "DIMSCALE"))
  (if (or (null s) (<= s 0.0))
    (setq s (cond ((and (getvar "CANNOSCALEVALUE")
                        (> (getvar "CANNOSCALEVALUE") 0.0))
                   (/ 1.0 (getvar "CANNOSCALEVALUE")))
                  (1.0))))
  (if (and h (> (* h s) 0.0)) (* h s) 1.0))

;;; ------------------------- drawing helpers ---------------------------

(defun cs-mkline (a b)
  (entmake (list '(0 . "LINE")
                 (cons 10 (list (car a) (cadr a) 0.0))
                 (cons 11 (list (car b) (cadr b) 0.0)))))

;; make dimension style NAME current, but only if it exists and is not
;; already current.  Uses ActiveX so style names containing spaces are
;; handled correctly (the -DIMSTYLE command would read a space as ENTER).
(defun cs-setstyle (name / doc)
  (if (and (tblsearch "DIMSTYLE" name)
           (/= (strcase name) (strcase (getvar "DIMSTYLE"))))
    ;; the argument list is required, even for a lambda that takes
    ;; none - without it this is a "too few arguments" error every
    ;; time a style really has to be switched
    (vl-catch-all-apply
      '(lambda ()
         (setq doc (vla-get-activedocument (vlax-get-acad-object)))
         (vla-put-activedimstyle
           doc (vla-item (vla-get-dimstyles doc) name)))
      '())))

;; aligned dimension between A and B in dim style STYLE, dim line
;; passing through THRU.  Points are WCS and are translated to the
;; current UCS for the command.  "_non" defeats running osnap.
(defun cs-dim (style a b thru / oldl)
  (cs-setstyle style)
  (if (and *cs-dim-layer* (cal:layer-usable-p *cs-dim-layer*))
    (progn (setq oldl (getvar "CLAYER"))
           (setvar "CLAYER" *cs-dim-layer*)))
  (command "_.DIMALIGNED" "_non" (trans a 0 1)
                          "_non" (trans b 0 1)
                          "_non" (trans thru 0 1))
  (if oldl (setvar "CLAYER" oldl)))

;; Vertical linear dimension between A and B in dim style STYLE, dim
;; line passing through THRU.  A and B are the real step corners, which
;; run diagonally to each other, so "_V" is forced: the dimension
;; measures the DROP between them while its extension lines still hook
;; the corners themselves.  Cleaner than dimensioning the riser line,
;; which leaves the dim marooned beside the step instead of reading
;; across to it.  Points are WCS.
(defun cs-dimv (style a b thru / oldl)
  (cs-setstyle style)
  (if (and *cs-dim-layer* (cal:layer-usable-p *cs-dim-layer*))
    (progn (setq oldl (getvar "CLAYER"))
           (setvar "CLAYER" *cs-dim-layer*)))
  (command "_.DIMLINEAR" "_non" (trans a 0 1)
                         "_non" (trans b 0 1)
                         "_V"
                         "_non" (trans thru 0 1))
  (if oldl (setvar "CLAYER" oldl)))

;; Draw the side (riser) line A-B unless it is degenerate or both points
;; already lie along the same wall (the wall provides that edge).
(defun cs-conn (a b w1 w2)
  (if (and a b (> (distance a b) 1e-8)
           (not (and (< (cs-ptline a (car w1) (cadr w1)) 1e-6)
                     (< (cs-ptline b (car w1) (cadr w1)) 1e-6)))
           (not (and (< (cs-ptline a (car w2) (cadr w2)) 1e-6)
                     (< (cs-ptline b (car w2) (cadr w2)) 1e-6))))
    (cs-mkline a b)))

;; entities created since MARK (nil = since the drawing was empty)
(defun cs-since (mark / e out)
  (setq e (if mark (entnext mark) (entnext)))
  (while e (setq out (cons e out) e (entnext e)))
  out)

;; Resolve a step's endpoints from the requested width WID (nil = fit
;; to the walls), the wall hits H1/H2 with opening NAT, the position P
;; on the measuring ray, and the tread direction PERP.  Returns the
;; list (e1 e2), or nil when the step must be skipped.  A width within
;; TOL of the wall opening is trimmed to the walls; any other width is
;; held, centered on the wall opening so the step runs equally past (or
;; equally short of) both walls.
(defun cs-resolve (wid nat h1 h2 p perp n tol / u cen e1 e2)
  (cond
    ;; Enter on width -> fit this step to the walls
    ((null wid)
     (if nat
       (progn
         (princ (strcat "\n  Step " (itoa n) ": fitted to walls, width = "
                        (rtos nat) "."))
         (list h1 h2))
       (progn
         (princ (strcat "\n  Step " (itoa n)
                        ": cannot reach both walls here - step skipped."))
         nil)))
    ;; requested width within tolerance of the wall opening -> trim
    ((and nat (<= (abs (- nat wid)) tol))
     (princ (strcat "\n  Step " (itoa n) ": wall opening " (rtos nat)
                    " is within " (rtos tol) " of " (rtos wid)
                    " - fitted to walls."))
     (list h1 h2))
    ;; otherwise hold the exact width; the step breaks from the walls
    (T
     (if nat
       (setq u   (cs-unit (cs-vec h2 h1))
             cen (cs-mid2 h1 h2)
             e1  (cs-add cen (cs-scl u (* 0.5 wid)))
             e2  (cs-add cen (cs-scl u (* -0.5 wid))))
       ;; no wall opening here - fall back to the measuring ray
       (setq e1 (cs-add p (cs-scl perp (* 0.5 wid)))
             e2 (cs-add p (cs-scl perp (* -0.5 wid)))))
     (princ (strcat "\n  Step " (itoa n) ": width " (rtos wid) " held"
                    (if nat (strcat " (wall opening " (rtos nat) ")") "")
                    " - step breaks from the walls."))
     (list e1 e2))))

;;; --------------------------- form answers -----------------------------
;;;
;;;  A form - the Calofin palette, or LAZFORM - can answer some or all
;;;  of CORNERSTP's questions before the run starts.  It leaves them in
;;;  *cs-form* as (key . value) pairs and the question sites look there
;;;  first, so a filled-in sheet drives the whole run and a half-filled
;;;  one simply shortens it.
;;;
;;;  Three states, and the difference between the last two IS the
;;;  feature:
;;;
;;;    key absent      the form did not answer it  -> ask, as usual
;;;    (key . nil)     what Enter means there      -> taken, no prompt
;;;    (key . 24.0)    the form answered it        -> 24.0, no prompt
;;;
;;;  (assoc key ...) tells those apart; (cdr (assoc ...)) alone cannot.
;;;
;;;  THE KEYS.  steps is the STEP COUNT - the one answer the prompts
;;;  never ask for directly: when it is known the tread loop stops
;;;  itself after that many steps instead of waiting for Enter.
;;;  tread1..treadN and width1..widthN feed the per-step prompts (a
;;;  width of nil = fit to the walls, what Enter means there);
;;;  depth1..depthN and depthafter feed the side profile's depths.
;;;  direction, measure, treadmode, dims, bench, benchoffset,
;;;  benchstep, outerwidth, profile and bead answer the named
;;;  questions; a keyword is checked against the live prompt's own
;;;  list and falls through to the prompt when it does not fit.
;;;  Selections and point picks are never form-answered.
;;;
;;;  AN ANSWER IS REMOVED AS IT IS USED.  Not marked used - removed.
;;;  Otherwise Back deadlocks: step back onto a form-answered question,
;;;  it answers itself instantly and walks forward again, and there is
;;;  no key the user can press to get out.  The store is cleared on
;;;  both exits from the command, so nothing leaks into the next run.

(setq *cs-form* nil)

;; Did the form answer KEY at all?  This is the absent/nil distinction
;; that (cdr (assoc ...)) throws away.
(defun cs-fhas (key) (if (assoc key *cs-form*) t nil))

;; The form's answer for KEY, removed from the store as it is read.
(defun cs-ftake (key / p)
  (setq p (assoc key *cs-form*))
  (setq *cs-form* (vl-remove p *cs-form*))
  (cdr p))

(defun cs-fclear () (setq *cs-form* nil))

;; The form's numeric answer for KEY, spent as it is read: the number
;; as a REAL (the way getdist hands one back), nil for anything else.
(defun cs-fnum (key / v)
  (setq v (cs-ftake key))
  (if (numberp v) (* 1.0 v)))

;; The key of a numbered question: (cs-fnkey "tread" 3) -> tread3.
(defun cs-fnkey (stem i) (read (strcat stem (itoa i))))

;; V as the question would spell it, or nil when the question does not
;; accept it at all: an answer the live prompt does not offer falls
;; through to the prompt instead of being handed on to fail later, and
;; the canonical SPELLING comes back, not the caller's, so downstream
;; (= key "Outside") tests keep working.
(defun cs-fkword (v kws / i n c w out)
  (setq i 1 n (strlen kws) w "" v (strcase v))
  (while (<= i (1+ n))
    (setq c (if (<= i n) (substr kws i 1) " "))
    (if (= c " ")
        (progn
          (if (and (/= w "") (= (strcase w) v)) (setq out w))
          (setq w ""))
        (setq w (strcat w c)))
    (setq i (1+ i)))
  out)

;; The form's keyword answer for KEY against the live list KWS: the
;; canonical keyword, DFLT when the form said nil (what Enter means at
;; every keyword prompt here), or nil when the form did not answer -
;; or answered a word the prompt does not offer - so the caller asks
;; as always.
(defun cs-fkw (key kws dflt / v)
  (if (cs-fhas key)
    (progn
      (setq v (cs-ftake key))
      (cond ((null v) dflt)
            ((and (= (type v) 'STR) (setq v (cs-fkword v kws))) v)))))

;; Run CORNERSTP with a form's answers already in hand.  Nothing
;; happens here that the direct path misses: a caller may equally set
;; *cs-form* itself and call c:CORNERSTP, which is what the tests do.
(defun cs-run-with-answers (answers)
  (setq *cs-form* answers)
  (c:CORNERSTP)
  (cs-fclear)
  (princ))

;;; --------------------------- main command ----------------------------

(defun c:CORNERSTP ( / *error* cs-popstep undoflag ss i en ed et zf
                       straights arcrecs lines diag arcr cand o1 o2
                       score best j k tmp w1 w2 corner ang c r a1 a2
                       mid key start d1 d2 bis perp reflen tol txth
                       dist n drawn dep wid p h1 h2 nat e1 e2 bey
                       prevL prevR dimflag w offd oldce oldstyle oldlu
                       outflag stopf op1 pprev tout tprev lastdep
                       slog mark svdist svl svr svp svt svn s
                       bsides btreads bnums bside bdir bss pr be
                       bnw bno bnk bnsd bnrm bnf bnpe bact bu1 bu2
                       bns bnfar bnff bnl
                       tlist tvals tds drops pd ix ppt pw
                       px py totr totd cnrs ca cb pfo pgap fsteps fkey)

  (defun *error* (msg)
    (cs-fclear)                     ; both exits clear the form store
    (if undoflag (command-s "_.UNDO" "_End"))
    (if oldstyle (cs-setstyle oldstyle))
    (if oldce (setvar "CMDECHO" oldce))
    (if oldlu (setvar "LUNITS" oldlu))
    (redraw)
    (if (not (wcmatch (strcase msg) "*BREAK*,*CANCEL*,*QUIT*,*EXIT*"))
      (princ (strcat "\nCORNERSTP: " msg)))
    (princ))

  ;; remove the most recently drawn step and roll the state back
  (defun cs-popstep ( / rec e)
    (cond
      ((null slog) (princ "\n  Already at the first step.") nil)
      ((and outflag (= 1 (length slog)))
       (princ (strcat "\n  The outermost step sets the layout - restart"
                      " the command to change its width."))
       nil)
      (T
       (setq rec (car slog))
       (foreach e (car rec) (if (and e (entget e)) (entdel e)))
       (setq dist  (nth 1 rec)
             prevL (nth 2 rec)
             prevR (nth 3 rec)
             pprev (nth 4 rec)
             tprev (nth 5 rec)   ; outside-in walks from here again
             n     (nth 6 rec)
             drawn (1- drawn)
             slog  (cdr slog)
             tlist (cdr tlist))
       (redraw)                  ; clear the erased step from the screen
       (princ "\n  Stepping back one step.")
       T)))

  ;; ---- 0. environment checks ------------------------------------------
  (princ (strcat "\nCORNERSTP " *cs-version*))
  ;; the form's step COUNT, spent here once for the whole run: when it
  ;; is known the tread loop stops itself after that many steps
  (if (cs-fhas 'steps)
    (progn
      (setq fsteps (cs-ftake 'steps))
      (if (not (and (numberp fsteps) (> fsteps 0))) (setq fsteps nil))))
  (setq tol  (cs-tolerance)
        txth (cs-txth))
  ;; Read distances architectural-style for the whole command: a bare
  ;; number is drawing units (inches in an inch-based drawing) and
  ;; feet-inch entry like 1'4 works whatever LUNITS was set to.
  (setq oldlu (getvar "LUNITS"))
  (setvar "LUNITS" 4)
  (if (not (equal (trans '(0.0 0.0 1.0) 1 0 T) '(0.0 0.0 1.0) 1e-8))
    (princ (strcat "\nWARNING: the current UCS is not parallel to the"
                   " World XY plane - results may be skewed."))
    (if (not (equal (trans '(0.0 0.0 0.0) 1 0) '(0.0 0.0 0.0) 1e-8))
      (princ "\nNote: a shifted/rotated UCS is in use; dimensions are placed to match.")))
  (if (not (cal:layer-usable-p (getvar "CLAYER")))
    (princ (strcat "\nWARNING: the current layer (" (getvar "CLAYER")
                   ") is off, frozen or locked - new steps may not"
                   " appear.")))
  (if (zerop (getvar "INSUNITS"))
    (princ (strcat "\nNote: drawing units are unitless; the width"
                   " tolerance is taken as " (rtos tol) ".")))

  ;; ---- 1. selection ---------------------------------------------------
  (princ "\nSelect the two walls forming the corner ")
  (princ "(a corner diagonal or fillet arc may be included):")
  (setq ss (ssget '((0 . "LINE,ARC,LWPOLYLINE,POLYLINE"))))
  (if (null ss)
    (progn (princ "\nNothing selected.") (exit)))

  (setq i 0)
  (repeat (sslength ss)
    (setq en (ssname ss i)
          ed (entget en)
          et (cdr (assoc 0 ed))
          i  (1+ i))
    (cond
      ((= et "LINE")
       (if (> (abs (- (caddr (cdr (assoc 10 ed)))
                      (caddr (cdr (assoc 11 ed))))) 1e-6)
         (setq zf T))
       (setq straights (cons (list (cdr (assoc 10 ed)) (cdr (assoc 11 ed))
                                   0.0 en nil)
                             straights)))
      ((= et "ARC")
       (setq arcrecs (cons (cs-arcdata en) arcrecs)))
      (T                                        ; polyline: take segments
       (foreach s (cs-plsegs en)
         (if (equal 0.0 (caddr s) 1e-9)
           (setq straights (cons s straights))
           (setq arcrecs (cons (cs-bulgearc (car s) (cadr s) (caddr s))
                               arcrecs)))))))
  (setq straights (reverse straights))
  (if zf
    (princ (strcat "\nWARNING: a selected line is not flat (its ends"
                   " differ in Z) - it is used as seen in plan.")))

  ;; drop duplicates of the same wall
  (setq tmp nil)
  (foreach s straights
    (if (not (vl-some '(lambda (q)
                         (or (and (equal (car s) (car q) 1e-8)
                                  (equal (cadr s) (cadr q) 1e-8))
                             (and (equal (car s) (cadr q) 1e-8)
                                  (equal (cadr s) (car q) 1e-8))))
                      tmp))
      (setq tmp (cons s tmp))))
  (setq straights (reverse tmp))

  ;; ---- 2. sort out walls / diagonal / fillet --------------------------
  (cond
    ((< (length straights) 2)
     (princ "\nSelect at least two straight walls forming the corner.")
     (exit))

    ;; two walls, optionally with a fillet arc
    ((= (length straights) 2)
     (setq lines straights
           arcr  (car arcrecs)))

    ;; three walls: the diagonal is the one whose ends sit closest to
    ;; the other two
    ((= (length straights) 3)
     (setq best 1e99 j 0 k 0)
     (repeat 3
       (setq cand  (nth k straights)
             o1    (nth (rem (+ k 1) 3) straights)
             o2    (nth (rem (+ k 2) 3) straights)
             score (+ (min (cs-ptline (car cand)  (car o1) (cadr o1))
                           (cs-ptline (car cand)  (car o2) (cadr o2)))
                      (min (cs-ptline (cadr cand) (car o1) (cadr o1))
                           (cs-ptline (cadr cand) (car o2) (cadr o2)))))
       (if (< score best) (setq best score j k))
       (setq k (1+ k)))
     (setq diag  (nth j straights)
           lines (list (nth (rem (+ j 1) 3) straights)
                       (nth (rem (+ j 2) 3) straights))))

    ;; more than three: too many to guess - let the user point them out
    (T
     (princ (strcat "\n" (itoa (length straights))
                    " straight walls were selected."))
     (while (null w1)
       (setq tmp (getpoint "\nPick the FIRST wall of the corner: "))
       (if (null tmp) (progn (princ "\nNothing picked.") (exit)))
       (setq w1 (cs-nearseg straights (trans tmp 1 0))))
     (while (null w2)
       (setq tmp (getpoint "\nPick the SECOND wall of the corner: "))
       (if (null tmp) (progn (princ "\nNothing picked.") (exit)))
       (setq w2 (cs-nearseg straights (trans tmp 1 0)))
       (if (equal w1 w2) (progn (princ "\nThat is the same wall.")
                                (setq w2 nil))))
     (setq lines (list w1 w2))
     ;; a straight segment sitting between the two picked walls on the
     ;; same polyline is the chamfer; otherwise look for a fillet arc
     (foreach s straights
       (if (and (null diag)
                (not (equal s w1)) (not (equal s w2))
                (nth 4 s) (nth 4 w1) (nth 4 w2)
                (eq (nth 3 s) (nth 3 w1)) (eq (nth 3 s) (nth 3 w2))
                (= 2 (abs (- (nth 4 w1) (nth 4 w2))))
                (= (nth 4 s) (/ (+ (nth 4 w1) (nth 4 w2)) 2)))
         (setq diag s)))
     (setq arcr (if diag nil (car arcrecs)))))

  (setq w1 (car lines)
        w2 (cadr lines))

  ;; ---- 3. true corner = apparent intersection of the walls -----------
  (setq corner (inters (car w1) (cadr w1) (car w2) (cadr w2) nil))
  (if (null corner)
    (progn (princ "\nThe two walls are parallel - no corner found.")
           (exit)))
  (setq ang (abs (- (angle (car w1) (cadr w1)) (angle (car w2) (cadr w2)))))
  (while (> ang pi) (setq ang (- ang pi)))
  (if (or (< ang 0.0175) (> ang (- pi 0.0175)))
    (princ (strcat "\nWARNING: the two walls are nearly parallel; the"
                   " corner is "
                   (rtos (distance corner (cs-mid2 (car w1) (cadr w1))))
                   " away - check the selection.")))

  ;; show what was classified so a wrong guess is obvious
  (foreach s lines (if (nth 3 s) (redraw (nth 3 s) 3)))
  (if (and diag (nth 3 diag)) (redraw (nth 3 diag) 3))
  (princ (strcat "\nUsing two walls"
                 (cond (diag " plus a corner diagonal")
                       (arcr " plus a fillet arc")
                       (T ""))
                 "."))

  ;; ---- 4. middle of the diagonal / fillet ----------------------------
  (if arcr
    (setq c  (car arcr)
          r  (cadr arcr)
          a1 (caddr arcr)
          a2 (cadddr arcr)))
  (cond
    (diag (setq mid (cs-mid2 (car diag) (cadr diag))))
    (arcr (setq mid (cs-arcpt c r (* 0.5 (+ a1 a2))))))

  ;; ---- 5. draw direction ----------------------------------------------
  ;; the form answers first; when it does not, the bracket is exactly
  ;; the keyword list (STANDARDS section 1 rule 1) and the explanation
  ;; lives in the question text
  (if (null (setq key (cs-fkw 'direction "Inside Outside" "Inside")))
    (progn
      (initget "Inside Outside")
      (setq key (getkword "\nDraw steps from the inside out, or the outside in? [Inside/Outside] <Inside>: "))))
  (setq outflag (= key "Outside"))

  ;; ---- 5a. starting point (inside out only) ---------------------------
  (if (and mid (not outflag))
    (progn
      (if (null (setq key (cs-fkw 'measure "Middle True" "Middle")))
        (progn
          (initget "Middle True")
          (setq key (getkword
            "\nMeasure step treads from the middle of the diagonal, or the true corner? [Middle/True] <Middle>: "))))
      (setq start (if (= key "True") corner mid)))
    (setq start corner))

  ;; ---- 6. tread orientation / measuring direction toward the pool ----
  ;; BIS  = direction the step treads are measured along
  ;; PERP = direction the step edges run (treads are drawn along PERP)
  (setq d1  (cs-unit (cs-vec corner (cs-far w1 corner)))
        d2  (cs-unit (cs-vec corner (cs-far w2 corner)))
        bis (cs-unit (mapcar '+ d1 d2)))
  (if (null bis)
    (progn (princ "\nThe walls are collinear - cannot find a step direction.")
           (exit)))
  (if (and mid (< (cs-dot bis (cs-vec corner mid)) 0.0))
    (setq bis (cs-scl bis -1.0)))
  (if diag
    (progn
      ;; one key answers whichever pair this run offers; a word the
      ;; live prompt does not list falls through to the prompt
      (if (null (setq key (cs-fkw 'treadmode
                                  (if outflag "Parallel Equidistant"
                                              "Parallel True")
                                  "Parallel")))
        (if outflag
          (progn
            (initget "Parallel Equidistant")
            (setq key (getkword (strcat
              "\nSteps parallel to the diagonal, or equidistant"
              " from the true corner? [Parallel/Equidistant] <Parallel>: "))))
          (progn
            (initget "Parallel True")
            (setq key (getkword
              "\nTreads parallel to the diagonal, or at the true angle? [Parallel/True] <Parallel>: ")))))
      (if (not (member key '("True" "Equidistant")))
        (progn
          ;; treads parallel to the diagonal; step treads measured square to it
          (setq perp (cs-unit (cs-vec (car diag) (cadr diag)))
                bis  (cs-perp90 perp))
          (if (< (cs-dot bis (cs-vec corner mid)) 0.0)
            (setq bis (cs-scl bis -1.0)))))))
  (if (null perp)
    ;; treads perpendicular to the true-angle (equal-angle) bisector
    (setq perp (cs-unit (cs-perp90 bis))))

  (if outflag
    (princ (strcat "\nOutermost step is bounded to the walls; drawing"
                   " back in toward the corner (direction "
                   (angtos (angle '(0.0 0.0 0.0) bis)) ")."))
    (princ (strcat "\nMeasuring from "
                   (if (equal start corner 1e-9)
                     "the true corner"
                     "the middle of the diagonal/arc")
                   " toward the pool (direction "
                   (angtos (angle '(0.0 0.0 0.0) bis)) ").")))

  ;; preview the measuring axis and the tread direction
  (setq reflen (max (distance corner (cs-far w1 corner))
                    (distance corner (cs-far w2 corner))))
  (grdraw (trans start 0 1)
          (trans (cs-add start (cs-scl bis reflen)) 0 1) 4 0)
  (grdraw (trans (cs-add start (cs-scl perp (* 0.25 reflen))) 0 1)
          (trans (cs-add start (cs-scl perp (* -0.25 reflen))) 0 1) 2 0)

  ;; previous edge ends, used to close the step sides (inside out only -
  ;; outside-in steps start out wall-bounded)
  (if (not outflag)
    (progn
      (cond
        (diag (setq prevL (car diag) prevR (cadr diag)))
        (arcr (setq prevL (cs-arcpt c r a1) prevR (cs-arcpt c r a2)))
        (T    (setq prevL corner prevR corner)))
      (if (> (cs-dot (cs-vec start prevL) perp)
             (cs-dot (cs-vec start prevR) perp))
        (setq tmp prevL prevL prevR prevR tmp))))

  ;; ---- 7. dimension the steps? ---------------------------------------
  (if (null (setq fkey (cs-fkw 'dims "Yes No" "Yes")))
    (progn
      (initget "Yes No")
      (setq fkey (getkword "\nDimension the steps? [Yes/No] <Yes>: "))))
  (setq dimflag (/= "No" fkey))
  (if dimflag
    (progn
      (setq oldstyle (getvar "DIMSTYLE")) ; restored when the command ends
      (if (not (tblsearch "DIMSTYLE" *cs-depth-dimstyle*))
        (princ (strcat "\nNote: dim style \"" *cs-depth-dimstyle*
                       "\" not found - step treads use the current style.")))
      (if (not (tblsearch "DIMSTYLE" *cs-width-dimstyle*))
        (princ (strcat "\nNote: dim style \"" *cs-width-dimstyle*
                       "\" not found - step widths use the current style.")))
      (if (and *cs-dim-layer* (not (cal:layer-usable-p *cs-dim-layer*)))
        (princ (strcat "\nNote: dim layer \"" *cs-dim-layer*
                       "\" is missing or not drawable - using the"
                       " current layer.")))))

  ;; ---- 7b. a bench along one wall? (inside out only) ------------------
  ;; The bench stands in for a stretch of its wall: steps up to the
  ;; attachment tread meet the wall, the bench's front edge starts on
  ;; that tread, and every later step is bounded by the front edge
  ;; instead.  Outside in walks toward the corner without knowing its
  ;; step count in advance, so the bench is an inside-out feature.
  (if (not outflag)
    (progn
      (if (null (setq fkey (cs-fkw 'bench "Yes No" "No")))
        (progn
          (initget "Yes No")
          (setq fkey (getkword "\nAdd a bench along a wall? [Yes/No] <No>: "))))
      (if (= "Yes" fkey)
        (progn
          (setq tmp (getpoint "\nPick the wall the bench sits against: "))
          (if (null tmp)
            (princ "\nNo wall picked - no bench added.")
            (progn
              (setq tmp  (trans tmp 1 0)
                    bnsd (if (<= (cs-ptseg tmp (car w1) (cadr w1))
                                 (cs-ptseg tmp (car w2) (cadr w2)))
                           1 2)
                    bnw  (if (= bnsd 1) w1 w2))
              ;; its offset and step number can come off the form; both
              ;; prompts refuse Enter, so nil falls back to the keyboard
              (if (cs-fhas 'benchoffset) (setq bno (cs-fnum 'benchoffset)))
              (if (not (numberp bno))
                (progn
                  (initget 7)
                  (setq bno (getdist "\nBench offset off the wall (its depth): "))))
              (if (cs-fhas 'benchstep) (setq bnk (cs-ftake 'benchstep)))
              (if (not (= (type bnk) 'INT))
                (progn
                  (initget 7)
                  (setq bnk (getint (strcat "\nWhich step is the bench attached"
                                            " to (it ends on that tread): ")))))
              ;; the front edge: the bench's wall shifted into the pool
              (setq bnrm (cs-unit (cs-perp90 (cs-vec (car bnw) (cadr bnw)))))
              (if (< (cs-dot bnrm bis) 0.0) (setq bnrm (cs-scl bnrm -1.0)))
              (setq bnf  (list (cs-add (car bnw) (cs-scl bnrm bno))
                               (cs-add (cadr bnw) (cs-scl bnrm bno)))
                    ;; which end of a normalized step that wall bounds
                    ;; (1 = the E1 end, 2 = the E2 end)
                    bnpe (if (> (cs-dot (if (= bnsd 1) d1 d2) perp) 0.0)
                           2 1))
              (princ (strcat "\n  Bench: " (rtos bno) " off that wall;"
                             " steps past step " (itoa bnk)
                             " run to its front edge."))))))))

  ;; ---- 8. prompt for each step and draw it ----------------------------
  (command "_.UNDO" "_Begin")
  (setq undoflag T dist 0.0 n 1 drawn 0
        oldce (getvar "CMDECHO"))
  (setvar "CMDECHO" 0)                    ; quiet the dimstyle/dim commands

  (if outflag

    ;; ========== OUTSIDE IN: outermost step first, then walk in ==========
    (progn
      (if (cs-fhas 'outerwidth)
        (setq wid (cs-fnum 'outerwidth))
        (progn
          (initget 6)
          (setq wid (getdist "\nWidth of the furthest (outermost) step: "))))
      (if (null wid)
        (princ "\nNo width given - nothing drawn.")
        (progn
          ;; the wall opening grows linearly with distance from the
          ;; corner, so the opening at distance 1 fixes where a step of
          ;; the given width must sit to be bounded by both walls
          (setq p   (cs-add corner bis)
                h1  (inters p (cs-add p perp) (car w1) (cadr w1) nil)
                h2  (inters p (cs-add p perp) (car w2) (cadr w2) nil)
                op1 (if (and h1 h2) (distance h1 h2)))
          (if (or (null op1) (<= op1 1e-10))
            (princ "\nCannot measure the wall opening - nothing drawn.")
            (progn
              (setq tout (/ wid op1)   ; outermost step's ray distance
                    wid  nil)          ; the first step fits the walls
              (while (and (not stopf) tout)
                (setq mark  (entlast)
                      svdist dist svl prevL svr prevR svp pprev
                      svt   tprev svn n)
                (setq p   (cs-add corner (cs-scl bis tout))
                      h1  (inters p (cs-add p perp) (car w1) (cadr w1) nil)
                      h2  (inters p (cs-add p perp) (car w2) (cadr w2) nil)
                      nat (if (and h1 h2) (distance h1 h2))
                      bey (if (and h1 h2)
                            (max (cs-beyond h1 (car w1) (cadr w1))
                                 (cs-beyond h2 (car w2) (cadr w2)))
                            0.0)
                      tmp (cs-resolve wid nat h1 h2 p perp n tol)
                      e1  (car tmp)
                      e2  (cadr tmp))
                (if (> bey 1e-6)
                  (princ (strcat "\n    (note: the wall had to be extended "
                                 (rtos bey) " to meet this step)")))
                (if (and mid (< (cs-dot (cs-vec corner p)
                                        (cs-vec corner mid))
                                (cs-dot (cs-vec corner mid)
                                        (cs-vec corner mid))))
                  (princ (strcat "\n    (note: this step is inside the"
                                 " diagonal/fillet region)")))
                (if (and e1 e2)
                  (progn
                    ;; keep a consistent left/right orientation
                    (if (> (cs-dot (cs-vec corner e1) perp)
                           (cs-dot (cs-vec corner e2) perp))
                      (setq tmp e1 e1 e2 e2 tmp))
                    (cs-mkline e1 e2)          ; the step (tread) edge
                    (cs-conn prevL e1 w1 w2)   ; side lines where the walls
                    (cs-conn prevR e2 w1 w2)   ; do not already close them
                    (setq w (distance e1 e2))
                    (if dimflag
                      (progn
                        (if (null offd)
                          (setq offd (max (* 2.0 txth) (* 0.2 w))))
                        ;; step width: nested just outside the corner
                        (cs-dim *cs-width-dimstyle* e1 e2
                                (cs-add corner
                                        (cs-scl bis
                                                (- (+ (* 0.5 w)
                                                      (* 1.5 txth))))))
                        ;; step tread: chain link back out to the
                        ;; previous (next-further-out) tread
                        (if pprev
                          (cs-dim *cs-depth-dimstyle* p pprev
                                  (cs-add (cs-mid2 p pprev)
                                          (cs-scl perp offd))))))
                    (setq prevL e1 prevR e2 pprev p tprev tout
                          drawn (1+ drawn)
                          slog  (cons (list (cs-since mark) svdist svl svr
                                            svp svt svn)
                                      slog)
                          tlist (cons tout tlist))))
                ;; next step inward: step tread, then width - same rules as
                ;; inside out (a held width breaks from the walls)
                (if (not stopf)
                  (progn
                    (setq n (1+ n) dep 'RETRY)
                    (while (eq dep 'RETRY)
                      (cond
                        ;; the form gave the step COUNT: past it the
                        ;; run stops itself - the auto-done no prompt
                        ;; ever offered
                        ((and fsteps (> n fsteps)) (setq dep nil))
                        ;; this step's tread from the form, spent as
                        ;; it is read - a Back onto it re-asks at the
                        ;; keyboard
                        ((cs-fhas (cs-fnkey "tread" n))
                         (setq dep (cs-fnum (cs-fnkey "tread" n))))
                        (T
                         ;; Undo is the old keyword, kept as a hidden synonym
                         (initget 6 (if lastdep "Back Same Undo" "Back Undo"))
                         (setq dep (getdist (strcat "\nStep " (itoa n)
                                     " - step tread (going in) ["
                                     (if lastdep "Back/Same" "Back")
                                     "] <Enter = done>: ")))
                         (if (= (type dep) 'STR)
                           (cond
                             ((or (= dep "Back") (= dep "Undo"))
                              (cs-popstep)
                              (setq dep 'RETRY))
                             ((= dep "Same")
                              (if lastdep
                                (setq dep lastdep)
                                (progn (princ "\n  No previous step tread.")
                                       (setq dep 'RETRY))))
                             (T (setq dep 'RETRY)))))))
                    (cond
                      ((null dep) (setq tout nil)) ; done
                      ((<= (setq tout (- tprev dep)) 1e-8)
                       (princ (strcat "\nReached the corner - no room"
                                      " for another step; stopping."))
                       (setq stopf T))
                      (T
                       (setq lastdep dep)
                       (if (cs-fhas (cs-fnkey "width" n))
                         ;; nil = fit to the walls, what Enter means
                         (setq wid (cs-fnum (cs-fnkey "width" n)))
                         (progn
                           (initget 6)
                           (setq wid (getdist (strcat "\nStep " (itoa n)
                             " - step width <Enter = fit to walls>: ")))))))))))))))

    ;; ========== INSIDE OUT: from the corner out toward the pool =========
    (while
      (progn
        (setq dep 'RETRY)
        (while (eq dep 'RETRY)
          (cond
            ;; the form gave the step COUNT: past it the run stops
            ;; itself - the auto-done no prompt ever offered
            ((and fsteps (> n fsteps)) (setq dep nil))
            ;; this step's tread from the form, spent as it is read -
            ;; a Back onto it re-asks at the keyboard
            ((cs-fhas (cs-fnkey "tread" n))
             (setq dep (cs-fnum (cs-fnkey "tread" n))))
            (T
             ;; Undo is the old keyword, kept as a hidden synonym
             (initget 6 (if lastdep "Back Same Undo" "Back Undo"))
             (setq dep (getdist (strcat "\nStep " (itoa n) " - step tread ["
                                        (if lastdep "Back/Same" "Back")
                                        "] <Enter = done>: ")))
             (if (= (type dep) 'STR)
               (cond
                 ((or (= dep "Back") (= dep "Undo")) (cs-popstep) (setq dep 'RETRY))
                 ((= dep "Same")
                  (if lastdep
                    (setq dep lastdep)
                    (progn (princ "\n  No previous step tread.") (setq dep 'RETRY))))
                 (T (setq dep 'RETRY)))))))
        dep)
      (setq mark  (entlast)
            svdist dist svl prevL svr prevR svp pprev svt tprev svn n
            lastdep dep)
      (if (cs-fhas (cs-fnkey "width" n))
        ;; the form's width, nil = fit to the walls (what Enter means)
        (setq wid (cs-fnum (cs-fnkey "width" n)))
        (progn
          (initget 6)
          (setq wid (getdist (strcat "\nStep " (itoa n)
                                     " - step width <Enter = fit to walls>: ")))))
      (setq dist (+ dist dep)                       ; step tread held exactly
            p    (cs-add start (cs-scl bis dist))
            ;; past the bench tread the bench's front edge stands in
            ;; for the wall it rides along
            bact (and bnf (> n bnk))
            bu1  (if (and bact (= bnsd 1)) bnf w1)
            bu2  (if (and bact (= bnsd 2)) bnf w2)
            h1   (inters p (cs-add p perp) (car bu1) (cadr bu1) nil)
            h2   (inters p (cs-add p perp) (car bu2) (cadr bu2) nil)
            nat  (if (and h1 h2) (distance h1 h2))  ; wall opening here
            bey  (if (and h1 h2)
                   (max (cs-beyond h1 (car bu1) (cadr bu1))
                        (cs-beyond h2 (car bu2) (cadr bu2)))
                   0.0)
            tmp  (cs-resolve wid nat h1 h2 p perp n tol)
            e1   (car tmp)
            e2   (cadr tmp))
      (if (> bey 1e-6)
        (princ (strcat "\n    (note: the wall had to be extended "
                       (rtos bey) " to meet this step)")))
      (if (and e1 e2)
        (progn
          ;; keep a consistent left/right orientation for the side lines
          (if (> (cs-dot (cs-vec start e1) perp)
                 (cs-dot (cs-vec start e2) perp))
            (setq tmp e1 e1 e2 e2 tmp))
          (cs-mkline e1 e2)          ; the step (tread) edge
          ;; side lines where the walls do not already close the step;
          ;; past the bench tread its front edge closes the bench side
          (if (not (and bact (= bnpe 1))) (cs-conn prevL e1 w1 w2))
          (if (not (and bact (= bnpe 2))) (cs-conn prevR e2 w1 w2))
          (if dimflag
            (progn
              (setq w (distance e1 e2))
              ;; fix the tread chain's side offset once, off the bisector
              (if (null offd) (setq offd (max (* 2.0 txth) (* 0.2 w))))
              ;; step tread: link of a chain along the bisector, from the
              ;; previous tread crossing (p - bis*dep) to this one (p)
              (cs-dim *cs-depth-dimstyle*
                      (cs-add p (cs-scl bis (- dep))) p
                      (cs-add (cs-add p (cs-scl bis (* -0.5 dep)))
                              (cs-scl perp offd)))
              ;; step width: full tread edge, placed just outside the
              ;; corner and nested by half the tread's own width so the
              ;; wider (deeper) steps stack progressively further out
              (cs-dim *cs-width-dimstyle*
                      e1 e2
                      (cs-add corner
                              (cs-scl bis (- (+ (* 0.5 w) (* 1.5 txth))))))))
          (setq prevL e1 prevR e2 pprev p drawn (1+ drawn)
                slog (cons (list (cs-since mark) svdist svl svr svp svt svn)
                           slog)
                tlist (cons dist tlist))))
      (setq n (1+ n))))

  ;; ---- 8b. the bench ---------------------------------------------------
  ;; Drawn once the treads exist: the front edge starts where the
  ;; attachment tread crosses it, runs to the far end of its wall and
  ;; is capped there; the attachment tread itself closes the near end.
  (if bnf
    (progn
      (foreach pr (cs-treadents slog)
        (if (= (car pr) bnk) (setq bnl (cdr pr))))
      (cond
        ((null bnl)
         (princ (strcat "\nOnly " (itoa drawn) " step(s) landed - step "
                        (itoa bnk) " does not exist, so no bench was"
                        " drawn.")))
        ((progn
           (setq ed  (entget bnl)
                 bns (inters (cdr (assoc 10 ed)) (cdr (assoc 11 ed))
                             (car bnf) (cadr bnf) nil))
           (null bns))
         (princ (strcat "\nStep " (itoa bnk) " runs parallel to the"
                        " bench's front edge - no bench drawn.")))
        (T
         (setq bnfar (cs-far bnw corner)
               bnff  (cs-add bnfar (cs-scl bnrm bno)))
         (cs-mkline bns bnff)             ; the front edge
         (cs-mkline bnff bnfar)           ; the cap at the wall's far end
         (if dimflag
           (progn
             ;; its length, placed behind the wall
             (cs-dim *cs-width-dimstyle* bns bnff
                     (cs-add (cs-mid2 bns bnff)
                             (cs-scl bnrm (- (+ bno (* 2.0 txth))))))
             ;; its offset off the wall, just past the cap
             (cs-dim *cs-depth-dimstyle* bnfar bnff
                     (cs-add (cs-mid2 bnfar bnff)
                             (cs-scl (cs-unit (cs-vec corner bnfar))
                                     (* 2.0 txth))))))
         (princ (strcat "\nBench drawn: " (rtos (distance bns bnff))
                        " along the wall, " (rtos bno)
                        " off it, ending on step " (itoa bnk) "."))))))

  ;; ---- 9. optional side profile ---------------------------------------
  ;; Drawn while the UNDO group is still open and before the entry dim
  ;; style is restored - the profile places its own dims.
  (if (> drawn 0)
    (progn
      (if (null (setq fkey (cs-fkw 'profile "Yes No" "Yes")))
        (progn
          (initget "Yes No")
          (setq fkey (getkword "\nAdd a side profile? [Yes/No] <Yes>: "))))
      (if (/= "No" fkey)
        (progn
          ;; treads, top step first: sort the axis distances ascending
          ;; (outside-in entered them outermost first) and take the
          ;; first value, then each successive difference
          (setq tvals (vl-sort tlist '<) tds nil pd 0.0)
          (foreach s tvals
            (if (> (- s pd) 1e-6) (setq tds (cons (- s pd) tds)))
            (setq pd s))
          (setq tds (reverse tds))
          (if (null tds)
            (princ "\nNo usable tread spacing - side profile skipped.")
            (progn
              ;; ask the depths, top step first, with Back support:
              ;; one per step PLUS one more for the drop after the
              ;; last tread, so 3 steps take 4 depths
              (setq drops nil ix 0)
              (while (<= ix (length tds))
                (setq pd 'RETRY)
                (while (eq pd 'RETRY)
                  ;; depth1..depthN and depthafter can come off the
                  ;; form, spent as they are read; nil reads as Enter,
                  ;; which the first depth refuses - that one falls
                  ;; back to the keyboard on the next pass, key spent
                  (setq fkey (if (= ix (length tds))
                               'depthafter
                               (cs-fnkey "depth" (1+ ix))))
                  (if (cs-fhas fkey)
                    (progn
                      (setq pd (cs-fnum fkey))
                      (if (null pd)
                        (setq pd (if (zerop ix) 'RETRY (car drops)))))
                    (progn
                      (if (zerop ix)
                        (progn
                          ;; Back/Undo hidden here: typing them only gets
                          ;; the already-at-the-first-step feedback
                          (initget 7 "Back Undo")
                          (setq pd (getdist "\nStep 1 - step depth (the drop): ")))
                        (progn
                          ;; Undo is the old keyword, kept as a hidden synonym
                          (initget 6 "Back Undo")
                          (setq pd (getdist (strcat
                                      (if (= ix (length tds))
                                        "\nDepth after the last tread [Back] <"
                                        (strcat "\nStep " (itoa (1+ ix))
                                                " - step depth [Back] <"))
                                      (rtos (car drops)) ">: ")))))
                      (cond
                        ((= (type pd) 'STR)             ; Back or Undo
                         (if (zerop ix)
                           (princ "\n  Already at the first step.")
                           (progn (setq drops (cdr drops) ix (1- ix))
                                  (princ "\n  Stepping back one step.")))
                         (setq pd 'RETRY))
                        ((null pd) (setq pd (car drops))))))) ; Enter = previous
                (setq drops (cons pd drops) ix (1+ ix)))
              (setq drops (reverse drops))
              ;; Place the profile.  It always runs DOWN AND TO THE
              ;; LEFT from the pick, so there is no side to ask about.
              (setq ppt (getpoint (strcat "\nPick the top of the first"
                                          " tread for the side profile: ")))
              (if (null ppt)
                (princ "\nNo point picked - side profile skipped.")
                (progn
                  ;; The alternating drop/tread silhouette in world
                  ;; X/Y, keeping the corner down its high side at
                  ;; every level: the pick, then the foot of each
                  ;; drop.  Those corners are what the dims bind to.
                  (setq totd (apply '+ drops)
                        totr (apply '+ tds)
                        pw   (trans ppt 1 0)
                        px   (car pw)
                        py   (cadr pw)
                        ix   0
                        cnrs (list (list px py 0.0)))
                  (foreach s tds
                    (setq pd (nth ix drops))
                    (cs-mkline (list px py 0.0) (list px (- py pd) 0.0))
                    (setq py   (- py pd)
                          cnrs (cons (list px py 0.0) cnrs))
                    ;; the tread runs left, and carries no dim of its
                    ;; own - the depths and the overall depth say it all
                    (cs-mkline (list px py 0.0) (list (- px s) py 0.0))
                    (setq px (- px s) ix (1+ ix)))
                  ;; the last depth: the drop after the last tread
                  (setq pd (nth ix drops))
                  (cs-mkline (list px py 0.0) (list px (- py pd) 0.0))
                  (setq py   (- py pd)
                        cnrs (reverse (cons (list px py 0.0) cnrs)))
                  (if dimflag
                    (progn
                      ;; Every depth dim stands the same distance right of
                      ;; the corner its drop lands on, so the dims climb up
                      ;; and to the right with the steps instead of stacking
                      ;; in one chain.  Clearing the widest tread is what
                      ;; keeps BOTH extension lines running forward, out of
                      ;; the flight; the gap on top of that is what makes
                      ;; the fan readable, and *cs-profile-dimgap* sets it.
                      ;; four text heights, or three quarters of a tread -
                      ;; whichever is more, so the fan keeps its proportions
                      ;; whether or not the drawing has a dim scale set up
                      (setq pgap (cond ((numberp *cs-profile-dimgap*)
                                        *cs-profile-dimgap*)
                                       ((max (* 4.0 txth)
                                             (* 0.75 (apply 'max tds)))))
                            pfo  (+ (apply 'max tds) pgap)
                            ix   1)
                      (while (< ix (length cnrs))
                        (setq ca (nth (1- ix) cnrs)
                              cb (nth ix cnrs))
                        (cs-dimv *cs-depth-dimstyle* ca cb
                                 (list (+ (car cb) pfo)
                                       (* 0.5 (+ (cadr ca) (cadr cb)))
                                       0.0))
                        (setq ix (1+ ix)))
                      ;; the overall depth, further out again - the
                      ;; whole diagonal, top corner to bottom corner
                      (cs-dimv *cs-depth-dimstyle*
                               (car cnrs) (last cnrs)
                               (list (+ (car pw) pfo pgap)
                                     (- (cadr pw) (* 0.5 totd)) 0.0))))
                  (princ (strcat "\nSide profile drawn: "
                                 (itoa (length tds))
                                 " step(s), " (itoa (length drops))
                                 " depths, down to the left; total run "
                                 (rtos totr) ", overall depth "
                                 (rtos totd) "."))))))))))

  ;; ---- 10. done --------------------------------------------------------
  (if (zerop drawn)
    (princ "\nNo steps drawn.")
    (princ (strcat "\n" (itoa drawn)
                   " step(s) drawn - step treads held exactly.")))
  (foreach s lines (if (nth 3 s) (redraw (nth 3 s) 4)))
  (if (and diag (nth 3 diag)) (redraw (nth 3 diag) 4))
  (redraw)
  (if oldstyle (cs-setstyle oldstyle))   ; back to the entry dim style
  (command "_.UNDO" "_End")
  (if oldce (setvar "CMDECHO" oldce))
  (if oldlu (setvar "LUNITS" oldlu))
  (setq undoflag nil)

  ;; ---- 11. bead the steps -----------------------------------------------
  ;; AUTOBEAD does the beading, on its own rules and in its own undo
  ;; group - which is why this sits outside ours: AutoCAD does not nest
  ;; undo groups, so one U undoes the beads and the next undoes the
  ;; steps.  Every tread is beaded; the only question left is which
  ;; steps carry the bead along their side walls, and that is answered
  ;; by step number here instead of by clicking each one.
  (if (> drawn 0)
    (if (not (boundp 'autobead-build))
      (princ (strcat "\nAUTOBEAD is not loaded - APPLOAD AUTOBEAD.lsp"
                     " if you want these steps beaded."))
      (progn
        (if (null (setq fkey (cs-fkw 'bead "Yes No" "Yes")))
          (progn
            (initget "Yes No")
            (setq fkey (getkword "\nBead the steps? [Yes/No] <Yes>: "))))
        (if (/= "No" fkey)
          (progn
            (setq btreads (cs-treadents slog)
                  bsides  (cs-sideents slog)
                  bnums   nil)
            (if (null btreads)
              (princ "\nNo tread lines to bead.")
              (progn
                ;; every tread is beaded - the side walls are the question
                (initget "All Some")
                (setq bside (cond ((getkword (strcat "\nWhich steps have"
                                                     " beaded side walls?"
                                                     " [All/Some] <All>: ")))
                                  ("All")))
                (if (= bside "Some")
                  (progn
                    (princ (strcat "\n  Steps drawn: "
                                   (cs-numsay btreads)))
                    (setq bnums (cs-numlist
                                  (getstring T (strcat "\nStep numbers with"
                                                       " beaded sides: "))))
                    (setq bnums (vl-remove-if-not
                                  '(lambda (k) (assoc k btreads)) bnums))
                    (if (null bnums)
                      (progn
                        (princ (strcat "\n  No step numbers recognized -"
                                       " beading every side wall full"
                                       " length."))
                        (setq bside "All")))))
                (setq bdir (getpoint "\nClick the side to bead toward: "))
                (if (null bdir)
                  (princ "\nNo direction picked - nothing beaded.")
                  (progn
                    ;; the treads, anything the run drew for its walls,
                    ;; and the lines it came off: the pool lines of this
                    ;; pocket, which is what AUTOBEAD beads
                    (setq bss (ssadd))
                    (foreach pr btreads (ssadd (cdr pr) bss))
                    (foreach be bsides
                      (if (and be (entget be)) (ssadd be bss)))
                    (setq i 0)
                    (while (< i (sslength ss))
                      (ssadd (ssname ss i) bss)
                      (setq i (1+ i)))
                    (autobead-ensure-layer *autobead-layer*)
                    (autobead-build
                      bss bdir
                      (= bside "Some")
                      (if (= bside "Some")
                        (mapcar '(lambda (k)
                                   (cs-entmid (cdr (assoc k btreads))))
                                bnums)
                        nil)))))))))))
  (cs-fclear)                       ; both exits clear the form store
  (princ))

;;; --------------------------- tutorial ---------------------------------

(defun cs-tut-pause ( )
  (princ "\n      --- press Enter to continue ---")
  (getstring)
  (princ))

(defun cs-tut-text (pt h s)
  (entmake (list '(0 . "TEXT")
                 (cons 10 (list (car pt) (cadr pt) 0.0))
                 (cons 40 h)
                 (cons 1 s))))

;; Walkthrough for new users: pages of what CORNERSTP does and checks,
;; then a live demonstration drawn step by step with the same geometry
;; code the real command uses.
(defun c:TUTORIALCORNERSTP ( / *error* undoflag oldce oldstyle org w1 w2
                               bis perp txth dist p h1 h2 nat tmp e1 e2
                               prevL prevR w offd n pt lst dep wid)
  (defun *error* (msg)
    (if undoflag (command-s "_.UNDO" "_End"))
    (if oldstyle (cs-setstyle oldstyle))
    (if oldce (setvar "CMDECHO" oldce))
    (princ))

  (princ (strcat "\n================ CORNERSTP TUTORIAL " *cs-version*
                 " ================"))
  (princ "\nCORNERSTP draws parallel corner steps fanning out of a pool")
  (princ "\ncorner toward the pool.  Step treads are always held exactly;")
  (princ "\nstep widths are held to within 1/8\" of the wall opening -")
  (princ "\ncloser than that and the step trims to the walls, further and")
  (princ "\nit holds your width and BREAKS from the walls, running equally")
  (princ "\npast both sides.")
  (cs-tut-pause)
  (princ "\nWHAT YOU SELECT")
  (princ "\n  - the two walls of the corner (LINEs or polyline segments)")
  (princ "\n  - optionally a chamfer diagonal or a fillet arc with them")
  (princ "\n  - more than two straight walls: it asks you to pick the two")
  (princ "\nTHE PROMPTS, IN ORDER")
  (princ "\n  1. Draw steps [Inside out/Outside in]")
  (princ "\n     Inside out: corner outward - each step asks step tread,")
  (princ "\n       then width (Enter fits the step to the walls).")
  (princ "\n     Outside in: the width of the furthest step places it")
  (princ "\n       wall-to-wall, then tread/width pairs walk back in.")
  (princ "\n  2. With a diagonal/arc: measure from its Middle or the True")
  (princ "\n     corner, and treads Parallel to the diagonal or square to")
  (princ "\n     the true-angle bisector.")
  (princ "\n  3. Dimension the steps? [Yes/No]")
  (princ "\n  4. Add a bench along a wall? [Yes/No] (inside out) - pick")
  (princ "\n     the wall it sits against, give its offset off that wall,")
  (princ "\n     then the step it is attached to.  Steps past that tread")
  (princ "\n     are bounded by the bench's front edge instead of the")
  (princ "\n     wall; the bench ends on that tread and runs out to the")
  (princ "\n     far end of its wall.")
  (princ "\n  5. Add a side profile? [Yes/No] - give the step depths, top")
  (princ "\n     step first: one per step plus the drop after the last")
  (princ "\n     tread (3 steps take 4 depths).  Then pick the top of the")
  (princ "\n     first tread - the flight always runs down and to the")
  (princ "\n     LEFT from there, so the steps rise to the right and the")
  (princ "\n     dims climb with them.  Each depth is dimensioned beside")
  (princ "\n     its own step and the overall depth further out; the")
  (princ "\n     treads are not dimensioned.")
  (princ "\n  6. Bead the steps? [Yes/No] - every tread is beaded, so the")
  (princ "\n     only question is which steps have beaded SIDE WALLS:")
  (princ "\n     [All/Some], and Some takes the step numbers (\"1 3 4\").")
  (princ "\n     Then click the side to bead toward and AUTOBEAD does the")
  (princ "\n     rest on its own rules - it has to be loaded for this.")
  (princ "\n  At any step tread prompt: Enter = done, Back = step back one")
  (princ "\n  step (removes it), Same = repeat the previous step tread.")
  (cs-tut-pause)
  (princ "\nWHAT IT CHECKS AND HANDLES FOR YOU")
  (princ "\n  - warns when the UCS is tilted, a line is not flat, or the")
  (princ "\n    current layer is off/frozen/locked")
  (princ "\n  - reads bare numbers as inches and accepts 1'4 style entry")
  (princ "\n    whatever the drawing's units setting")
  (princ "\n  - finds the true corner by extending the walls; warns when")
  (princ "\n    they are nearly parallel")
  (princ "\n  - picks out the chamfer among three lines and highlights")
  (princ "\n    what it classified before asking anything")
  (princ "\n  - reads arcs from their own geometry (mirrored arcs behave)")
  (princ "\n  - notes when a wall had to be extended to meet a step")
  (princ "\n  - dims go in \"STANDARD INCHES\" (step treads) and")
  (princ "\n    \"SIDE STANDARD\" (widths), falling back to the current")
  (princ "\n    style if missing; the whole run is ONE undo")
  (cs-tut-pause)

  (initget "Yes No")
  (if (= "No" (getkword (strcat "\nDraw a demonstration in this drawing?"
                                " [Yes/No] <Yes>: ")))
    (progn (princ "\nTutorial done - type CORNERSTP to use it for real.")
           (exit)))
  (setq pt (getpoint "\nPick a clear spot (about 250 x 250 needed): "))
  (if (null pt)
    (progn (princ "\nNo spot picked - tutorial done.") (exit)))
  (setq org  (trans pt 1 0)
        txth (cs-txth)
        w1   (list org (cs-add org '(200.0 0.0 0.0)))
        w2   (list org (cs-add org '(0.0 200.0 0.0)))
        bis  (cs-unit '(1.0 1.0 0.0))
        perp (cs-perp90 bis))
  (command "_.UNDO" "_Begin")
  (setq undoflag T
        oldce (getvar "CMDECHO")
        oldstyle (getvar "DIMSTYLE"))
  (setvar "CMDECHO" 0)

  (cs-mkline (car w1) (cadr w1))
  (cs-mkline (car w2) (cadr w2))
  (cs-tut-text (cs-add org '(30.0 -18.0 0.0)) (* 1.2 txth)
               "CORNERSTP demo: an L corner - these two lines get selected")
  (princ "\n[1] Two WALLS drawn - this is what you select.  The corner is")
  (princ "\n    their intersection; the steps will fan out along the 45")
  (princ "\n    degree bisector between them.")
  (cs-tut-pause)

  (setq prevL org prevR org dist 0.0 n 1)
  (foreach lst '((24.0 . 48.0) (12.0 . 72.0) (12.0 . 100.0))
    (setq dep  (car lst)
          wid  (cdr lst)
          dist (+ dist dep)
          p    (cs-add org (cs-scl bis dist))
          h1   (inters p (cs-add p perp) (car w1) (cadr w1) nil)
          h2   (inters p (cs-add p perp) (car w2) (cadr w2) nil)
          nat  (if (and h1 h2) (distance h1 h2))
          tmp  (cs-resolve wid nat h1 h2 p perp n (cs-tolerance))
          e1   (car tmp)
          e2   (cadr tmp))
    (if (> (cs-dot (cs-vec org e1) perp) (cs-dot (cs-vec org e2) perp))
      (setq tmp e1 e1 e2 e2 tmp))
    (cs-mkline e1 e2)
    (cs-conn prevL e1 w1 w2)
    (cs-conn prevR e2 w1 w2)
    (setq w (distance e1 e2))
    (if (null offd) (setq offd (max (* 2.0 txth) (* 0.2 w))))
    (cs-dim *cs-depth-dimstyle*
            (cs-add p (cs-scl bis (- dep))) p
            (cs-add (cs-add p (cs-scl bis (* -0.5 dep)))
                    (cs-scl perp offd)))
    (cs-dim *cs-width-dimstyle* e1 e2
            (cs-add org (cs-scl bis (- (+ (* 0.5 w) (* 1.5 txth))))))
    (cond
      ((= n 1)
       (princ "\n[2] Step 1: step tread 24, width 48.  The wall opening")
       (princ "\n    at that distance IS 48, so it trims to the walls.  Its")
       (princ "\n    tread dim starts the chain along the bisector; its")
       (princ "\n    width dim nests outside the corner."))
      ((= n 2)
       (princ "\n[3] Step 2: step tread 12, width 72 - also fits.  Step")
       (princ "\n    treads are each measured from the previous step,")
       (princ "\n    never a total."))
      (T
       (princ "\n[4] Step 3: step tread 12, width 100 - the opening here is")
       (princ "\n    only 96.  More than 1/8\" apart, so the width is HELD")
       (princ "\n    and the step breaks the walls, running 2 past each")
       (princ "\n    side.  Riser lines close its ends.")))
    (cs-tut-pause)
    (setq prevL e1 prevR e2 n (1+ n)))

  (if oldstyle (cs-setstyle oldstyle))
  (command "_.UNDO" "_End")
  (setq undoflag nil)
  (setvar "CMDECHO" oldce)
  (princ "\n[5] Done.  One U removes this whole demo.  Now try it for")
  (princ "\n    real: type CORNERSTP, select two wall lines of a corner,")
  (princ "\n    and follow the same prompts you just watched.")
  (princ))

(princ (strcat "\nCORNERSTP.lsp " *cs-version*
               " loaded - CORNERSTP to draw corner steps,"
               " TUTORIALCORNERSTP to learn it."))
(princ)


;;; ======================================================================
;;; >>> HEMISTEP.lsp
;;; ======================================================================

;;; ======================================================================
;;; HEMISTEP.lsp
;;; ----------------------------------------------------------------------
;;; Hemisphere (semicircle) step layout routine.
;;; Written for AutoCAD 2018 (plain AutoLISP + ActiveX for dim styles).
;;;
;;; LOAD:     APPLOAD this file (or drag it into the drawing window).
;;; COMMAND:  HEMISTEP
;;;
;;; WHAT IT DOES
;;;   Draws pool steps that act like chords inside a circle: parallel
;;;   step edges centered on a measuring axis.  What you select decides
;;;   how the axis is found:
;;;
;;;   LINE only ........ the classic base-line mode.  Steps are centered
;;;                      on the middle of the line, run parallel to it,
;;;                      and march perpendicular away from it in a
;;;                      direction you pick.  The hemisphere boundary is
;;;                      drawn for you (see step 6).
;;;   CURVE + LINE ..... inside-out mode with an axis line.  The line
;;;                      (through the curve or ending on it) is where
;;;                      the step treads are measured from: treads run
;;;                      along the line starting where it meets the
;;;                      curve, going INTO the curve, and the step
;;;                      widths sit perpendicular to the line.
;;;   CURVE only ....... inside-out mode from the middle of the curve.
;;;                      Treads are measured from there going INTO the
;;;                      curve, and the step widths sit along the
;;;                      tangent at that point.
;;;
;;;   A CURVE may be an ARC, a CIRCLE, or a POLYLINE - including a
;;;   composite hemisphere built from several arc segments, and
;;;   including a boundary this command drew earlier.  Each step is
;;;   measured against whichever part of the curve it actually lands
;;;   on, using the opening nearest the axis on each side.
;;;
;;;   In the curve modes the routine holds as true to the curve as it
;;;   can, the same way CORNERSTP holds to the walls: a step width
;;;   within the width tolerance of the curve's opening at that distance
;;;   is snapped to the curve; any other width is held, centered on the
;;;   opening so it breaks the curve equally on both sides.
;;;
;;; WORKFLOW
;;;   1.  Select the base line, the base curve, or the curve plus its
;;;       axis line.
;;;   2.  LINE-only mode asks you to pick a point for the side the
;;;       steps go.  The curve modes assume the steps go into the curve
;;;       and only ask for a side when the geometry is ambiguous.
;;;   3.  You are asked whether to dimension the steps [Yes/No]:
;;;         - Step widths across each chord, nested behind the start of
;;;           the measuring axis (wider steps further out), in dim style
;;;           "SIDE STANDARD".
;;;         - Step treads chained along the axis (start to step 1, step
;;;           1 to step 2, ...), in dim style "STANDARD INCHES".
;;;       If a style is missing the current style is used instead.
;;;   4.  LINE mode starts with the width of the step AT THE WALL: that
;;;       is the top of the run, so no chord is drawn there (the wall
;;;       already is one), but it is dimensioned and it anchors both
;;;       ends of the boundary curve.  The curve modes skip it, since
;;;       the width at the start is set by the curve itself.
;;;   5.  From there both modes run STEP TREAD then WIDTH, repeating.
;;;       Every step tread is measured FROM THE PREVIOUS STEP EDGE (from
;;;       the start of the axis for the first step) - never a running
;;;       total.
;;;       Distances read architectural style: a bare number is inches
;;;       (drawing units) and feet-inch entry like 1'4 (= 16") works
;;;       whatever the units setting.
;;;   6.  Ending and shortcuts:
;;;         - Enter at a step tread prompt = done.
;;;         - Back at a step tread prompt steps back one step: it
;;;           removes the step just drawn (its line and its dimensions).
;;;           Undo, the old keyword, is still accepted.  Same repeats
;;;           the previous step tread.
;;;         - Enter at a width prompt fits that step to the curve in
;;;           the curve modes, or repeats the previous width in LINE
;;;           mode.
;;;   7.  The hemisphere is then rebuilt as one polyline of arc segments
;;;       through every step end.  In LINE mode you are asked for one
;;;       last distance from the last step to the back of the curve, and
;;;       the polyline runs wall - side A - crown - side B - wall (the
;;;       last distance also gets the final link of the tread-dim chain).
;;;       In the curve modes the polyline runs from the deepest step
;;;       around the first one and back, and the segment spanning the
;;;       first step carries the SELECTED CURVE'S OWN bulge: a first
;;;       step sitting on the curve reproduces that curve exactly, and
;;;       a wider one still follows its curvature instead of spiking in
;;;       to the point where the axis met it.
;;;   8.  When steps were drawn you may add a SIDE PROFILE [Yes/No]:
;;;       give the step depths (the vertical drops), top step first -
;;;       one per step PLUS one more for the drop after the last
;;;       tread, so 3 steps take 4 depths - with Back to re-ask the
;;;       previous one; then pick the top of the first tread.  The
;;;       flight always runs DOWN AND TO THE LEFT from there, so there
;;;       is no side to pick.  See "The side profile" below.
;;;   9.  Finally, BEAD THE STEPS.  Every tread is beaded - that is the
;;;       assumption - so the only thing asked is which steps carry the
;;;       bead along their side walls: All of them, or Some, given by
;;;       step number.  AUTOBEAD does the work on its own rules (2"
;;;       toward the side you click, onto its Bead Track layer), so
;;;       AUTOBEAD.lsp has to be loaded; when it is not, the run says
;;;       so and finishes without beading.  The beads are their own
;;;       undo group - AutoCAD does not nest them - so one U undoes
;;;       the beads and the next undoes the steps.
;;;
;;; THE SIDE PROFILE
;;;   The flight is drawn as an alternating drop/tread silhouette in
;;;   world X/Y, always descending to the LEFT of the picked top of the
;;;   first tread and ending on the last depth - so the steps rise to
;;;   the right, the way the shop's own elevations read.
;;;   The dims climb with them, up and to the right, on the high side:
;;;     * every depth is a dim of its own, standing the same distance
;;;       right of the corner its drop lands on, so they step out with
;;;       the flight instead of stacking in one chain;
;;;     * the overall depth sits further out again;
;;;     * the treads carry no dims - the depths and the overall say it.
;;;   How far out the fan sits is *CS-PROFILE-DIMGAP* - the gap on top
;;;   of the clearance the geometry needs.  Raise it to open the dims
;;;   out further, lower it to tuck them in.
;;;   Each one is a VERTICAL LINEAR dim bound to the two step corners
;;;   that bracket the drop.  Those corners run diagonally to each
;;;   other, so binding the diagonal (rather than dimensioning the
;;;   riser line) keeps the extension lines hooked to the geometry
;;;   while the dim still reads the drop, not the slope.
;;;
;;; OPTIONAL SETTINGS (set these before running the command)
;;;   *CS-WIDTH-TOL*      width tolerance in drawing units.  When nil
;;;                       (the default) it is 1/8" converted through the
;;;                       drawing's INSUNITS setting.
;;;   *CS-DEPTH-DIMSTYLE* dim style for step-tread dims (the side
;;;                       profile's dims use it too).
;;;   *CS-WIDTH-DIMSTYLE* dim style for step-width dims.
;;;   *CS-DIM-LAYER*      layer for the dimensions.  When nil (the
;;;                       default) the current layer is used.
;;;   *CS-PROFILE-DIMGAP* how far the side profile's dims stand off the
;;;                       flight, on top of the clearance the geometry
;;;                       needs.  nil (the default) is four text
;;;                       heights or three quarters of a tread,
;;;                       whichever is more, so the fan keeps its
;;;                       proportions whether or not the drawing has a
;;;                       dim scale set up.  It also sets how much
;;;                       further out again the overall depth sits.
;;;
;;; NOTES
;;;   - Geometry is assumed to be drawn in plan view.  The routine warns
;;;     when the current UCS is not World, when selected geometry is not
;;;     flat, and when the current layer is off/frozen/locked.
;;;   - Steps are drawn as LINEs on the current layer.
;;;   - DIMSCALE (or the annotation scale for annotative styles) sets
;;;     the dimension size; grab a dimension line to slide it if it
;;;     lands awkwardly.
;;;   - One U / UNDO reverses the whole command; a bead run added at
;;;     the end is its own group, so it takes a U of its own.
;;;   - A form (the Calofin palette / LAZFORM) can pre-answer the
;;;     questions - the step COUNT included, which the prompts only
;;;     ever learn from Enter - by leaving (key . value) pairs in
;;;     *HS-FORM*; see "form answers" below.  Selections and point
;;;     picks are always made by hand.
;;; ======================================================================

;; Settings - only defined if not already set, so this file and
;; CORNERSTP.lsp stay in sync no matter which one loads first.
;;; SHARED BUILD: requires CALOFIN-LIB.lsp (load via CALOFIN-LOADER.lsp).
;;; Generic helpers live there under cal: - see STANDARDS.md.
;;;

(if (not (boundp '*cs-width-tol*))      (setq *cs-width-tol* nil))
(if (not (boundp '*cs-dim-layer*))      (setq *cs-dim-layer* nil))
(if (not (boundp '*cs-depth-dimstyle*)) (setq *cs-depth-dimstyle* "STANDARD INCHES"))
(if (not (boundp '*cs-width-dimstyle*)) (setq *cs-width-dimstyle* "SIDE STANDARD"))
;; How far the side profile's dims stand off the flight, on top of the
;; clearance the geometry itself needs.  nil = four text heights, which
;; is what the shop's own elevations read like; raise it to open the
;; fan out further, lower it to tuck the dims in.
(if (not (boundp '*cs-profile-dimgap*)) (setq *cs-profile-dimgap* nil))

(vl-load-com) ; ActiveX is used to set styles (handles names with spaces)

(setq *hs-version* "v3.3") ; printed on load and at command start so a
                           ; stale APPLOADed copy is easy to spot

;;; ------------------------- vector helpers -----------------------------

(defun hs-add (p v) (list (+ (car p) (car v)) (+ (cadr p) (cadr v)) 0.0))

(defun hs-vec (a b) (list (- (car b) (car a)) (- (cadr b) (cadr a)) 0.0))

(defun hs-scl (v s) (list (* (car v) s) (* (cadr v) s) 0.0))

(defun hs-dot (a b) (+ (* (car a) (car b)) (* (cadr a) (cadr b))))

(defun hs-unit (v / l)
  (if (> (setq l (sqrt (hs-dot v v))) 1e-10) (hs-scl v (/ 1.0 l))))

(defun hs-perp (v) (list (- (cadr v)) (car v) 0.0))

(defun hs-mid2 (a b) (list (* 0.5 (+ (car a) (car b)))
                           (* 0.5 (+ (cadr a) (cadr b)))
                           0.0))

(defun hs-cross (a b) (- (* (car a) (cadr b)) (* (cadr a) (car b))))

;; distance from point P to the segment A-B
(defun hs-ptseg (p a b / d l2 t2)
  (setq d  (hs-vec a b)
        l2 (hs-dot d d))
  (if (< l2 1e-20)
    (distance p a)
    (progn
      (setq t2 (/ (hs-dot (hs-vec a p) d) l2))
      (cond ((< t2 0.0) (distance p a))
            ((> t2 1.0) (distance p b))
            (T (distance p (hs-add a (hs-scl d t2))))))))

;; how far point P lies beyond the ends of segment A-B (0.0 when on it)
(defun hs-beyond (p a b / d l t2)
  (setq d (hs-vec a b)
        l (sqrt (hs-dot d d)))
  (if (< l 1e-10)
    (distance p a)
    (progn
      (setq t2 (/ (hs-dot (hs-vec a p) d) (* l l)))
      (cond ((< t2 0.0) (* (- t2) l))
            ((> t2 1.0) (* (- t2 1.0) l))
            (T 0.0)))))

;; point on a circle: center C, radius R, angle A
(defun hs-arcpt (c r a)
  (list (+ (car c) (* r (cos a))) (+ (cadr c) (* r (sin a))) 0.0))

;; T when angle A lies on the counterclockwise span A1 -> A2
(defun hs-inspan (a a1 a2 / e)
  (setq e (- a2 a1))
  (if (< e 0.0) (setq e (+ e pi pi)))
  (setq a (- a a1))
  (if (< a 0.0) (setq a (+ a pi pi)))
  (<= a (+ e 1e-6)))

;;; ------------------------ curve description ---------------------------
;;; The selected curve becomes a list of boundary "pieces":
;;;   ("A" center radius startang endang)   arc, counterclockwise
;;;   ("S" p1 p2)                           straight segment
;;; so an arc, a circle and a multi-arc polyline are all handled alike.

;; intersections of the circle (C,R) with the infinite line through A
;; along the UNIT direction D; a list of 0 or 2 points
(defun hs-linecirc (a d c r / f g disc)
  (setq f    (hs-vec c a)
        g    (hs-dot d f)
        disc (+ (* r r) (- (* g g) (hs-dot f f))))
  (if (>= disc 0.0)
    (progn
      (setq disc (sqrt disc))
      (list (hs-add a (hs-scl d (- (- g) disc)))
            (hs-add a (hs-scl d (+ (- g) disc)))))))

;; Arc piece from an ARC entity.  Built from the curve's own start/mid/
;; end points and its OCS center, so mirrored arcs are handled.
(defun hs-arcpiece (en / ed c r sp ep mp a1 a2 sw)
  (setq ed (entget en)
        c  (trans (cdr (assoc 10 ed)) en 0)
        r  (cdr (assoc 40 ed))
        sp (vlax-curve-getstartpoint en)
        ep (vlax-curve-getendpoint en)
        mp (vlax-curve-getpointatdist
             en (* 0.5 (vlax-curve-getdistatparam
                         en (vlax-curve-getendparam en))))
        a1 (angle c sp)
        a2 (angle c ep))
  (if (not (hs-inspan (angle c mp) a1 a2))
    (setq sw a1 a1 a2 a2 sw))
  (if (< a2 a1) (setq a2 (+ a2 pi pi)))
  (list "A" c r a1 a2))

;; Arc piece for a polyline bulge segment P1 -> P2
(defun hs-bulgepiece (p1 p2 b / th l r h nrm cen a1 a2)
  (setq th  (* 4.0 (atan b))
        l   (distance p1 p2)
        r   (abs (/ l (* 2.0 (sin (/ th 2.0)))))
        h   (* r (cos (/ (abs th) 2.0)))
        nrm (hs-unit (hs-perp (hs-vec p1 p2)))
        cen (hs-add (hs-mid2 p1 p2)
                    (hs-scl nrm (if (> b 0.0) h (- h)))))
  (if (> b 0.0)
    (setq a1 (angle cen p1) a2 (angle cen p2))
    (setq a1 (angle cen p2) a2 (angle cen p1)))
  (if (< a2 a1) (setq a2 (+ a2 pi pi)))
  (list "A" cen r a1 a2))

;; Pieces of a POLYLINE (LWPOLYLINE or heavy 2D), points brought to WCS
(defun hs-plpieces (en / ed el cl vs bs i m out v1 v2 b sub pr)
  (setq ed (entget en)
        el (cond ((cdr (assoc 38 ed))) (0.0))
        cl (= 1 (logand 1 (cond ((cdr (assoc 70 ed))) (0)))))
  (if (= "LWPOLYLINE" (cdr (assoc 0 ed)))
    (foreach pr ed
      (cond
        ((= 10 (car pr))
         (setq vs (cons (trans (list (car (cdr pr)) (cadr (cdr pr)) el) en 0) vs)
               bs (cons 0.0 bs)))
        ((= 42 (car pr))
         (if bs (setq bs (cons (cdr pr) (cdr bs)))))))
    (progn
      (setq sub (entnext en))
      (while (and sub (= "VERTEX" (cdr (assoc 0 (entget sub)))))
        (setq ed  (entget sub)
              vs  (cons (trans (cdr (assoc 10 ed)) en 0) vs)
              bs  (cons (cond ((cdr (assoc 42 ed))) (0.0)) bs)
              sub (entnext sub)))))
  (setq vs (reverse vs) bs (reverse bs) m (length vs) i 0)
  (while (< i (if cl m (1- m)))
    (setq v1 (nth i vs)
          v2 (nth (rem (1+ i) m) vs)
          b  (nth i bs))
    (if (> (distance v1 v2) 1e-10)
      (setq out (cons (if (equal 0.0 b 1e-9)
                        (list "S" v1 v2)
                        (hs-bulgepiece v1 v2 b))
                      out)))
    (setq i (1+ i)))
  (reverse out))

;; every crossing of the line (P along unit U) with the curve, as a list
;; of (point . piece) pairs
(defun hs-hits (p u pieces / out q pc)
  (foreach pc pieces
    (if (= "A" (car pc))
      (foreach q (hs-linecirc p u (cadr pc) (caddr pc))
        (if (hs-inspan (angle (cadr pc) q) (cadddr pc) (nth 4 pc))
          (setq out (cons (cons q pc) out))))
      (progn
        (setq q (inters p (hs-add p u) (cadr pc) (caddr pc) nil))
        (if (and q (< (hs-beyond q (cadr pc) (caddr pc)) 1e-8))
          (setq out (cons (cons q pc) out))))))
  out)

;; The curve's opening across P along U: the nearest crossing on each
;; side of P, as (h1 h2 width).  nil when the curve does not bracket P.
(defun hs-open (p u pieces / s sp sn h1 h2 hp)
  (foreach hp (hs-hits p u pieces)
    (setq s (hs-dot (hs-vec p (car hp)) u))
    (cond
      ((> s 1e-9)  (if (or (null sp) (< s sp)) (setq sp s h1 (car hp))))
      ((< s -1e-9) (if (or (null sn) (> s sn)) (setq sn s h2 (car hp))))))
  (if (and h1 h2) (list h1 h2 (- sp sn))))

;;; ---------------------- boundary polyline output ----------------------

;; center of the circle through three points, nil if collinear
(defun hs-circum (a b q / ax ay bx by qx qy d)
  (setq ax (car a) ay (cadr a)
        bx (car b) by (cadr b)
        qx (car q) qy (cadr q)
        d  (* 2.0 (+ (* ax (- by qy)) (* bx (- qy ay)) (* qx (- ay by)))))
  (if (> (abs d) 1e-12)
    (list (/ (+ (* (+ (* ax ax) (* ay ay)) (- by qy))
                (* (+ (* bx bx) (* by by)) (- qy ay))
                (* (+ (* qx qx) (* qy qy)) (- ay by)))
             d)
          (/ (+ (* (+ (* ax ax) (* ay ay)) (- qx bx))
                (* (+ (* bx bx) (* by by)) (- ax qx))
                (* (+ (* qx qx) (* qy qy)) (- bx ax)))
             d)
          0.0)))

;; polyline bulge for the arc A->B on the circle centered O
(defun hs-segb (a b o ccw / t1 t2 th)
  (setq t1 (angle o a)
        t2 (angle o b)
        th (if ccw (- t2 t1) (- t1 t2)))
  (if (< th 0.0) (setq th (+ th pi pi)))
  (* (if ccw 1.0 -1.0) (/ (sin (/ th 4.0)) (cos (/ th 4.0)))))

;; Midpoint of the arc that chord A-B carries with bulge BL.  A positive
;; bulge is counterclockwise, which bulges to the RIGHT of A->B.
(defun hs-bulgemid (a b bl / d nrm)
  (setq d   (hs-vec a b)
        nrm (hs-unit (list (cadr d) (- (car d)) 0.0)))
  (if nrm
    (hs-add (hs-mid2 a b) (hs-scl nrm (* 0.5 (distance a b) bl)))
    (hs-mid2 a b)))

;; Bulge for the boundary segment that spans the first step, A -> B,
;; taken from the arc piece PC that the start point REF sits on.  So the
;; boundary follows the ORIGINAL curve across the first step instead of
;; cutting in to a point on it.
;;
;; The side is chosen geometrically - whichever of the two possible arcs
;; bulges nearer REF - so no angle-wrap case can select the wrong one.
;; An arc sweeping more than half a circle would leave A heading back the
;; way the boundary came, folding the corner into a spike, so it is
;; rejected in favour of closing the span straight.
(defun hs-firstspan (a b pc ref / c b1 b2 bl)
  (setq c  (cadr pc)
        b1 (hs-segb a b c T)
        b2 (hs-segb a b c nil)
        bl (if (< (distance (hs-bulgemid a b b1) ref)
                  (distance (hs-bulgemid a b b2) ref))
             b1 b2))
  (if (> (abs bl) 1.0)
    (progn
      (princ (strcat "\n  Note: the curve wraps more than half a circle"
                     " across the first step - closing it straight."))
      0.0)
    bl))

;; A bulge past 1.0 sweeps more than half a circle, which folds the
;; boundary back on itself; such a segment is drawn straight instead.
(defun hs-safeb (bl)
  (if (or (null bl) (> (abs bl) 1.0)) 0.0 bl))

;; Circle through PTS[i], PTS[i+1], PTS[i+2] as (center . counterclockwise)
(defun hs-fit3 (pts i / a b c o)
  (setq a (nth i pts)
        b (nth (1+ i) pts)
        c (nth (+ i 2) pts)
        o (hs-circum a b c))
  (if o (cons o (> (hs-cross (hs-vec a b) (hs-vec a c)) 0.0))))

;; Bulges for a polyline through PTS, one per segment, by fitting a
;; circle through consecutive triples (a chain of 3-point arcs).
;;
;; K is the index of the crown vertex, or nil.  When given, the first
;; circle fitted is the one through the crown and its two neighbours,
;; and the rest are fitted outward from there.  That keeps the apex on
;; a single arc - so when those three points sit on the original curve
;; the reconstructed arc IS the original curve - instead of falling on
;; a seam between two circles.
;;
;; FIXED is an optional alist of (segment . bulge) that wins over any
;; fitting; when it holds the middle segment (the curve modes put the
;; original curve's own bulge there) the rest are fitted outward from
;; it, keeping both sides symmetric.
(defun hs-blgs (pts k fixed / nseg starts i res oc out st m)
  (setq nseg (1- (length pts))
        res  fixed)
  (if (or (null k) (< k 1) (> (1+ k) nseg)) (setq k nil))
  ;; the order triples are fitted in; earlier entries win
  (cond
    (k
     (setq starts (list (1- k))                ; the arc across the crown
           i      (- k 3))
     (while (>= i 0)                           ; outward, crown side A
       (setq starts (append starts (list i)) i (- i 2)))
     (setq i (1+ k))
     (while (<= (+ i 2) nseg)                  ; outward, crown side B
       (setq starts (append starts (list i)) i (+ i 2))))
    (fixed                                     ; outward from the fixed one
     (setq m (car (car fixed))
           i (- m 2))
     (while (>= i 0)
       (setq starts (append starts (list i)) i (- i 2)))
     (setq i (1+ m))
     (while (<= (+ i 2) nseg)
       (setq starts (append starts (list i)) i (+ i 2))))
    (T
     (setq i 0)
     (while (<= (+ i 2) nseg)
       (setq starts (append starts (list i)) i (+ i 2)))))
  ;; sweep every triple as a fallback so leftover end segments are
  ;; fitted through their own three points rather than a neighbour's
  (setq i 0)
  (while (<= (+ i 2) nseg)
    (setq starts (append starts (list i)) i (1+ i)))
  ;; A fitted segment sweeping more than half a circle leaves its start
  ;; heading back the way the boundary came - a fold, never right between
  ;; consecutive step ends - so such a segment is drawn straight.
  (foreach st starts
    (if (setq oc (hs-fit3 pts st))
      (progn
        (if (null (assoc st res))
          (setq res (cons (cons st (hs-safeb
                                     (hs-segb (nth st pts) (nth (1+ st) pts)
                                              (car oc) (cdr oc))))
                          res)))
        (if (null (assoc (1+ st) res))
          (setq res (cons (cons (1+ st) (hs-safeb
                                          (hs-segb (nth (1+ st) pts)
                                                   (nth (+ st 2) pts)
                                                   (car oc) (cdr oc))))
                          res))))))
  (setq i 0)
  (repeat nseg                                 ; 0.0 where nothing fitted
    (setq out (append out (list (cond ((cdr (assoc i res))) (0.0))))
          i   (1+ i)))
  out)

;; open LWPOLYLINE through PTS with one bulge per segment
(defun hs-mkpoly (pts blgs)
  (entmake (append
             (list '(0 . "LWPOLYLINE")
                   '(100 . "AcDbEntity")
                   '(100 . "AcDbPolyline")
                   (cons 90 (length pts))
                   '(70 . 0))
             (apply 'append
                    (mapcar '(lambda (p b)
                               (list (cons 10 (list (car p) (cadr p)))
                                     (cons 42 b)))
                            pts
                            (append blgs '(0.0)))))))


;;; --------------------------- bead helpers -----------------------------

;; The step numbers typed at a prompt - "1 3 4", "1,3,4" and "1, 3 and 4"
;; all read the same.  Anything that is not a digit separates.
(defun hs-numlist (str / out tok i c)
  (setq out '() tok "" i 0)
  (while (<= i (strlen str))
    (setq c (if (< i (strlen str)) (substr str (1+ i) 1) " "))
    (if (and (>= (ascii c) 48) (<= (ascii c) 57))
      (setq tok (strcat tok c))
      (progn
        (if (/= tok "") (setq out (cons (atoi tok) out)))
        (setq tok "")))
    (setq i (1+ i)))
  (reverse out))

;; The tread line of every step that was committed, as
;; (step-number . ename).  A step's log record carries its entities
;; first and its step number at index 3, and the only LINE among
;; those entities is its tread - any dimension beside it is a DIMENSION.
(defun hs-treadents (log / out rec e ln)
  (setq out '())
  (foreach rec log
    (setq ln nil)
    ;; ...-since lists newest first, and a step draws its tread before
    ;; any side line or dimension, so the LAST line seen is the tread
    (foreach e (car rec)
      (if (and e (entget e)
               (= "LINE" (cdr (assoc 0 (entget e)))))
        (setq ln e)))
    (if ln (setq out (cons (cons (nth 3 rec) ln) out))))
  ;; the log runs newest first, so consing through it already leaves
  ;; the pairs in step order - lowest first, the way they were drawn
  out)

;; The step numbers on offer, as "1, 2, 3" - so the numbers prompt can
;; be answered without scrolling back through the run.
(defun hs-numsay (pairs / out pr)
  (setq out "")
  (foreach pr pairs
    (setq out (strcat out (if (= out "") "" ", ") (itoa (car pr)))))
  out)

;; Midpoint (WCS) of a LINE entity.
(defun hs-entmid (e / ed)
  (setq ed (entget e))
  (hs-mid2 (cdr (assoc 10 ed)) (cdr (assoc 11 ed))))

;;; ------------------------- drawing helpers ----------------------------

(defun hs-mkline (a b)
  (entmake (list '(0 . "LINE")
                 (cons 10 (list (car a) (cadr a) 0.0))
                 (cons 11 (list (car b) (cadr b) 0.0)))))

;; 1/8" expressed in the drawing's units (INSUNITS); inches if unitless
(defun hs-autotol ( / iu)
  (setq iu (getvar "INSUNITS"))
  (cond ((= iu 1) 0.125)            ; inches
        ((= iu 2) (/ 0.125 12.0))   ; feet
        ((= iu 4) 3.175)            ; millimeters
        ((= iu 5) 0.3175)           ; centimeters
        ((= iu 6) 0.003175)         ; meters
        (T        0.125)))          ; unitless - assume inches

(defun hs-tolerance ( )
  (if (numberp *cs-width-tol*) *cs-width-tol* (hs-autotol)))

;; annotation text height in drawing units; DIMSCALE is 0 for
;; annotative dim styles, where the annotation scale governs instead
(defun hs-txth ( / h s)
  (setq h (getvar "DIMTXT")
        s (getvar "DIMSCALE"))
  (if (or (null s) (<= s 0.0))
    (setq s (cond ((and (getvar "CANNOSCALEVALUE")
                        (> (getvar "CANNOSCALEVALUE") 0.0))
                   (/ 1.0 (getvar "CANNOSCALEVALUE")))
                  (1.0))))
  (if (and h (> (* h s) 0.0)) (* h s) 1.0))

;; make dimension style NAME current, but only if it exists and is not
;; already current.  Uses ActiveX so style names containing spaces are
;; handled correctly (the -DIMSTYLE command would read a space as ENTER).
(defun hs-setstyle (name / doc)
  (if (and (tblsearch "DIMSTYLE" name)
           (/= (strcase name) (strcase (getvar "DIMSTYLE"))))
    ;; the argument list is required, even for a lambda that takes
    ;; none - without it this is a "too few arguments" error every
    ;; time a style really has to be switched
    (vl-catch-all-apply
      '(lambda ()
         (setq doc (vla-get-activedocument (vlax-get-acad-object)))
         (vla-put-activedimstyle
           doc (vla-item (vla-get-dimstyles doc) name)))
      '())))

;; aligned dimension between A and B in dim style STYLE, dim line
;; passing through THRU.  Points are WCS and are translated to the
;; current UCS for the command.  "_non" defeats running osnap.
(defun hs-dim (style a b thru / oldl)
  (hs-setstyle style)
  (if (and *cs-dim-layer* (cal:layer-usable-p *cs-dim-layer*))
    (progn (setq oldl (getvar "CLAYER"))
           (setvar "CLAYER" *cs-dim-layer*)))
  (command "_.DIMALIGNED" "_non" (trans a 0 1)
                          "_non" (trans b 0 1)
                          "_non" (trans thru 0 1))
  (if oldl (setvar "CLAYER" oldl)))

;; Vertical linear dimension between A and B in dim style STYLE, dim
;; line passing through THRU.  A and B are the real step corners, which
;; run diagonally to each other, so "_V" is forced: the dimension
;; measures the DROP between them while its extension lines still hook
;; the corners themselves.  Cleaner than dimensioning the riser line,
;; which leaves the dim marooned beside the step instead of reading
;; across to it.  Points are WCS.
(defun hs-dimv (style a b thru / oldl)
  (hs-setstyle style)
  (if (and *cs-dim-layer* (cal:layer-usable-p *cs-dim-layer*))
    (progn (setq oldl (getvar "CLAYER"))
           (setvar "CLAYER" *cs-dim-layer*)))
  (command "_.DIMLINEAR" "_non" (trans a 0 1)
                         "_non" (trans b 0 1)
                         "_V"
                         "_non" (trans thru 0 1))
  (if oldl (setvar "CLAYER" oldl)))

;; entities created since MARK (nil = since the drawing was empty)
(defun hs-since (mark / e out)
  (setq e (if mark (entnext mark) (entnext)))
  (while e (setq out (cons e out) e (entnext e)))
  out)

;;; --------------------------- form answers -----------------------------
;;;
;;;  A form - the Calofin palette, or LAZFORM - can answer some or all
;;;  of HEMISTEP's questions before the run starts.  It leaves them in
;;;  *hs-form* as (key . value) pairs and the question sites look there
;;;  first, so a filled-in sheet drives the whole run and a half-filled
;;;  one simply shortens it.
;;;
;;;  Three states, and the difference between the last two IS the
;;;  feature:
;;;
;;;    key absent      the form did not answer it  -> ask, as usual
;;;    (key . nil)     what Enter means there      -> taken, no prompt
;;;    (key . 24.0)    the form answered it        -> 24.0, no prompt
;;;
;;;  (assoc key ...) tells those apart; (cdr (assoc ...)) alone cannot.
;;;
;;;  THE KEYS.  steps is the STEP COUNT - the one answer the prompts
;;;  never ask for directly: when it is known the tread loop stops
;;;  itself after that many steps instead of waiting for Enter.
;;;  tread1..treadN and width1..widthN feed the per-step prompts (a
;;;  width of nil = what Enter means there: fit to the curve, or
;;;  repeat the previous width in line mode); depth1..depthN and
;;;  depthafter feed the side profile's depths.  wallwidth and crown
;;;  (nil = none, either) answer line mode's two extra distances;
;;;  dims, boundary, profile and bead answer the named questions; a
;;;  keyword is checked against the live prompt's own list and falls
;;;  through to the prompt when it does not fit.  Selections and
;;;  point picks are never form-answered.
;;;
;;;  AN ANSWER IS REMOVED AS IT IS USED.  Not marked used - removed.
;;;  Otherwise Back deadlocks: step back onto a form-answered question,
;;;  it answers itself instantly and walks forward again, and there is
;;;  no key the user can press to get out.  The store is cleared on
;;;  both exits from the command, so nothing leaks into the next run.

(setq *hs-form* nil)

;; Did the form answer KEY at all?  This is the absent/nil distinction
;; that (cdr (assoc ...)) throws away.
(defun hs-fhas (key) (if (assoc key *hs-form*) t nil))

;; The form's answer for KEY, removed from the store as it is read.
(defun hs-ftake (key / p)
  (setq p (assoc key *hs-form*))
  (setq *hs-form* (vl-remove p *hs-form*))
  (cdr p))

(defun hs-fclear () (setq *hs-form* nil))

;; The form's numeric answer for KEY, spent as it is read: the number
;; as a REAL (the way getdist hands one back), nil for anything else.
(defun hs-fnum (key / v)
  (setq v (hs-ftake key))
  (if (numberp v) (* 1.0 v)))

;; The key of a numbered question: (hs-fnkey "tread" 3) -> tread3.
(defun hs-fnkey (stem i) (read (strcat stem (itoa i))))

;; V as the question would spell it, or nil when the question does not
;; accept it at all: an answer the live prompt does not offer falls
;; through to the prompt instead of being handed on to fail later, and
;; the canonical SPELLING comes back, not the caller's, so downstream
;; (= v "No") tests keep working.
(defun hs-fkword (v kws / i n c w out)
  (setq i 1 n (strlen kws) w "" v (strcase v))
  (while (<= i (1+ n))
    (setq c (if (<= i n) (substr kws i 1) " "))
    (if (= c " ")
        (progn
          (if (and (/= w "") (= (strcase w) v)) (setq out w))
          (setq w ""))
        (setq w (strcat w c)))
    (setq i (1+ i)))
  out)

;; The form's keyword answer for KEY against the live list KWS: the
;; canonical keyword, DFLT when the form said nil (what Enter means at
;; every keyword prompt here), or nil when the form did not answer -
;; or answered a word the prompt does not offer - so the caller asks
;; as always.
(defun hs-fkw (key kws dflt / v)
  (if (hs-fhas key)
    (progn
      (setq v (hs-ftake key))
      (cond ((null v) dflt)
            ((and (= (type v) 'STR) (setq v (hs-fkword v kws))) v)))))

;; Run HEMISTEP with a form's answers already in hand.  Nothing
;; happens here that the direct path misses: a caller may equally set
;; *hs-form* itself and call c:HEMISTEP, which is what the tests do.
(defun hs-run-with-answers (answers)
  (setq *hs-form* answers)
  (c:HEMISTEP)
  (hs-fclear)
  (princ))

;;; --------------------------- main command -----------------------------

(defun c:HEMISTEP ( / *error* hs-popstep undoflag ss i en ed et zf
                      lin lp1 lp2 pieces arcs cmode sp spc dir u
                      q hp bscr best side pt inref stopf cum n wid dep
                      p op nat cen e1 e2 drawn tol txth offd pprev
                      oldce oldstyle ea eb crown pts reflen lastdep
                      dimflag slog mark svcum svp svn svea sveb rec pc oldlu
                      bmark bsides btreads bnums bside bdir bss pr be
                      wallA wallB lastwid kx fx
                      tlist srt treads pv drops dd jx tcount ptop
                      px py totrun totdrop td cnrs pfo pgap fsteps fkey)

  (defun *error* (msg)
    (hs-fclear)                     ; both exits clear the form store
    (if undoflag (command-s "_.UNDO" "_End"))
    (if oldstyle (hs-setstyle oldstyle))
    (if oldce (setvar "CMDECHO" oldce))
    (if oldlu (setvar "LUNITS" oldlu))
    (redraw)
    (if (not (wcmatch (strcase msg) "*BREAK*,*CANCEL*,*QUIT*,*EXIT*"))
      (princ (strcat "\nHEMISTEP: " msg)))
    (princ))

  ;; remove the most recently drawn step and roll the state back
  (defun hs-popstep ( / e)
    (if (null slog)
      (progn (princ "\n  Already at the first step.") nil)
      (progn
        (setq rec (car slog))
        (foreach e (car rec) (if (and e (entget e)) (entdel e)))
        (setq cum   (nth 1 rec)
              pprev (nth 2 rec)
              n     (nth 3 rec)
              ea    (nth 4 rec)
              eb    (nth 5 rec)
              drawn (1- drawn)
              tlist (cdr tlist)
              slog  (cdr slog))
        (redraw)
        (princ "\n  Stepping back one step.")
        T)))

  ;; ---- 0. environment checks -------------------------------------------
  (princ (strcat "\nHEMISTEP " *hs-version* " - each step tread is measured"
                 " from the previous step."))
  ;; the form's step COUNT, spent here once for the whole run: when it
  ;; is known the tread loop stops itself after that many steps
  (if (hs-fhas 'steps)
    (progn
      (setq fsteps (hs-ftake 'steps))
      (if (not (and (numberp fsteps) (> fsteps 0))) (setq fsteps nil))))
  (setq tol  (hs-tolerance)
        txth (hs-txth))
  ;; Read distances architectural-style for the whole command: a bare
  ;; number is drawing units (inches in an inch-based drawing) and
  ;; feet-inch entry like 1'4 works whatever LUNITS was set to.
  (setq oldlu (getvar "LUNITS"))
  (setvar "LUNITS" 4)
  (if (not (equal (trans '(0.0 0.0 1.0) 1 0 T) '(0.0 0.0 1.0) 1e-8))
    (princ (strcat "\nWARNING: the current UCS is not parallel to the"
                   " World XY plane - results may be skewed.")))
  (if (not (cal:layer-usable-p (getvar "CLAYER")))
    (princ (strcat "\nWARNING: the current layer (" (getvar "CLAYER")
                   ") is off, frozen or locked - new steps may not"
                   " appear.")))
  (if (zerop (getvar "INSUNITS"))
    (princ (strcat "\nNote: drawing units are unitless; the width"
                   " tolerance is taken as " (rtos tol) ".")))

  ;; ---- 1. selection ----------------------------------------------------
  (princ (strcat "\nSelect the base line, the base curve (arc, circle or"
                 " polyline), or the curve plus its axis line:"))
  (setq ss (ssget '((0 . "LINE,ARC,CIRCLE,LWPOLYLINE,POLYLINE"))))
  (if (null ss)
    (progn (princ "\nNothing selected.") (exit)))
  (setq i 0)
  (repeat (sslength ss)
    (setq en (ssname ss i)
          ed (entget en)
          et (cdr (assoc 0 ed))
          i  (1+ i))
    (cond
      ((= et "LINE")
       (if lin
         (progn (princ "\nSelect only ONE line.") (exit)))
       (if (> (abs (- (caddr (cdr (assoc 10 ed)))
                      (caddr (cdr (assoc 11 ed))))) 1e-6)
         (setq zf T))
       (setq lin ed
             lp1 (cdr (assoc 10 ed))
             lp2 (cdr (assoc 11 ed))))
      ((= et "ARC")
       (setq pieces (cons (hs-arcpiece en) pieces)))
      ((= et "CIRCLE")
       (setq pieces (cons (list "A" (trans (cdr (assoc 10 ed)) en 0)
                                (cdr (assoc 40 ed)) 0.0 (+ pi pi))
                          pieces)))
      (T
       (setq pieces (append (hs-plpieces en) pieces)))))
  (if zf
    (princ (strcat "\nWARNING: the selected line is not flat (its ends"
                   " differ in Z) - it is used as seen in plan.")))
  (setq arcs  (vl-remove-if-not '(lambda (pc) (= "A" (car pc))) pieces)
        cmode (if arcs T nil))
  (cond
    ((and (null lin) (null pieces))
     (princ "\nSelect a line and/or a curve.") (exit))
    ((and (null cmode) (null lin))
     (princ (strcat "\nNo arc was selected and there is no base line -"
                    " select an arc, a circle, or the base line."))
     (exit))
    ((and (null cmode) pieces)
     (princ (strcat "\nNote: the selected polyline has no arc segments;"
                    " using the line as the base line."))))
  (if lin
    (setq lp1 (list (car lp1) (cadr lp1) 0.0)
          lp2 (list (car lp2) (cadr lp2) 0.0)))

  ;; ---- 2. measuring axis -----------------------------------------------
  ;; SP  = start point of the axis (treads measured from here)
  ;; DIR = direction the steps march (unit)
  ;; U   = direction the step widths run (unit, perpendicular to DIR)
  (cond

    ;; CURVE selected: steps go INTO the curve
    (cmode
     (if lin
       ;; axis line given: start where the line meets the curve, treads
       ;; run along the line, widths perpendicular to it
       (progn
         (setq dir (hs-unit (hs-vec lp1 lp2)))
         (if (null dir)
           (progn (princ "\nThe selected line has zero length.") (exit)))
         ;; prefer a crossing on the drawn segment, then an arc piece,
         ;; then the crossing nearest the line's far end
         (foreach hp (hs-hits lp1 dir pieces)
           (setq bscr (+ (* 1e6 (hs-ptseg (car hp) lp1 lp2))
                         (if (= "A" (car (cdr hp))) 0.0 1e3)
                         (* 1e-3 (distance (car hp) lp2))))
           (if (or (null sp) (< bscr best))
             (setq sp (car hp) spc (cdr hp) best bscr)))
         (if (null sp)
           (progn (princ "\nThe line does not reach the curve.") (exit)))
         (setq inref (if (= "A" (car spc)) (cadr spc)))
         (if inref
           (progn
             (if (< (abs (hs-dot dir (hs-vec sp inref))) 1e-9)
               (progn (princ (strcat "\nThe line is tangent to the curve"
                                     " - cannot tell which way is into it."))
                      (exit)))
             (if (< (hs-dot dir (hs-vec sp inref)) 0.0)
               (setq dir (hs-scl dir -1.0))))
           ;; the line lands on a straight part - ask which way to go
           (progn
             (princ "\nThe line meets a straight part of the curve.")
             (while (null side)
               (setq pt (getpoint (trans sp 0 1)
                          "\nPick a point on the side the steps go: "))
               (if (null pt)
                 (progn (princ "\nNo direction picked - nothing drawn.")
                        (exit)))
               (setq side (hs-dot (hs-vec sp (trans pt 1 0)) dir))
               (if (< (abs side) 1e-10)
                 (progn (princ "\nThat point is square to the line - pick again.")
                        (setq side nil))))
             (if (< side 0.0) (setq dir (hs-scl dir -1.0)))))
         (princ "\nMeasuring from where the line meets the curve, into the curve."))
       ;; no axis line
       (if (= 1 (length arcs))
         ;; a single arc: start at its middle, widths along the tangent
         (progn
           (setq spc (car arcs)
                 sp  (hs-arcpt (cadr spc) (caddr spc)
                               (* 0.5 (+ (cadddr spc) (nth 4 spc))))
                 dir (hs-unit (hs-vec sp (cadr spc))))
           (princ "\nMeasuring from the middle of the arc, into the curve."))
         ;; a composite curve: too many arcs to guess a middle
         (progn
           (while (null sp)
             (setq pt (getpoint
                        "\nPick the point on the curve to measure from: "))
             (if (null pt)
               (progn (princ "\nNothing picked - nothing drawn.") (exit)))
             (setq pt   (trans pt 1 0)
                   best nil)
             (foreach pc arcs                    ; nearest arc piece
               (setq bscr (abs (- (distance (cadr pc) pt) (caddr pc))))
               (if (or (null best) (< bscr best)) (setq best bscr spc pc)))
             (setq sp  (hs-arcpt (cadr spc) (caddr spc)
                                 (angle (cadr spc) pt))
                   dir (hs-unit (hs-vec sp (cadr spc)))))
           (princ "\nMeasuring from the picked point on the curve, into the curve."))))
     (setq u (hs-unit (hs-perp dir))))

    ;; LINE only: the classic base-line mode
    (T
     (setq sp (hs-mid2 lp1 lp2)
           u  (hs-unit (hs-vec lp1 lp2)))
     (if (null u)
       (progn (princ "\nThe selected line has zero length.") (exit)))
     (while (null dir)
       (setq pt (getpoint (trans sp 0 1)
                          "\nPick a point on the side the steps go: "))
       (if (null pt)
         (progn (princ "\nNo direction picked - nothing drawn.") (exit)))
       (setq side (hs-dot (hs-vec sp (trans pt 1 0)) (hs-perp u)))
       (if (< (abs side) 1e-10)
         (princ "\nThat point is on the line - pick a point to one side.")
         (setq dir (hs-unit (hs-scl (hs-perp u)
                                    (if (< side 0.0) -1.0 1.0))))))))

  ;; preview the measuring axis and the step direction
  (setq reflen (if lin (distance lp1 lp2) (* 2.0 (caddr (car arcs)))))
  (grdraw (trans sp 0 1)
          (trans (hs-add sp (hs-scl dir (* 0.75 reflen))) 0 1) 4 0)
  (grdraw (trans (hs-add sp (hs-scl u (* 0.25 reflen))) 0 1)
          (trans (hs-add sp (hs-scl u (* -0.25 reflen))) 0 1) 2 0)

  ;; ---- 3. dimension the steps? -----------------------------------------
  (if (null (setq fkey (hs-fkw 'dims "Yes No" "Yes")))
    (progn
      (initget "Yes No")
      (setq fkey (getkword "\nDimension the steps? [Yes/No] <Yes>: "))))
  (setq dimflag (/= "No" fkey))
  (if dimflag
    (progn
      (setq oldstyle (getvar "DIMSTYLE")) ; restored when the command ends
      (if (not (tblsearch "DIMSTYLE" *cs-depth-dimstyle*))
        (princ (strcat "\nNote: dim style \"" *cs-depth-dimstyle*
                       "\" not found - step treads use the current style.")))
      (if (not (tblsearch "DIMSTYLE" *cs-width-dimstyle*))
        (princ (strcat "\nNote: dim style \"" *cs-width-dimstyle*
                       "\" not found - step widths use the current style.")))
      (if (and *cs-dim-layer* (not (cal:layer-usable-p *cs-dim-layer*)))
        (princ (strcat "\nNote: dim layer \"" *cs-dim-layer*
                       "\" is missing or not drawable - using the"
                       " current layer.")))))

  ;; ---- 4. widths and step treads, chord by chord -----------------------
  (command "_.UNDO" "_Begin")
  (setq undoflag T cum 0.0 n 1 drawn 0
        pprev sp                        ; tread chain starts at the axis
        offd  (* 2.0 txth)              ; tread-dim offset off the axis
        oldce (getvar "CMDECHO"))
  (setvar "CMDECHO" 0)                  ; quiet the dimstyle/dim commands

  ;; In base-line mode the first width sits AT the wall: it is the top
  ;; of the run, so no chord is drawn there (the wall already is one),
  ;; but it is dimensioned and it anchors both ends of the boundary.
  ;; In the curve modes the width at the start is set by the curve, so
  ;; the run begins straight away with a step tread.
  (if (not cmode)
    (progn
      (if (hs-fhas 'wallwidth)
        ;; nil = no width at the wall, what Enter means there
        (setq wid (hs-fnum 'wallwidth))
        (progn
          (initget 6)
          (setq wid (getdist "\nWidth of the step at the wall <Enter = none>: "))))
      (if wid
        (progn
          (setq wallA   (hs-add sp (hs-scl u (* 0.5 wid)))
                wallB   (hs-add sp (hs-scl u (* -0.5 wid)))
                lastwid wid)
          (if dimflag
            (hs-dim *cs-width-dimstyle* wallA wallB
                    (hs-add sp (hs-scl dir (- (+ (* 0.5 wid)
                                                 (* 1.5 txth)))))))
          (princ (strcat "\n  Width at the wall: " (rtos wid) "."))))))

  (while
    (and (not stopf)
         (progn
           (setq dep 'RETRY)
           (while (eq dep 'RETRY)
             (cond
               ;; the form gave the step COUNT: past it the run stops
               ;; itself - the auto-done no prompt ever offered
               ((and fsteps (> n fsteps)) (setq dep nil))
               ;; this step's tread from the form, spent as it is
               ;; read - a Back onto it re-asks at the keyboard
               ((hs-fhas (hs-fnkey "tread" n))
                (setq dep (hs-fnum (hs-fnkey "tread" n))))
               (T
                ;; Undo is the old keyword, kept as a hidden synonym
                (initget 6 (strcat "Back" (if lastdep " Same" "") " Undo"))
                (setq dep (getdist
                            (strcat "\nStep " (itoa n)
                                    " - step tread [Back"
                                    (if lastdep "/Same" "") "]"
                                    " <Enter = done>: ")))
                (if (= (type dep) 'STR)
                  (cond
                    ((or (= dep "Back") (= dep "Undo"))
                     (hs-popstep) (setq dep 'RETRY))
                    ((= dep "Same")
                     (if lastdep
                       (setq dep lastdep)
                       (progn (princ "\n  No previous step tread.")
                              (setq dep 'RETRY))))
                    (T (setq dep 'RETRY)))))))
           dep))
    (setq wid 'RETRY)
    (while (eq wid 'RETRY)
      (if (hs-fhas (hs-fnkey "width" n))
        ;; the form's width, spent as it is read; nil reads as Enter -
        ;; fit to the curve, repeat the previous width, or (line mode,
        ;; first step) fall back to the keyboard, its key now spent
        (setq wid (hs-fnum (hs-fnkey "width" n)))
        (progn
          (initget 6)
          (setq wid (getdist (strcat "\nStep " (itoa n) " - step width "
                                     (cond
                                       (cmode "<Enter = fit to the curve>: ")
                                       (lastwid (strcat "<Enter = "
                                                        (rtos lastwid) ">: "))
                                       (T ": ")))))))
      (if (null wid)
        (cond
          (cmode   (setq wid 'FIT))
          (lastwid (setq wid lastwid))
          (T (princ "\n  A width is needed for this step.")
             (setq wid 'RETRY)))))
    (if (null dep)
      (progn
        (princ "\nNo step tread given - step discarded; finishing.")
        (setq stopf T))
      (progn
        (setq mark (entlast)
              svcum cum svp pprev svn n svea ea sveb eb
              lastdep dep
              ;; each step sits DEP past the PREVIOUS step edge, never
              ;; a running total from the start
              p    (hs-add pprev (hs-scl dir dep))
              e1   nil
              e2   nil)
        (if cmode
          ;; hold as true to the curve as the tolerance allows
          (progn
            (setq op  (hs-open p u pieces)
                  nat (if op (caddr op)))
            (cond
              ;; Enter on width -> fit this step to the curve
              ((eq wid 'FIT)
               (if op
                 (progn
                   (setq e1 (car op) e2 (cadr op))
                   (princ (strcat "\n  Step " (itoa n)
                                  ": fitted to the curve, width = "
                                  (rtos (caddr op)) ".")))
                 (princ (strcat "\n  Step " (itoa n)
                                ": the curve does not reach this distance"
                                " - step skipped."))))
              ((and nat (<= (abs (- nat wid)) tol))
               (setq e1 (car op) e2 (cadr op))
               (princ (strcat "\n  Step " (itoa n) ": curve opening "
                              (rtos nat) " is within " (rtos tol) " of "
                              (rtos wid) " - snapped to the curve.")))
              (T
               ;; center on the curve's opening so the step breaks it
               ;; equally on both sides; on the axis when there is none
               (setq cen (if op (hs-mid2 (car op) (cadr op)) p)
                     e1  (hs-add cen (hs-scl u (* 0.5 wid)))
                     e2  (hs-add cen (hs-scl u (* -0.5 wid))))
               (princ (strcat "\n  Step " (itoa n) ": width " (rtos wid)
                              " held"
                              (if nat
                                (strcat " (curve opening " (rtos nat) ")")
                                " (the curve does not reach this distance)")
                              " - step breaks from the curve.")))))
          ;; classic base-line mode: centered on the axis as given
          (progn
            (setq e1 (hs-add p (hs-scl u (* 0.5 wid)))
                  e2 (hs-add p (hs-scl u (* -0.5 wid))))))
        (if (and e1 e2)
          (progn
            (setq cum (+ cum dep))             ; running total (echo + profile)
            (princ (strcat "\n  Step " (itoa n) ": " (rtos dep)
                           " past the previous step ("
                           (rtos cum) " from the start)."))
            (hs-mkline e1 e2)                  ; the chord (step edge)
            (setq ea (append ea (list e1))     ; remember the ends for
                  eb (append eb (list e2)))    ; the boundary polyline
            (if dimflag
              (progn
                ;; step width: across the chord, nested behind the start
                ;; of the axis by half the chord's own width so the
                ;; wider steps sit progressively further out
                (hs-dim *cs-width-dimstyle* e1 e2
                        (hs-add sp
                                (hs-scl dir
                                        (- (+ (* 0.5 (distance e1 e2))
                                              (* 1.5 txth))))))
                ;; step tread: chain link along the axis, from the
                ;; previous step edge (the start for step 1) to here
                (hs-dim *cs-depth-dimstyle* pprev p
                        (hs-add (hs-mid2 pprev p) (hs-scl u offd)))))
            (setq pprev p drawn (1+ drawn)
                  lastwid (distance e1 e2)
                  tlist (cons cum tlist)       ; axis distances, newest first
                  slog  (cons (list (hs-since mark) svcum svp svn svea sveb)
                              slog))))
        (setq n (1+ n)))))

  ;; ---- 5. boundary curve through the step ends -------------------------
  ;; The hemisphere is rebuilt as one polyline of arc segments running
  ;; through every step end.  In base-line mode it starts and finishes
  ;; at the wall (the width given at the wall) and bulges out to a crown
  ;; set by one last distance.  In the curve modes the crown is the point
  ;; where the measuring axis meets the selected curve, so the arc
  ;; beside it is fitted through that original point.
  (if (> drawn 0)
    (progn
      (if (not cmode)
        (progn
          (if (hs-fhas 'crown)
            ;; nil = no crown distance, what Enter means there
            (setq dep (hs-fnum 'crown))
            (progn
              (initget 6)
              (setq dep (getdist (strcat "\nDistance from the last step to the back"
                                         " of the curve <Enter = none>: ")))))
          (if (and dep (= (type dep) 'REAL))
            (progn
              (setq crown (hs-add pprev (hs-scl dir dep)))
              (if dimflag                    ; last link of the tread chain
                (hs-dim *cs-depth-dimstyle* pprev crown
                        (hs-add (hs-mid2 pprev crown)
                                (hs-scl u offd))))))
          ;; wallA - side A - crown - side B - wallB
          (setq pts (append (if wallA (list wallA))
                            ea
                            (if crown (list crown))
                            (reverse eb)
                            (if wallB (list wallB)))
                ;; index of the crown vertex, for the arc fitting
                kx  (if crown
                      (+ (length ea) (if wallA 1 0)))))
        (progn
          (if (null (setq fkey (hs-fkw 'boundary "Yes No" "Yes")))
            (progn
              (initget "Yes No")
              (setq fkey (getkword (strcat "\nDraw the reconstructed boundary"
                                           " through the step ends? [Yes/No]"
                                           " <Yes>: ")))))
          (if (/= "No" fkey)
            ;; Deepest step - side A - across the first step - side B.
            ;; The start point is NOT made a vertex: near the crown the
            ;; curve's opening is narrow, so forcing the boundary through
            ;; it would spike inward whenever the first step is wider
            ;; than the curve there.  Instead the segment spanning the
            ;; first step carries the ORIGINAL curve's own bulge, which
            ;; traces the crown exactly when that step sits on the curve.
            (progn
              (setq pts (append (reverse ea) eb))
              (if (and spc (= "A" (car spc)))
                (setq fx (list (cons (1- (length ea))
                                     (hs-firstspan (car ea) (car eb)
                                                   spc sp)))))))))
      (if (and pts (> (length pts) 1))
        (progn
          (setq bmark (entlast))       ; the boundary is this run's wall
          (hs-mkpoly pts (hs-blgs pts kx fx))
          (setq bsides (hs-since bmark))
          (princ (strcat "\nBoundary polyline drawn through the step ends"
                         (cond ((not cmode)
                                (if wallA ", held to the wall" ""))
                               (T ", held to the original point"))
                         "."))))))

  ;; ---- 6. side profile -------------------------------------------------
  ;; The plan run seen from the side: alternating vertical drops (the
  ;; step depths) and horizontal step treads, drawn in world X/Y from a
  ;; picked top-of-wall point.  Still inside the command's UNDO group,
  ;; and before the entry dim style is restored - the profile dims use
  ;; *cs-depth-dimstyle* too.
  (if (> drawn 0)
    (progn
      (if (null (setq fkey (hs-fkw 'profile "Yes No" "Yes")))
        (progn
          (initget "Yes No")
          (setq fkey (getkword "\nAdd a side profile? [Yes/No] <Yes>: "))))
      (if (/= "No" fkey)
        (progn
          ;; step treads, top step first: sort the logged axis distances
          ;; ascending and take successive differences
          (setq srt    (vl-sort tlist '<)
                treads (list (car srt))
                pv     (car srt))
          (foreach td (cdr srt)
            (if (> (- td pv) 1e-6)
              (setq treads (append treads (list (- td pv)))))
            (setq pv td))
          (setq tcount (length treads))
          ;; the depths, top step first, with Back (Undo accepted
          ;; too): one per step PLUS one more for the drop after the
          ;; last tread, so 3 steps take 4 depths
          (setq jx 1 drops nil)
          (while (<= jx (1+ tcount))
            ;; depth1..depthN and depthafter can come off the form,
            ;; spent as they are read; nil reads as Enter, which the
            ;; first depth refuses - that one falls back to the
            ;; keyboard, its key now spent
            (setq fkey (if (> jx tcount) 'depthafter (hs-fnkey "depth" jx)))
            (setq dd (if (hs-fhas fkey) (hs-fnum fkey) 'RETRY))
            (if (or (eq dd 'RETRY) (and (null dd) (= jx 1)))
              (progn
                (if (= jx 1)
                  (initget 7 "Back Undo")
                  (initget 6 "Back Undo"))
                (setq dd (getdist
                           (cond
                             ((= jx 1) "\nStep 1 - step depth (the drop): ")
                             ((> jx tcount)
                              (strcat "\nDepth after the last tread [Back] <"
                                      (rtos (car drops)) ">: "))
                             (T (strcat "\nStep " (itoa jx)
                                        " - step depth [Back] <"
                                        (rtos (car drops)) ">: ")))))))
            (cond
              ((and (= (type dd) 'STR)
                    (or (= dd "Back") (= dd "Undo")))
               (if (= jx 1)
                 (princ "\n  Already at the first step.")
                 (progn (princ "\n  Stepping back one step.")
                        (setq drops (cdr drops) jx (1- jx)))))
              ((null dd)                       ; Enter = same as previous
               (setq drops (cons (car drops) drops) jx (1+ jx)))
              (T
               (setq drops (cons dd drops) jx (1+ jx)))))
          (setq drops (reverse drops))
          ;; Placement.  The profile always runs DOWN AND TO THE LEFT
          ;; from the pick, so there is no side to ask about.
          (setq ptop (getpoint (strcat "\nPick the top of the first tread"
                                       " for the side profile: ")))
          (if (null ptop)
            (princ "\nNo point picked - side profile skipped.")
            (progn
              (setq totdrop 0.0 totrun 0.0)
              (foreach dd drops (setq totdrop (+ totdrop dd)))
              (foreach td treads (setq totrun (+ totrun td)))
              ;; The alternating drop/tread silhouette in world X/Y,
              ;; keeping the corner down its high side at every level:
              ;; the pick, then the foot of each drop.  Those corners
              ;; are what the dims bind to.
              (setq ptop (trans ptop 1 0)
                    px   (car ptop)
                    py   (cadr ptop)
                    jx   0
                    cnrs (list (list px py 0.0)))
              (foreach td treads
                (setq dd (nth jx drops))
                (hs-mkline (list px py 0.0) (list px (- py dd) 0.0))
                (setq py   (- py dd)
                      cnrs (cons (list px py 0.0) cnrs))
                ;; the tread runs left, and carries no dim of its own -
                ;; the depths and the overall depth say it all
                (hs-mkline (list px py 0.0) (list (- px td) py 0.0))
                (setq px (- px td)
                      jx (1+ jx)))
              ;; the last depth: the drop after the last tread
              (setq dd (nth jx drops))
              (hs-mkline (list px py 0.0) (list px (- py dd) 0.0))
              (setq py   (- py dd)
                    cnrs (reverse (cons (list px py 0.0) cnrs)))
              (if dimflag
                (progn
                  ;; Every depth dim stands the same distance right of
                  ;; the corner its drop lands on, so the dims climb up
                  ;; and to the right with the steps instead of stacking
                  ;; in one chain.  Clearing the widest tread is what
                  ;; keeps BOTH extension lines running forward, out of
                  ;; the flight; the gap on top of that is what makes
                  ;; the fan readable, and *cs-profile-dimgap* sets it.
                  ;; four text heights, or three quarters of a tread -
                  ;; whichever is more, so the fan keeps its proportions
                  ;; whether or not the drawing has a dim scale set up
                  (setq pgap (cond ((numberp *cs-profile-dimgap*)
                                    *cs-profile-dimgap*)
                                   ((max (* 4.0 txth)
                                         (* 0.75 (apply 'max treads)))))
                        pfo  (+ (apply 'max treads) pgap)
                        jx   1)
                  (while (< jx (length cnrs))
                    (setq e1 (nth (1- jx) cnrs)
                          e2 (nth jx cnrs))
                    (hs-dimv *cs-depth-dimstyle* e1 e2
                             (list (+ (car e2) pfo)
                                   (* 0.5 (+ (cadr e1) (cadr e2))) 0.0))
                    (setq jx (1+ jx)))
                  ;; the overall depth, further out again - the whole
                  ;; diagonal, top corner to bottom corner
                  (hs-dimv *cs-depth-dimstyle* (car cnrs) (last cnrs)
                           (list (+ (car ptop) pfo pgap)
                                 (- (cadr ptop) (* 0.5 totdrop)) 0.0))))
              (princ (strcat "\nSide profile drawn: " (itoa tcount)
                             " step(s), " (itoa (length drops))
                             " depths, down to the left; total run "
                             (rtos totrun) ", overall depth "
                             (rtos totdrop) "."))))))))

  ;; ---- 7. done ---------------------------------------------------------
  (if (zerop drawn)
    (princ "\nNo steps drawn.")
    (princ (strcat "\n" (itoa drawn)
                   " step(s) drawn, parallel and centered on the axis.")))
  (redraw)
  (if oldstyle (hs-setstyle oldstyle))   ; back to the entry dim style
  (command "_.UNDO" "_End")
  (if oldce (setvar "CMDECHO" oldce))
  (if oldlu (setvar "LUNITS" oldlu))
  (setq undoflag nil)

  ;; ---- 8. bead the steps -----------------------------------------------
  ;; AUTOBEAD does the beading, on its own rules and in its own undo
  ;; group - which is why this sits outside ours: AutoCAD does not nest
  ;; undo groups, so one U undoes the beads and the next undoes the
  ;; steps.  Every tread is beaded; the only question left is which
  ;; steps carry the bead along their side walls, and that is answered
  ;; by step number here instead of by clicking each one.
  (if (> drawn 0)
    (if (not (boundp 'autobead-build))
      (princ (strcat "\nAUTOBEAD is not loaded - APPLOAD AUTOBEAD.lsp"
                     " if you want these steps beaded."))
      (progn
        (if (null (setq fkey (hs-fkw 'bead "Yes No" "Yes")))
          (progn
            (initget "Yes No")
            (setq fkey (getkword "\nBead the steps? [Yes/No] <Yes>: "))))
        (if (/= "No" fkey)
          (progn
            (setq btreads (hs-treadents slog)
                  bnums   nil)
            (if (null btreads)
              (princ "\nNo tread lines to bead.")
              (progn
                ;; every tread is beaded - the side walls are the question
                (initget "All Some")
                (setq bside (cond ((getkword (strcat "\nWhich steps have"
                                                     " beaded side walls?"
                                                     " [All/Some] <All>: ")))
                                  ("All")))
                (if (= bside "Some")
                  (progn
                    (princ (strcat "\n  Steps drawn: "
                                   (hs-numsay btreads)))
                    (setq bnums (hs-numlist
                                  (getstring T (strcat "\nStep numbers with"
                                                       " beaded sides: "))))
                    (setq bnums (vl-remove-if-not
                                  '(lambda (k) (assoc k btreads)) bnums))
                    (if (null bnums)
                      (progn
                        (princ (strcat "\n  No step numbers recognized -"
                                       " beading every side wall full"
                                       " length."))
                        (setq bside "All")))))
                (setq bdir (getpoint "\nClick the side to bead toward: "))
                (if (null bdir)
                  (princ "\nNo direction picked - nothing beaded.")
                  (progn
                    ;; the treads, anything the run drew for its walls,
                    ;; and the lines it came off: the pool lines of this
                    ;; pocket, which is what AUTOBEAD beads
                    (setq bss (ssadd))
                    (foreach pr btreads (ssadd (cdr pr) bss))
                    (foreach be bsides
                      (if (and be (entget be)) (ssadd be bss)))
                    (setq i 0)
                    (while (< i (sslength ss))
                      (ssadd (ssname ss i) bss)
                      (setq i (1+ i)))
                    (autobead-ensure-layer *autobead-layer*)
                    (autobead-build
                      bss bdir
                      (= bside "Some")
                      (if (= bside "Some")
                        (mapcar '(lambda (k)
                                   (hs-entmid (cdr (assoc k btreads))))
                                bnums)
                        nil)))))))))))
  (hs-fclear)                       ; both exits clear the form store
  (princ))

;;; --------------------------- tutorial ---------------------------------

(defun hs-tut-pause ( )
  (princ "\n      --- press Enter to continue ---")
  (getstring)
  (princ))

(defun hs-tut-text (pt h s)
  (entmake (list '(0 . "TEXT")
                 (cons 10 (list (car pt) (cadr pt) 0.0))
                 (cons 40 h)
                 (cons 1 s))))

;; Walkthrough for new users: pages of what HEMISTEP does and checks,
;; then a live demonstration drawn step by step with the same geometry
;; code the real command uses - the numbers are the reference example
;; this routine was built against.
(defun c:TUTORIALHEMISTEP ( / *error* undoflag oldce oldstyle org sp u dir
                              txth pt wallw wallA wallB ea eb pprev p cum
                              e1 e2 offd n lst wid dep crown pts kx)
  (defun *error* (msg)
    (if undoflag (command-s "_.UNDO" "_End"))
    (if oldstyle (hs-setstyle oldstyle))
    (if oldce (setvar "CMDECHO" oldce))
    (princ))

  (princ (strcat "\n================ HEMISTEP TUTORIAL " *hs-version*
                 " ================"))
  (princ "\nHEMISTEP draws steps that act like chords inside a circle:")
  (princ "\nparallel step edges centered on a measuring axis, plus the")
  (princ "\nhemisphere boundary itself, rebuilt as one polyline of arc")
  (princ "\nsegments through every step end.")
  (hs-tut-pause)
  (princ "\nWHAT YOU SELECT DECIDES THE MODE")
  (princ "\n  LINE only ....... steps centered on the line, marching away")
  (princ "\n                    from it on the side you pick")
  (princ "\n  CURVE + LINE .... the line is the measuring axis; treads")
  (princ "\n                    start where it meets the curve, going in")
  (princ "\n  CURVE only ...... from the middle of the arc, going in")
  (princ "\n  (a curve may be an arc, circle, or polyline - including a")
  (princ "\n   composite hemisphere and a boundary this command drew)")
  (princ "\nTHE PROMPTS, IN ORDER")
  (princ "\n  1. LINE mode first asks the width of the step AT THE WALL -")
  (princ "\n     it anchors the boundary; no chord is drawn there.")
  (princ "\n  2. Then STEP TREAD, WIDTH, repeating.  Every step tread is")
  (princ "\n     from the previous step - never a running total.  Enter at")
  (princ "\n     a step tread = done; Back steps back one step; Same repeats.")
  (princ "\n     Enter at a width fits the step to the curve (curve modes)")
  (princ "\n     or repeats the previous width (line mode).")
  (princ "\n  3. One last distance to the back of the curve places the crown,")
  (princ "\n     and the boundary polyline is drawn through the step ends.")
  (princ "\n  4. Finally you may add a SIDE PROFILE: give the step depths")
  (princ "\n     (top step first, plus the drop after the last tread, so")
  (princ "\n     3 steps take 4 depths; Back supported), then pick the")
  (princ "\n     top of the first tread.  The flight always runs down and")
  (princ "\n     to the LEFT from there, so the steps rise to the right")
  (princ "\n     and the dims climb with them - each depth beside its own")
  (princ "\n     step, the overall further out; the treads are not dimmed.")
  (princ "\n  5. Bead the steps? [Yes/No] - every tread is beaded, so the")
  (princ "\n     only question is which steps have beaded SIDE WALLS:")
  (princ "\n     [All/Some], and Some takes the step numbers (\"1 3 4\").")
  (princ "\n     Then click the side to bead toward and AUTOBEAD does the")
  (princ "\n     rest on its own rules - it has to be loaded for this.")
  (hs-tut-pause)
  (princ "\nWHAT IT CHECKS AND HANDLES FOR YOU")
  (princ "\n  - warns on tilted UCS / non-flat lines / unusable layer")
  (princ "\n  - bare numbers read as inches; 1'4 style works anywhere")
  (princ "\n  - in the curve modes a width within 1/8\" of the curve's")
  (princ "\n    opening snaps to the curve; any other width is held and")
  (princ "\n    breaks the curve EQUALLY at both ends")
  (princ "\n  - each step measures against whichever part of a composite")
  (princ "\n    curve it lands on, nearest the axis")
  (princ "\n  - the boundary's arcs are fitted so the crown sits inside")
  (princ "\n    ONE arc, and a segment that would fold back is refused")
  (princ "\n  - dims: step treads chained along the axis (STANDARD INCHES),")
  (princ "\n    widths nested behind the start (SIDE STANDARD); one undo")
  (hs-tut-pause)

  (initget "Yes No")
  (if (= "No" (getkword (strcat "\nDraw a demonstration in this drawing?"
                                " [Yes/No] <Yes>: ")))
    (progn (princ "\nTutorial done - type HEMISTEP to use it for real.")
           (exit)))
  (setq pt (getpoint "\nPick a clear spot (about 300 x 150 needed): "))
  (if (null pt)
    (progn (princ "\nNo spot picked - tutorial done.") (exit)))
  (setq org  (trans pt 1 0)
        txth (hs-txth)
        sp   org                       ; middle of the base line
        u    '(1.0 0.0 0.0)
        dir  '(0.0 1.0 0.0)
        wallw 257.61)
  (command "_.UNDO" "_Begin")
  (setq undoflag T
        oldce (getvar "CMDECHO")
        oldstyle (getvar "DIMSTYLE"))
  (setvar "CMDECHO" 0)

  (hs-mkline (hs-add sp (hs-scl u -140.0)) (hs-add sp (hs-scl u 140.0)))
  (hs-tut-text (hs-add org '(-135.0 -14.0 0.0)) (* 1.2 txth)
               "HEMISTEP demo: base-line mode - select this wall line")
  (princ "\n[1] The WALL drawn - in line mode this is all you select.")
  (princ "\n    Steps center on its middle and march off the side you")
  (princ "\n    pick.  The width at the wall here is 257.61 - it anchors")
  (princ "\n    both ends of the boundary but draws no chord.")
  (setq wallA (hs-add sp (hs-scl u (* 0.5 wallw)))
        wallB (hs-add sp (hs-scl u (* -0.5 wallw)))
        offd  (* 2.0 txth)
        pprev sp
        cum   0.0
        n     1)
  (hs-tut-pause)

  (foreach lst '((240.0 . 13.0) (216.0 . 12.0) (168.0 . 16.0)
                 (120.0 . 10.0))
    (setq wid (car lst)
          dep (cdr lst)
          p   (hs-add pprev (hs-scl dir dep))
          cum (+ cum dep)
          e1  (hs-add p (hs-scl u (* 0.5 wid)))
          e2  (hs-add p (hs-scl u (* -0.5 wid))))
    (hs-mkline e1 e2)
    (setq ea (append ea (list e1))
          eb (append eb (list e2)))
    (hs-dim *cs-width-dimstyle* e1 e2
            (hs-add sp (hs-scl dir (- (+ (* 0.5 wid) (* 1.5 txth))))))
    (hs-dim *cs-depth-dimstyle* pprev p
            (hs-add (hs-mid2 pprev p) (hs-scl u offd)))
    (princ (strcat "\n[" (itoa (1+ n)) "] Step " (itoa n) ": width "
                   (rtos wid) ", " (rtos dep) " past the previous edge ("
                   (rtos cum) " from the wall).  Parallel to the wall,"
                   " centered on the axis."))
    (hs-tut-pause)
    (setq pprev p n (1+ n)))

  (setq crown (hs-add pprev (hs-scl dir 9.45)))
  (hs-dim *cs-depth-dimstyle* pprev crown
          (hs-add (hs-mid2 pprev crown) (hs-scl u offd)))
  (setq pts (append (list wallA) ea (list crown) (reverse eb) (list wallB))
        kx  (+ 1 (length ea)))
  (hs-mkpoly pts (hs-blgs pts kx nil))
  (princ "\n[6] One last distance (9.45) places the CROWN, and the boundary")
  (princ "\n    polyline is drawn: wall - step ends - crown - step ends -")
  (princ "\n    wall, in arc segments fitted so the apex sits inside one")
  (princ "\n    arc.  This is the hemisphere the steps sit in.")
  (hs-tut-pause)

  (if oldstyle (hs-setstyle oldstyle))
  (command "_.UNDO" "_End")
  (setq undoflag nil)
  (setvar "CMDECHO" oldce)
  (princ "\n[7] Done.  One U removes the demo.  For the curve modes, draw")
  (princ "\n    an arc and run HEMISTEP selecting it (plus an axis line if")
  (princ "\n    you have one) - Enter at any width fits that step to the")
  (princ "\n    curve exactly.")
  (princ))

(princ (strcat "\nHEMISTEP.lsp " *hs-version*
               " loaded - HEMISTEP to draw hemisphere steps,"
               " TUTORIALHEMISTEP to learn it."))
(princ)


;;; ======================================================================
;;; >>> NORMIESTEP.lsp
;;; ======================================================================

;;; ======================================================================
;;; NORMIESTEP.lsp
;;; ----------------------------------------------------------------------
;;; The most normal, boring pool steps of all time: straight, parallel
;;; treads of one constant width.
;;; Written for AutoCAD 2018 (plain AutoLISP + ActiveX for dim styles).
;;;
;;; LOAD:     APPLOAD this file (or drag it into the drawing window).
;;; COMMAND:  NORMIESTEP
;;;
;;; WHAT IT DOES
;;;   Every step is the same width - that is the whole point.  What you
;;;   select decides where the run sits:
;;;
;;;   ONE LINE ......... the steps are CENTERED on that line.  You pick
;;;                      which side they go, give the width once, then
;;;                      the step treads.  The side walls leave the wall
;;;                      square and run to the last tread; the corner
;;;                      treatment sits on the last step.
;;;   TWO LINES (a corner)
;;;                      the steps sit against the corner and always run
;;;                      OUTWARD from it.  You are asked which of the two
;;;                      lines the steps run off of - the same line the
;;;                      back-corner offset is measured on; the treads run
;;;                      parallel to it and butt against the other one.
;;;   A "U" ............ the outline the steps sit in is already drawn,
;;;                      so the treads are just filled in.  The BASE of
;;;                      the U - its closed end - is the wall the steps
;;;                      come off: the run STARTS there and marches out
;;;                      toward the open end, trimmed to the two arms.
;;;                      No width is asked for - the arms give it.  The
;;;                      U may already have its back corners drawn where
;;;                      the arms meet the base: three lines is a plain
;;;                      square-cornered U, five lines is one with Cut
;;;                      (diagonal) corners, and three lines plus two
;;;                      arcs is one with Radius (rounded) corners.
;;;                      Polylines work too, including bulged (rounded)
;;;                      corner segments.  Treads trim to whatever part
;;;                      of the side they land on - arm, diagonal, or
;;;                      arc.  A plain square U is asked for its back
;;;                      corners like the other modes.
;;;
;;; WORKFLOW
;;;   1.  Select the base line, the two lines of a corner, or a U-shaped
;;;       perimeter (LINEs or the straight segments of a POLYLINE).
;;;   2.  One-line mode asks which side the steps go.  Corner mode asks
;;;       which line the steps run off of.  The U needs neither.
;;;   3.  Unless it is a U, you give the step width ONCE - every step
;;;       gets it.  Then comes the corner treatment.  One-line mode asks
;;;       for the CORNERS OF THE LAST STEP - the two where the side
;;;       walls meet the last tread; the other modes ask for their BACK
;;;       CORNERS - the two where the sides of the run meet the wall it
;;;       comes off.  Either way a corner is
;;;         Square   - a true 90 degree corner (the default)
;;;         Radius   - a fillet arc, you give the radius
;;;         Cut      - a straight 45 degree diagonal, given as either
;;;                    its Offset back along each line or the Cut face
;;;                    length (each gives the other: cut = offset x
;;;                    root 2)
;;;         NotGiven - the order sheet never said.  The corner is drawn
;;;                    square, like Square, but a note on the drawing
;;;                    says it was never recorded, so nobody reads it
;;;                    as a measured 90.
;;;       In one-line mode the treatment is worked into the last step:
;;;       the last tread gives up the offset at each end, the side walls
;;;       stop that much short, and the corner piece bridges the two.
;;;       In corner mode the treatment stays at the wall and flares the
;;;       mouth of the recess the run sits in by that offset; in a U it
;;;       is cut into the corner and the treads trim to it.  A U that
;;;       already has its back corners drawn is not asked.
;;;   4.  Then step treads, one per step - each the plan-view spacing
;;;       measured FROM THE PREVIOUS TREAD (from the base line for the
;;;       first).  Distances read architectural style: a bare number is
;;;       inches (drawing units) and feet-inch entry like 1'4 (= 16")
;;;       works whatever the units setting.
;;;   5.  Enter at a step tread prompt = done.  Back steps back one
;;;       step: it removes the step just drawn (its line and its
;;;       dimensions).  Undo, the old keyword, is still accepted.  Same
;;;       repeats the previous step tread, which is what most runs want.
;;;   6.  The side lines of the run are drawn for the one-line and
;;;       corner modes.  One-line mode draws plain side walls, square
;;;       off the base wall, running from the wall to the last tread -
;;;       the treatment sits on the last step's corners, so a Radius or
;;;       Cut one stops the walls an offset short and the corner
;;;       piece finishes the trip.  In corner mode only the outer side
;;;       is drawn - with its back corner flare at the wall - since the
;;;       steps run outward from the corner and the line they sit
;;;       against closes the inner side.  That outer side runs OUTWARD
;;;       with the treads: it is the line they sit against offset by
;;;       the step width, not a line square to the base, so it still
;;;       meets every tread end where the corner is not a true 90.
;;;       The U already has its arms, so only a back corner asked for
;;;       there is drawn.
;;;   7.  Optional dimensions: the step treads chained along the run,
;;;       plus the step width once (it is the same for every step).
;;;   8.  Optionally a SIDE PROFILE: you give the STEP DEPTHS - the
;;;       vertical drops, top step first, one per step PLUS one more
;;;       for the drop after the last tread, so 3 steps take 4 depths
;;;       (Enter repeats the previous one, Back steps back) - then
;;;       pick the top of the first tread.  The flight always runs
;;;       DOWN AND TO THE LEFT from there, so there is no side to
;;;       pick.  See "The side profile" below.
;;;   9.  Finally, BEAD THE STEPS.  Every tread is beaded - that is the
;;;       assumption - so the only thing asked is which steps carry the
;;;       bead along their side walls: All of them, or Some, given by
;;;       step number.  AUTOBEAD does the work on its own rules (2"
;;;       toward the side you click, onto its Bead Track layer), so
;;;       AUTOBEAD.lsp has to be loaded; when it is not, the run says
;;;       so and finishes without beading.  The beads are their own
;;;       undo group - AutoCAD does not nest them - so one U undoes
;;;       the beads and the next undoes the steps.
;;;
;;; THE SIDE PROFILE
;;;   The flight is drawn as an alternating drop/tread silhouette in
;;;   world X/Y, always descending to the LEFT of the picked top of the
;;;   first tread and ending on the last depth - so the steps rise to
;;;   the right, the way the shop's own elevations read.
;;;   The dims climb with them, up and to the right, on the high side:
;;;     * every depth is a dim of its own, standing the same distance
;;;       right of the corner its drop lands on, so they step out with
;;;       the flight instead of stacking in one chain;
;;;     * the overall depth sits further out again;
;;;     * the treads carry no dims - the depths and the overall say it.
;;;   How far out the fan sits is *CS-PROFILE-DIMGAP* - the gap on top
;;;   of the clearance the geometry needs.  Raise it to open the dims
;;;   out further, lower it to tuck them in.
;;;   Each one is a VERTICAL LINEAR dim bound to the two step corners
;;;   that bracket the drop.  Those corners run diagonally to each
;;;   other, so binding the diagonal (rather than dimensioning the
;;;   riser line) keeps the extension lines hooked to the geometry
;;;   while the dim still reads the drop, not the slope.
;;;
;;; OPTIONAL SETTINGS (set these before running the command)
;;;   *CS-WIDTH-TOL*      width tolerance in drawing units.  When nil
;;;                       (the default) it is 1/8" converted through the
;;;                       drawing's INSUNITS setting.
;;;   *CS-DEPTH-DIMSTYLE* dim style for step-tread dims (the side
;;;                       profile's dims use it too).
;;;   *CS-WIDTH-DIMSTYLE* dim style for step-width dims.
;;;   *CS-DIM-LAYER*      layer for the dimensions.  When nil (the
;;;                       default) the current layer is used.
;;;   *CS-PROFILE-DIMGAP* how far the side profile's dims stand off the
;;;                       flight, on top of the clearance the geometry
;;;                       needs.  nil (the default) is four text
;;;                       heights or three quarters of a tread,
;;;                       whichever is more, so the fan keeps its
;;;                       proportions whether or not the drawing has a
;;;                       dim scale set up.  It also sets how much
;;;                       further out again the overall depth sits.
;;;
;;; NOTES
;;;   - Geometry is assumed to be drawn in plan view.  The routine warns
;;;     when the current UCS is not World, when a selected line is not
;;;     flat, and when the current layer is off/frozen/locked.
;;;   - Steps are drawn as LINEs on the current layer.
;;;   - One U / UNDO reverses the whole command; a bead run added at
;;;     the end is its own group, so it takes a U of its own.
;;;   - A form (the Calofin palette / LAZFORM) can pre-answer the
;;;     questions - the step COUNT included, which the prompts only
;;;     ever learn from Enter - by leaving (key . value) pairs in
;;;     *NS-FORM*; see "form answers" below.  Selections and point
;;;     picks are always made by hand.
;;; ======================================================================

;; Settings - only defined if not already set, so this file, CORNERSTP
;; and HEMISTEP stay in sync no matter which one loads first.
;;; SHARED BUILD: requires CALOFIN-LIB.lsp (load via CALOFIN-LOADER.lsp).
;;; Generic helpers live there under cal: - see STANDARDS.md.
;;;

(if (not (boundp '*cs-width-tol*))      (setq *cs-width-tol* nil))
(if (not (boundp '*cs-dim-layer*))      (setq *cs-dim-layer* nil))
(if (not (boundp '*cs-depth-dimstyle*)) (setq *cs-depth-dimstyle* "STANDARD INCHES"))
(if (not (boundp '*cs-width-dimstyle*)) (setq *cs-width-dimstyle* "SIDE STANDARD"))
;; How far the side profile's dims stand off the flight, on top of the
;; clearance the geometry itself needs.  nil = four text heights, which
;; is what the shop's own elevations read like; raise it to open the
;; fan out further, lower it to tuck the dims in.
(if (not (boundp '*cs-profile-dimgap*)) (setq *cs-profile-dimgap* nil))

(vl-load-com) ; ActiveX is used to set styles (handles names with spaces)

(setq *ns-version* "v2.6") ; printed on load and at command start so a
                           ; stale APPLOADed copy is easy to spot

;;; ------------------------- vector helpers -----------------------------

(defun ns-add (p v) (list (+ (car p) (car v)) (+ (cadr p) (cadr v)) 0.0))

(defun ns-vec (a b) (list (- (car b) (car a)) (- (cadr b) (cadr a)) 0.0))

(defun ns-scl (v s) (list (* (car v) s) (* (cadr v) s) 0.0))

(defun ns-dot (a b) (+ (* (car a) (car b)) (* (cadr a) (cadr b))))

(defun ns-unit (v / l)
  (if (> (setq l (sqrt (ns-dot v v))) 1e-10) (ns-scl v (/ 1.0 l))))

(defun ns-perp (v) (list (- (cadr v)) (car v) 0.0))

(defun ns-mid2 (a b) (list (* 0.5 (+ (car a) (car b)))
                           (* 0.5 (+ (cadr a) (cadr b)))
                           0.0))

;; distance from point P to the segment A-B
(defun ns-ptseg (p a b / d l2 t2)
  (setq d  (ns-vec a b)
        l2 (ns-dot d d))
  (if (< l2 1e-20)
    (distance p a)
    (progn
      (setq t2 (/ (ns-dot (ns-vec a p) d) l2))
      (cond ((< t2 0.0) (distance p a))
            ((> t2 1.0) (distance p b))
            (T (distance p (ns-add a (ns-scl d t2))))))))

;; how far point P lies beyond the ends of segment A-B (0.0 when on it)
(defun ns-beyond (p a b / d l t2)
  (setq d (ns-vec a b)
        l (sqrt (ns-dot d d)))
  (if (< l 1e-10)
    (distance p a)
    (progn
      (setq t2 (/ (ns-dot (ns-vec a p) d) (* l l)))
      (cond ((< t2 0.0) (* (- t2) l))
            ((> t2 1.0) (* (- t2 1.0) l))
            (T 0.0)))))

;; endpoint of segment S farther from PT
(defun ns-far (s pt)
  (if (> (distance (car s) pt) (distance (cadr s) pt)) (car s) (cadr s)))

;; nearest segment in SEGS to point PT
(defun ns-nearseg (segs pt / best bd d s)
  (foreach s segs
    (setq d (ns-ptseg pt (car s) (cadr s)))
    (if (or (null best) (< d bd)) (setq best s bd d)))
  best)

;;; --------------------- geometry from entities -------------------------

;; Straight segments of a POLYLINE as (p1 p2 ename), points in WCS.
;; Bulged segments are skipped - this routine is all straight lines.
(defun ns-plsegs (en / ed el cl vs bs i m out v1 v2 pr sub)
  (setq ed (entget en)
        el (cond ((cdr (assoc 38 ed))) (0.0))
        cl (= 1 (logand 1 (cond ((cdr (assoc 70 ed))) (0)))))
  (if (= "LWPOLYLINE" (cdr (assoc 0 ed)))
    (foreach pr ed
      (cond
        ((= 10 (car pr))
         (setq vs (cons (trans (list (car (cdr pr)) (cadr (cdr pr)) el) en 0) vs)
               bs (cons 0.0 bs)))
        ((= 42 (car pr))
         (if bs (setq bs (cons (cdr pr) (cdr bs)))))))
    (progn
      (setq sub (entnext en))
      (while (and sub (= "VERTEX" (cdr (assoc 0 (entget sub)))))
        (setq ed  (entget sub)
              vs  (cons (trans (cdr (assoc 10 ed)) en 0) vs)
              bs  (cons (cond ((cdr (assoc 42 ed))) (0.0)) bs)
              sub (entnext sub)))))
  (setq vs (reverse vs) bs (reverse bs) m (length vs) i 0)
  (while (< i (if cl m (1- m)))
    (setq v1 (nth i vs)
          v2 (nth (rem (1+ i) m) vs))
    (if (and (> (distance v1 v2) 1e-10) (equal 0.0 (nth i bs) 1e-9))
      (setq out (cons (list v1 v2 en) out)))
    (setq i (1+ i)))
  (reverse out))

(defun ns-flat (p) (list (car p) (cadr p) 0.0))

;; point on a circle: center C, radius R, angle A
(defun ns-arcpt (c r a)
  (list (+ (car c) (* r (cos a))) (+ (cadr c) (* r (sin a))) 0.0))

;; T when angle A lies on the counterclockwise span A1 -> A2
(defun ns-inspan (a a1 a2 / e)
  (setq e (- a2 a1))
  (if (< e 0.0) (setq e (+ e pi pi)))
  (setq a (- a a1))
  (if (< a 0.0) (setq a (+ a pi pi)))
  (<= a (+ e 1e-6)))

;; intersections of the circle (C,R) with the infinite line through A
;; along the UNIT direction D; a list of 0 or 2 points
(defun ns-linecirc (a d c r / f g disc)
  (setq f    (ns-vec c a)
        g    (ns-dot d f)
        disc (+ (* r r) (- (* g g) (ns-dot f f))))
  (if (>= disc 0.0)
    (progn
      (setq disc (sqrt disc))
      (list (ns-add a (ns-scl d (- (- g) disc)))
            (ns-add a (ns-scl d (+ (- g) disc)))))))

;;; U pieces: every part of a U perimeter as a uniform record so lines
;;; and corner arcs chain and trim alike -
;;;   ("S" p1 p2)                 a straight part
;;;   ("A" p1 p2 center r a1 a2)  a corner arc, counterclockwise

;; arc piece from an ARC entity, normalized from the curve's own
;; start/mid/end points and its OCS center so mirrored arcs behave
(defun ns-arcent (en / ed c r ep mp a1 a2 sw)
  (setq ed (entget en)
        c  (trans (cdr (assoc 10 ed)) en 0)
        r  (cdr (assoc 40 ed))
        ep (vlax-curve-getendpoint en)
        mp (vlax-curve-getpointatdist
             en (* 0.5 (vlax-curve-getdistatparam
                         en (vlax-curve-getendparam en))))
        a1 (angle c (vlax-curve-getstartpoint en))
        a2 (angle c ep))
  (if (not (ns-inspan (angle c mp) a1 a2))
    (setq sw a1 a1 a2 a2 sw))
  (if (< a2 a1) (setq a2 (+ a2 pi pi)))
  (list "A" (ns-arcpt c r a1) (ns-arcpt c r a2) (ns-flat c) r a1 a2))

;; arc piece from a polyline bulge segment P1 -> P2
(defun ns-bulgepc (p1 p2 b / th l r h nrm cen a1 a2)
  (setq p1  (ns-flat p1)
        p2  (ns-flat p2)
        th  (* 4.0 (atan b))
        l   (distance p1 p2)
        r   (abs (/ l (* 2.0 (sin (/ th 2.0)))))
        h   (* r (cos (/ (abs th) 2.0)))
        nrm (ns-unit (ns-perp (ns-vec p1 p2)))
        cen (ns-add (ns-mid2 p1 p2)
                    (ns-scl nrm (if (> b 0.0) h (- h)))))
  (if (> b 0.0)
    (setq a1 (angle cen p1) a2 (angle cen p2))
    (setq a1 (angle cen p2) a2 (angle cen p1)))
  (if (< a2 a1) (setq a2 (+ a2 pi pi)))
  (list "A" p1 p2 cen r a1 a2))

;; Bulged segments of a POLYLINE as arc pieces (the straight ones come
;; from ns-plsegs)
(defun ns-plarcs (en / ed el cl vs bs i m out v1 v2 pr sub)
  (setq ed (entget en)
        el (cond ((cdr (assoc 38 ed))) (0.0))
        cl (= 1 (logand 1 (cond ((cdr (assoc 70 ed))) (0)))))
  (if (= "LWPOLYLINE" (cdr (assoc 0 ed)))
    (foreach pr ed
      (cond
        ((= 10 (car pr))
         (setq vs (cons (trans (list (car (cdr pr)) (cadr (cdr pr)) el) en 0) vs)
               bs (cons 0.0 bs)))
        ((= 42 (car pr))
         (if bs (setq bs (cons (cdr pr) (cdr bs)))))))
    (progn
      (setq sub (entnext en))
      (while (and sub (= "VERTEX" (cdr (assoc 0 (entget sub)))))
        (setq ed  (entget sub)
              vs  (cons (trans (cdr (assoc 10 ed)) en 0) vs)
              bs  (cons (cond ((cdr (assoc 42 ed))) (0.0)) bs)
              sub (entnext sub)))))
  (setq vs (reverse vs) bs (reverse bs) m (length vs) i 0)
  (while (< i (if cl m (1- m)))
    (setq v1 (nth i vs)
          v2 (nth (rem (1+ i) m) vs))
    (if (and (> (distance v1 v2) 1e-10)
             (not (equal 0.0 (nth i bs) 1e-9)))
      (setq out (cons (ns-bulgepc v1 v2 (nth i bs)) out)))
    (setq i (1+ i)))
  (reverse out))

;; The on-piece hit of the tread line (P along U) nearest to P among
;; SIDE's pieces - the arm, and the corner treatment when there is one.
(defun ns-sidehit (p u side fuzz / best bd q pc)
  (foreach pc side
    (if (= "S" (car pc))
      (progn
        (setq q (inters p (ns-add p u) (cadr pc) (caddr pc) nil))
        (if (and q (< (ns-beyond q (cadr pc) (caddr pc)) fuzz)
                 (or (null best) (< (distance p q) bd)))
          (setq best q bd (distance p q))))
      (foreach q (ns-linecirc p u (nth 3 pc) (nth 4 pc))
        (if (and (ns-inspan (angle (nth 3 pc) q) (nth 5 pc) (nth 6 pc))
                 (or (null best) (< (distance p q) bd)))
          (setq best q bd (distance p q))))))
  best)

;; Draw a U piece record - a straight cut or a corner arc.
(defun ns-drawpc (pc)
  (if (= "S" (car pc))
    (ns-mkline (cadr pc) (caddr pc))
    (entmake (list '(0 . "ARC")
                   (cons 10 (list (car (nth 3 pc)) (cadr (nth 3 pc)) 0.0))
                   (cons 40 (nth 4 pc))
                   (cons 50 (nth 5 pc))
                   (cons 51 (nth 6 pc))))))

;; The back corner where arm AP meets the base BS of a U, cut OFF back
;; along each of them - KIND "Cut" gives a 45 degree diagonal, "Radius"
;; a fillet arc tangent to both.  Unlike the recess corner of a run that
;; comes off an open wall, this one is cut INTO the U, since the arms
;; are the sides of the step itself.  The piece comes back in the same
;; form as the rest of the U so the treads trim to it; nil when the
;; offset will not fit inside the corner.
(defun ns-ucorner (bs ap kind off / b1 b2 fe ub ua t1 t2 o a1 a2 sw)
  (setq b1 (if (< (ns-ptseg (car bs) (car ap) (cadr ap))
                  (ns-ptseg (cadr bs) (car ap) (cadr ap)))
             (car bs)
             (cadr bs))
        b2 (if (equal b1 (car bs)) (cadr bs) (car bs))
        fe (ns-far ap b1)
        ub (ns-unit (ns-vec b1 b2))
        ua (ns-unit (ns-vec b1 fe)))
  (if (and ub ua (> off 0.0)
           (< off (distance b1 b2))
           (< off (distance b1 fe)))
    (progn
      (setq t1 (ns-add b1 (ns-scl ub off))     ; in along the base
            t2 (ns-add b1 (ns-scl ua off)))    ; out along the arm
      (if (= kind "Radius")
        (progn
          ;; centre sits one radius off each leg, so the arc is tangent
          ;; to both; the record spans counterclockwise t1 -> t2
          (setq o  (ns-add t1 (ns-scl ua off))
                a1 (angle o t1)
                a2 (angle o t2))
          (if (< a2 a1) (setq a2 (+ a2 pi pi)))
          (if (> (- a2 a1) pi)                 ; the other way round is the arc
            (setq sw a1 a1 (- a2 pi pi) a2 sw))
          (if (< a1 0.0) (setq a1 (+ a1 pi pi) a2 (+ a2 pi pi)))
          (list "A" t1 t2 o off a1 a2))
        (list "S" t1 t2)))))

;;; -------------------------- ask helpers -------------------------------

;; Keyword question of STANDARDS.md section 1.  KWS is the initget list
;; (hidden aliases included, spelled ALL-CAPS so they must be typed in
;; full and cannot steal a canonical hotkey); SHOWN is the bracket text,
;; which carries only the options a click may send.  DFLT nil = an
;; answer is required.
(defun ns-askkw (msg kws shown dflt / v)
  (initget (if dflt 0 1) kws)
  (setq v (getkword (strcat "\n" msg " [" shown "]"
                            (if dflt (strcat " <" dflt ">") "") ": ")))
  (cond ((null v) (if dflt dflt (ns-askkw msg kws shown dflt)))
        (t v)))

;; The Treatment question of STANDARDS.md section 2: "How should
;; <subject> be treated?"  SUBJECT reads like prose ("the back
;; corners").  Returns "Square", "Radius", "Cut" or "NotGiven" - the
;; old words this tool used to store, and NG, are still accepted typed
;; in full and are normalized HERE, never downstream.
(defun ns-asktreat (subject dflt / v)
  (setq v (ns-askkw (strcat "How should " subject " be treated?")
                    "Square Radius Cut NotGiven NG 90 ROUNDED DIAG DIAGONAL"
                    "Square/Radius/Cut/NotGiven"
                    dflt))
  (cond ((= v "NG") "NotGiven")
        ((= v "90") "Square")
        ((= v "ROUNDED") "Radius")
        ((member v '("DIAG" "DIAGONAL")) "Cut")
        (t v)))

;;; --------------------------- bead helpers -----------------------------

;; The step numbers typed at a prompt - "1 3 4", "1,3,4" and "1, 3 and 4"
;; all read the same.  Anything that is not a digit separates.
(defun ns-numlist (str / out tok i c)
  (setq out '() tok "" i 0)
  (while (<= i (strlen str))
    (setq c (if (< i (strlen str)) (substr str (1+ i) 1) " "))
    (if (and (>= (ascii c) 48) (<= (ascii c) 57))
      (setq tok (strcat tok c))
      (progn
        (if (/= tok "") (setq out (cons (atoi tok) out)))
        (setq tok "")))
    (setq i (1+ i)))
  (reverse out))

;; The tread line of every step that was committed, newest first, as
;; (step-number . ename).  A step's log record is (entities cum pprev n),
;; and the only LINE among those entities is its tread - the dimensions
;; that may sit beside it are DIMENSIONs.
(defun ns-treadents (log / out rec e ln)
  (setq out '())
  (foreach rec log
    (setq ln nil)
    ;; ...-since lists newest first, and a step draws its tread before
    ;; any side line or dimension, so the LAST line seen is the tread
    (foreach e (car rec)
      (if (and e (entget e)
               (= "LINE" (cdr (assoc 0 (entget e)))))
        (setq ln e)))
    (if ln (setq out (cons (cons (nth 3 rec) ln) out))))
  ;; the log runs newest first, so consing through it already leaves
  ;; the pairs in step order - lowest first, the way they were drawn
  out)

;; The step numbers on offer, as "1, 2, 3" - so the numbers prompt can
;; be answered without scrolling back through the run.
(defun ns-numsay (pairs / out pr)
  (setq out "")
  (foreach pr pairs
    (setq out (strcat out (if (= out "") "" ", ") (itoa (car pr)))))
  out)

;; Midpoint (WCS) of a LINE entity.
(defun ns-entmid (e / ed)
  (setq ed (entget e))
  (ns-mid2 (cdr (assoc 10 ed)) (cdr (assoc 11 ed))))

;;; ------------------------- setting helpers ----------------------------

;; 1/8" expressed in the drawing's units (INSUNITS); inches if unitless
(defun ns-autotol ( / iu)
  (setq iu (getvar "INSUNITS"))
  (cond ((= iu 1) 0.125)            ; inches
        ((= iu 2) (/ 0.125 12.0))   ; feet
        ((= iu 4) 3.175)            ; millimeters
        ((= iu 5) 0.3175)           ; centimeters
        ((= iu 6) 0.003175)         ; meters
        (T        0.125)))          ; unitless - assume inches

(defun ns-tolerance ( )
  (if (numberp *cs-width-tol*) *cs-width-tol* (ns-autotol)))

;; annotation text height in drawing units; DIMSCALE is 0 for
;; annotative dim styles, where the annotation scale governs instead
(defun ns-txth ( / h s)
  (setq h (getvar "DIMTXT")
        s (getvar "DIMSCALE"))
  (if (or (null s) (<= s 0.0))
    (setq s (cond ((and (getvar "CANNOSCALEVALUE")
                        (> (getvar "CANNOSCALEVALUE") 0.0))
                   (/ 1.0 (getvar "CANNOSCALEVALUE")))
                  (1.0))))
  (if (and h (> (* h s) 0.0)) (* h s) 1.0))

;;; ------------------------- drawing helpers ----------------------------

(defun ns-mkline (a b)
  (entmake (list '(0 . "LINE")
                 (cons 10 (list (car a) (cadr a) 0.0))
                 (cons 11 (list (car b) (cadr b) 0.0)))))

;; Fillet arc of radius R about centre O between tangent points T1 and
;; T2.  The minor arc is taken, so a quarter-round comes out as one.
(defun ns-mkfillet (o r t1 t2 / a1 a2 sw)
  (setq a1 (angle o t1)
        a2 (angle o t2)
        sw (- a2 a1))
  (if (< sw 0.0) (setq sw (+ sw pi pi)))
  (if (> sw pi) (setq sw a1 a1 a2 a2 sw))    ; the other way round is shorter
  (entmake (list '(0 . "ARC")
                 (cons 10 (list (car o) (cadr o) 0.0))
                 (cons 40 r)
                 (cons 50 a1)
                 (cons 51 a2))))

;; Draw one side of the run: the back corner where it meets the wall at
;; E - the wall carries on along WDIR, the run heads along DIR for LEN -
;; and then the side line down to the last tread.
;;   RTYPE nil / "Square"   - a plain 90 degree side line off the wall
;;   "Radius"               - a fillet arc of radius RRAD
;;   "Cut"                  - a 45 degree diagonal, ROFF back each leg
;; Either treatment flares the mouth of the recess by that offset.
(defun ns-side (e wdir dir len rtype roff rrad / off t1 t2 o)
  (setq off (cond ((and (= rtype "Cut") roff) roff)
                  ((and (= rtype "Radius") rrad) rrad)
                  (0.0)))
  (if (>= off len)
    (progn
      (princ (strcat "\n  Note: the back corner (" (rtos off)
                     ") is deeper than the whole run (" (rtos len)
                     ") - that side is drawn square."))
      (setq off 0.0 rtype "Square")))
  (setq t1 (ns-add e (ns-scl wdir off))      ; tangent/cut point on the wall
        t2 (ns-add e (ns-scl dir off)))      ; and on the side of the run
  (cond
    ((and (= rtype "Cut") (> off 0.0))
     (ns-mkline t1 t2))
    ((and (= rtype "Radius") (> off 0.0))
     ;; centre sits one radius off each leg, so the arc is tangent to both
     (setq o (ns-add t1 (ns-scl dir off)))
     (ns-mkfillet o off t1 t2)))
  (ns-mkline t2 (ns-add e (ns-scl dir len))))

;; The corner of the LAST step of a centered (one-line) run, where the
;; side wall meets the last tread.  E is where the side wall leaves the
;; base wall, UIN the unit vector along the tread toward the run's
;; centre, DIR the way the run heads, LEN the whole run - so the
;; theoretical square corner sits at C = E + DIR x LEN.
;;   "Cut"     - a 45 degree diagonal from OFF back along the side wall
;;               to OFF in along the last tread
;;   "Radius"  - a fillet arc of radius OFF tangent to both
;; The side wall and the trimmed tread are drawn by the caller; OFF 0
;; (a square corner) draws nothing.
(defun ns-outer (e uin dir len rtype off / c t1 t2 o)
  (setq c  (ns-add e (ns-scl dir len))       ; the theoretical square corner
        t1 (ns-add c (ns-scl dir (- off)))   ; back along the side wall
        t2 (ns-add c (ns-scl uin off)))      ; in along the last tread
  (cond
    ((and (= rtype "Cut") (> off 0.0))
     (ns-mkline t1 t2))
    ((and (= rtype "Radius") (> off 0.0))
     ;; centre sits one offset off each leg, so the arc is tangent to both
     (setq o (ns-add t1 (ns-scl uin off)))
     (ns-mkfillet o off t1 t2))))

;; A note on the drawing at PT (WCS), height H.  The geometry cannot
;; say that a corner treatment was never recorded - this does.
(defun ns-note (pt h str)
  (entmake (list '(0 . "TEXT")
                 (cons 10 (list (car pt) (cadr pt) 0.0))
                 (cons 40 h)
                 (cons 1 str))))

;; make dimension style NAME current, but only if it exists and is not
;; already current.  Uses ActiveX so style names containing spaces are
;; handled correctly (the -DIMSTYLE command would read a space as ENTER).
(defun ns-setstyle (name / doc)
  (if (and (tblsearch "DIMSTYLE" name)
           (/= (strcase name) (strcase (getvar "DIMSTYLE"))))
    ;; the argument list is required, even for a lambda that takes
    ;; none - without it this is a "too few arguments" error every
    ;; time a style really has to be switched
    (vl-catch-all-apply
      '(lambda ()
         (setq doc (vla-get-activedocument (vlax-get-acad-object)))
         (vla-put-activedimstyle
           doc (vla-item (vla-get-dimstyles doc) name)))
      '())))

;; aligned dimension between A and B in dim style STYLE, dim line
;; passing through THRU.  Points are WCS and are translated to the
;; current UCS for the command.  "_non" defeats running osnap.
(defun ns-dim (style a b thru / oldl)
  (ns-setstyle style)
  (if (and *cs-dim-layer* (cal:layer-usable-p *cs-dim-layer*))
    (progn (setq oldl (getvar "CLAYER"))
           (setvar "CLAYER" *cs-dim-layer*)))
  (command "_.DIMALIGNED" "_non" (trans a 0 1)
                          "_non" (trans b 0 1)
                          "_non" (trans thru 0 1))
  (if oldl (setvar "CLAYER" oldl)))

;; Vertical linear dimension between A and B in dim style STYLE, dim
;; line passing through THRU.  A and B are the real step corners, which
;; run diagonally to each other, so "_V" is forced: the dimension
;; measures the DROP between them while its extension lines still hook
;; the corners themselves.  Cleaner than dimensioning the riser line,
;; which leaves the dim marooned beside the step instead of reading
;; across to it.  Points are WCS.
(defun ns-dimv (style a b thru / oldl)
  (ns-setstyle style)
  (if (and *cs-dim-layer* (cal:layer-usable-p *cs-dim-layer*))
    (progn (setq oldl (getvar "CLAYER"))
           (setvar "CLAYER" *cs-dim-layer*)))
  (command "_.DIMLINEAR" "_non" (trans a 0 1)
                         "_non" (trans b 0 1)
                         "_V"
                         "_non" (trans thru 0 1))
  (if oldl (setvar "CLAYER" oldl)))

;; entities created since MARK (nil = since the drawing was empty)
(defun ns-since (mark / e out)
  (setq e (if mark (entnext mark) (entnext)))
  (while e (setq out (cons e out) e (entnext e)))
  out)

;;; --------------------------- form answers -----------------------------
;;;
;;;  A form - the Calofin palette, or LAZFORM - can answer some or all
;;;  of NORMIESTEP's questions before the run starts.  It leaves them
;;;  in *ns-form* as (key . value) pairs and the question sites look
;;;  there first, so a filled-in sheet drives the whole run and a
;;;  half-filled one simply shortens it.
;;;
;;;  Three states, and the difference between the last two IS the
;;;  feature:
;;;
;;;    key absent      the form did not answer it  -> ask, as usual
;;;    (key . nil)     what Enter means there      -> taken, no prompt
;;;    (key . 24.0)    the form answered it        -> 24.0, no prompt
;;;
;;;  (assoc key ...) tells those apart; (cdr (assoc ...)) alone cannot.
;;;
;;;  THE KEYS.  steps is the STEP COUNT - the one answer the prompts
;;;  never ask for directly: when it is known the tread loop stops
;;;  itself after that many steps instead of waiting for Enter.
;;;  tread1..treadN feed the per-step prompts; depth1..depthN and
;;;  depthafter feed the side profile's depths; width is the one width
;;;  every step gets.  treat answers the corner-treatment question
;;;  (the hidden aliases are accepted and normalized exactly as typing
;;;  them would be), treat-sz its number - the radius, or the cut's
;;;  face/offset value, whichever cutgiven ("Offset"/"Cut") says it
;;;  is.  dims, profile and bead answer the named gates; a keyword is
;;;  checked against the live prompt's own list and falls through to
;;;  the prompt when it does not fit.  Selections and point picks are
;;;  never form-answered.
;;;
;;;  AN ANSWER IS REMOVED AS IT IS USED.  Not marked used - removed.
;;;  Otherwise Back deadlocks: step back onto a form-answered question,
;;;  it answers itself instantly and walks forward again, and there is
;;;  no key the user can press to get out.  The store is cleared on
;;;  both exits from the command, so nothing leaks into the next run.

(setq *ns-form* nil)

;; Did the form answer KEY at all?  This is the absent/nil distinction
;; that (cdr (assoc ...)) throws away.
(defun ns-fhas (key) (if (assoc key *ns-form*) t nil))

;; The form's answer for KEY, removed from the store as it is read.
(defun ns-ftake (key / p)
  (setq p (assoc key *ns-form*))
  (setq *ns-form* (vl-remove p *ns-form*))
  (cdr p))

(defun ns-fclear () (setq *ns-form* nil))

;; The form's numeric answer for KEY, spent as it is read: the number
;; as a REAL (the way getdist hands one back), nil for anything else.
(defun ns-fnum (key / v)
  (setq v (ns-ftake key))
  (if (numberp v) (* 1.0 v)))

;; The key of a numbered question: (ns-fnkey "tread" 3) -> tread3.
(defun ns-fnkey (stem i) (read (strcat stem (itoa i))))

;; V as the question would spell it, or nil when the question does not
;; accept it at all: an answer the live prompt does not offer falls
;; through to the prompt instead of being handed on to fail later, and
;; the canonical SPELLING comes back, not the caller's, so downstream
;; (= rtype "Cut") tests keep working.
(defun ns-fkword (v kws / i n c w out)
  (setq i 1 n (strlen kws) w "" v (strcase v))
  (while (<= i (1+ n))
    (setq c (if (<= i n) (substr kws i 1) " "))
    (if (= c " ")
        (progn
          (if (and (/= w "") (= (strcase w) v)) (setq out w))
          (setq w ""))
        (setq w (strcat w c)))
    (setq i (1+ i)))
  out)

;; The form's keyword answer for KEY against the live list KWS: the
;; canonical keyword, DFLT when the form said nil (what Enter means at
;; every keyword prompt here), or nil when the form did not answer -
;; or answered a word the prompt does not offer - so the caller asks
;; as always.
(defun ns-fkw (key kws dflt / v)
  (if (ns-fhas key)
    (progn
      (setq v (ns-ftake key))
      (cond ((null v) dflt)
            ((and (= (type v) 'STR) (setq v (ns-fkword v kws))) v)))))

;; The Treatment question a form can answer: the form's word runs
;; through the same alias list and the same normalization typing it
;; would get (NG, 90, ROUNDED, DIAG and DIAGONAL all land on their
;; canonical words), nil reads as the Enter default, and a word the
;; question does not offer falls through to the prompt.  A WRAPPER
;; around the ask helper, not an argument on it: the grouped build
;; swaps that helper for the library's, so this defun is what the
;; mirror leaves alone while the ask call inside it is rewritten like
;; any other call site.
(defun ns-ftreat (subject dflt / v)
  (cond
    ((not (ns-fhas 'treat)) (ns-asktreat subject dflt))
    ((null (setq v (ns-ftake 'treat))) dflt)
    ((and (= (type v) 'STR)
          (setq v (ns-fkword
                    v
                    "Square Radius Cut NotGiven NG 90 ROUNDED DIAG DIAGONAL")))
     (cond ((= v "NG") "NotGiven")
           ((= v "90") "Square")
           ((= v "ROUNDED") "Radius")
           ((member v '("DIAG" "DIAGONAL")) "Cut")
           (t v)))
    (T (ns-asktreat subject dflt))))

;; Run NORMIESTEP with a form's answers already in hand.  Nothing
;; happens here that the direct path misses: a caller may equally set
;; *ns-form* itself and call c:NORMIESTEP, which is what the tests do.
(defun ns-run-with-answers (answers)
  (setq *ns-form* answers)
  (c:NORMIESTEP)
  (ns-fclear)
  (princ))

;;; --------------------------- main command -----------------------------

(defun c:NORMIESTEP ( / *error* ns-popstep undoflag ss i en ed et zf
                        segs mode base side arm1 arm2 corner fuzz
                        sp u dir pt s d1 d2 f1 f2 reflen tol txth
                        wid dep n drawn p inn outp e1 e2 bey stopf
                        first1 first2 lastdep dimflag dimoff offd
                        pprev oldce oldstyle oldlu slog mark svcum svp svn
                        cum rec rtype roff rrad rcut mouth usquare
                        bc1 bc2 arcps pieces freep chain cure rest nxt
                        basepc side1 side2 pc qc e coff tent te1 te2
                        rsubj ngp ngv
                        bmark bsides btreads bnums bside bdir bss pr be
                        tlist svals treads prevv nsteps drops k dv
                        wpu wpt totrun totdrop px0 cx cy
                        tt cnrs ca cb pfo pgap lastinn fsteps fkey)

  (defun *error* (msg)
    (ns-fclear)                     ; both exits clear the form store
    (if undoflag (command-s "_.UNDO" "_End"))
    (if oldstyle (ns-setstyle oldstyle))
    (if oldce (setvar "CMDECHO" oldce))
    (if oldlu (setvar "LUNITS" oldlu))
    (redraw)
    (if (not (wcmatch (strcase msg) "*BREAK*,*CANCEL*,*QUIT*,*EXIT*"))
      (princ (strcat "\nNORMIESTEP: " msg)))
    (princ))

  ;; remove the most recently drawn step and roll the state back
  (defun ns-popstep ( / e)
    (if (null slog)
      (progn (princ "\n  Already at the first step.") nil)
      (progn
        (setq rec (car slog))
        (foreach e (car rec) (if (and e (entget e)) (entdel e)))
        (setq cum   (nth 1 rec)
              pprev (nth 2 rec)
              n     (nth 3 rec)
              drawn (1- drawn)
              slog  (cdr slog)
              tlist (cdr tlist))
        (redraw)
        (princ "\n  Stepping back one step.")
        T)))

  ;; ---- 0. environment checks -------------------------------------------
  (princ (strcat "\nNORMIESTEP " *ns-version*
                 " - every step the same width."))
  ;; the form's step COUNT, spent here once for the whole run: when it
  ;; is known the tread loop stops itself after that many steps
  (if (ns-fhas 'steps)
    (progn
      (setq fsteps (ns-ftake 'steps))
      (if (not (and (numberp fsteps) (> fsteps 0))) (setq fsteps nil))))
  (setq tol  (ns-tolerance)
        txth (ns-txth))
  ;; Read distances architectural-style for the whole command: a bare
  ;; number is drawing units (inches in an inch-based drawing) and
  ;; feet-inch entry like 1'4 works whatever LUNITS was set to.
  (setq oldlu (getvar "LUNITS"))
  (setvar "LUNITS" 4)
  (if (not (equal (trans '(0.0 0.0 1.0) 1 0 T) '(0.0 0.0 1.0) 1e-8))
    (princ (strcat "\nWARNING: the current UCS is not parallel to the"
                   " World XY plane - results may be skewed.")))
  (if (not (cal:layer-usable-p (getvar "CLAYER")))
    (princ (strcat "\nWARNING: the current layer (" (getvar "CLAYER")
                   ") is off, frozen or locked - new steps may not"
                   " appear.")))

  ;; ---- 1. selection ----------------------------------------------------
  (princ (strcat "\nSelect the base line, the two lines of a corner,"
                 " or a U-shaped step perimeter:"))
  (setq ss (ssget '((0 . "LINE,ARC,LWPOLYLINE,POLYLINE"))))
  (if (null ss)
    (progn (princ "\nNothing selected.") (exit)))
  (setq i 0)
  (repeat (sslength ss)
    (setq en (ssname ss i)
          ed (entget en)
          et (cdr (assoc 0 ed))
          i  (1+ i))
    (cond
      ((= et "LINE")
       (if (> (abs (- (caddr (cdr (assoc 10 ed)))
                      (caddr (cdr (assoc 11 ed))))) 1e-6)
         (setq zf T))
       (setq segs (cons (list (cdr (assoc 10 ed)) (cdr (assoc 11 ed)) en)
                        segs)))
      ((= et "ARC")
       (setq arcps (cons (ns-arcent en) arcps)))
      (T
       (setq segs  (append (ns-plsegs en) segs)
             arcps (append (ns-plarcs en) arcps)))))
  (setq segs (reverse segs))
  (if zf
    (princ (strcat "\nWARNING: a selected line is not flat (its ends"
                   " differ in Z) - it is used as seen in plan.")))
  ;; endpoint fuzz for deciding what joins what
  (setq fuzz (max (* 4.0 tol) 1e-6))

  (cond
    ((null segs)
     (princ "\nNo straight lines in the selection.") (exit))
    ((and (= 1 (length segs)) (null arcps)) (setq mode "LINE"))
    ((and (= 2 (length segs)) (null arcps)) (setq mode "CORNER"))
    ;; a U: three straights; five when its corners are cut diagonally;
    ;; three straights plus two arcs when its corners are rounded
    ((and (member (length segs) '(3 5)) (null arcps)) (setq mode "U"))
    ((and (= 3 (length segs)) (= 2 (length arcps)))   (setq mode "U"))
    (T
     (princ (strcat "\nThat selection does not fit - NORMIESTEP takes one"
                    " line, two lines forming a corner, or a U (three"
                    " lines; five with diagonal corners; three lines and"
                    " two arcs with rounded corners)."))
     (exit)))

  ;; ---- 2. work out the run from what was selected ----------------------
  (cond

    ;; ---------- one line: the steps are centered on it ----------
    ((= mode "LINE")
     (setq base (car segs)
           sp   (ns-mid2 (car base) (cadr base))
           u    (ns-unit (ns-vec (car base) (cadr base))))
     (if (null u)
       (progn (princ "\nThe selected line has zero length.") (exit)))
     (while (null dir)
       (setq pt (getpoint (trans sp 0 1)
                          "\nPick a point on the side the steps go: "))
       (if (null pt)
         (progn (princ "\nNo direction picked - nothing drawn.") (exit)))
       (setq d1 (ns-dot (ns-vec sp (trans pt 1 0)) (ns-perp u)))
       (if (< (abs d1) 1e-10)
         (princ "\nThat point is on the line - pick a point to one side.")
         (setq dir (ns-unit (ns-scl (ns-perp u) (if (< d1 0.0) -1.0 1.0))))))
     (princ "\nSteps centered on the line."))

    ;; ---------- two lines: the steps sit against the corner ----------
    ((= mode "CORNER")
     (setq d1     (car segs)
           d2     (cadr segs)
           corner (inters (car d1) (cadr d1) (car d2) (cadr d2) nil))
     (if (null corner)
       (progn (princ "\nThe two lines are parallel - no corner found.")
              (exit)))
     (while (null base)
       (setq pt (getpoint "\nPick the line the steps run OFF OF: "))
       (if (null pt)
         (progn (princ "\nNothing picked - nothing drawn.") (exit)))
       (setq base (ns-nearseg segs (trans pt 1 0))
             side (if (equal base d1) d2 d1)))
     ;; U runs along the base, away from the corner; DIR heads away from
     ;; the base on the side the other line goes
     (setq u   (ns-unit (ns-vec corner (ns-far base corner)))
           dir (ns-unit (ns-vec corner (ns-far side corner))))
     (if (or (null u) (null dir))
       (progn (princ "\nA selected line has zero length.") (exit)))
     ;; keep DIR square to the treads so step treads measure true
     (setq dir (ns-unit (ns-scl (ns-perp u)
                                (if (< (ns-dot (ns-perp u) dir) 0.0)
                                  -1.0 1.0)))
           sp  corner)
     (princ (strcat "\nSteps against the corner, running OUTWARD from it"
                    " off the picked line.")))

    ;; ---------- a U: the outline is drawn, fill in the treads ----------
    ;; The parts - arms, an optional back corner on each side (diagonal
    ;; cut or fillet arc), and the base - are chained end to end from one
    ;; free end to the other; the middle of the chain is the base and
    ;; each half-chain is one side's trimming boundary.  The base is the
    ;; wall the steps come off, so the run STARTS there and marches out
    ;; toward the open end of the U.
    (T
     (setq pieces (append (mapcar '(lambda (s)
                                     (list "S" (ns-flat (car s))
                                               (ns-flat (cadr s))))
                                  segs)
                          arcps))
     ;; the two free endpoints (shared with nothing) mark the arms
     (foreach pc pieces
       (foreach e (list (cadr pc) (caddr pc))
         (setq d1 0)
         (foreach qc pieces
           (if (not (eq qc pc))
             (progn
               (if (< (distance e (cadr qc)) fuzz) (setq d1 (1+ d1)))
               (if (< (distance e (caddr qc)) fuzz) (setq d1 (1+ d1))))))
         (if (zerop d1) (setq freep (cons (list pc e) freep)))))
     (if (/= 2 (length freep))
       (progn (princ (strcat "\nThose parts do not form a U - they must"
                             " chain end to end with two open ends."))
              (exit)))
     ;; walk the chain from one free end to the other
     (setq arm1 (car (car freep))
           f1   (cadr (car freep))
           chain (list arm1)
           cure  (if (< (distance f1 (cadr arm1)) fuzz)
                   (caddr arm1)
                   (cadr arm1))
           rest  (vl-remove arm1 pieces))
     (while (setq nxt (car (vl-remove-if-not
                             '(lambda (pc)
                                (or (< (distance cure (cadr pc)) fuzz)
                                    (< (distance cure (caddr pc)) fuzz)))
                             rest)))
       (setq chain (append chain (list nxt))
             cure  (if (< (distance cure (cadr nxt)) fuzz)
                     (caddr nxt)
                     (cadr nxt))
             rest  (vl-remove nxt rest)))
     (if rest
       (progn (princ "\nThose parts do not all connect - not a U.")
              (exit)))
     (setq f2     cure                          ; the other free end
           d2     (length chain)
           basepc (nth (/ d2 2) chain))         ; the middle of the chain
     (if (/= "S" (car basepc))
       (progn (princ "\nThe middle of the U (its base) must be straight.")
              (exit)))
     (setq base  (list (cadr basepc) (caddr basepc))
           u     (ns-unit (ns-vec (car base) (cadr base)))
           mouth (ns-mid2 f1 f2)                ; the open end of the U
           sp    (ns-mid2 (car base) (cadr base))) ; the base - the wall
     ;; each half of the chain is one side's boundary
     (setq i 0)
     (foreach pc chain
       (cond ((< i (/ d2 2)) (setq side1 (cons pc side1)))
             ((> i (/ d2 2)) (setq side2 (cons pc side2))))
       (setq i (1+ i)))
     (setq arm1 (list (cadr (car chain)) (caddr (car chain)))
           arm2 (list (cadr (last chain)) (caddr (last chain))))
     (if (null u)
       (progn (princ "\nThe base of the U has zero length.") (exit)))
     (setq usquare (= 3 d2))                    ; no back corners drawn yet
     (if (not usquare)
       (princ "\nU with its back corners drawn: treads trim to them."))
     ;; DIR runs from the base out toward the open end, square to the treads
     (setq dir (ns-unit (ns-scl (ns-perp u)
                                (if (< (ns-dot (ns-perp u)
                                               (ns-vec sp mouth))
                                       0.0)
                                  -1.0 1.0))))
     (princ (strcat "\nU outline: the run starts at its base - the wall -"
                    " and marches out, trimmed to its arms."))))

  ;; preview the run direction and the tread direction
  (setq reflen (distance (car base) (cadr base)))
  (grdraw (trans sp 0 1)
          (trans (ns-add sp (ns-scl dir (* 0.75 reflen))) 0 1) 4 0)
  (grdraw (trans (ns-add sp (ns-scl u (* 0.4 reflen))) 0 1)
          (trans (ns-add sp (ns-scl u (* -0.4 reflen))) 0 1) 2 0)

  ;; ---- 3. the one width every step gets --------------------------------
  (if (/= mode "U")
    (progn
      ;; the width can come off the form; the prompt refuses Enter, so
      ;; nil (or anything not a number) falls back to the keyboard
      (if (ns-fhas 'width) (setq wid (ns-fnum 'width)))
      (if (not (numberp wid))
        (progn
          (initget 7)                          ; required, no zero/negative
          (setq wid (getdist "\nStep width (the same for every step): "))))))

  ;; ---- 3b. the corner treatment ----------------------------------------
  ;; The corners are square (90 degrees), radiused, or cut at 45
  ;; degrees - but where they sit depends on the mode.  A centered
  ;; (one-line) run puts the treatment on the LAST step's two corners,
  ;; where the side walls meet the last tread: the tread gives up the
  ;; offset at each end, the side walls stop that much short, and the
  ;; corner piece bridges the two.  Corner mode keeps its BACK corners
  ;; at the wall the run comes off, where the treatment also flares the
  ;; mouth of the recess; in a U it is cut into the corner where the arm
  ;; meets the base and the treads trim to it.  A U that already has its
  ;; back corners drawn keeps them.
  (if (and (= mode "U") (not usquare))
    (princ (strcat "\nBack corners: already drawn on the U - using them"
                   " as they are."))
    (progn
      ;; the subject reads like prose, as STANDARDS.md section 2 has it
      (setq rsubj (if (= mode "LINE")
                    "the corners of the last step"
                    "the back corners")
            rtype (ns-ftreat rsubj "Square"))
      (cond
        ((= rtype "Radius")
         ;; treat-sz is its radius; the prompt refuses Enter, so nil
         ;; falls back to the keyboard
         (if (ns-fhas 'treat-sz) (setq rrad (ns-fnum 'treat-sz)))
         (if (not (numberp rrad))
           (progn
             (initget 7)
             (setq rrad (getdist (strcat "\nRadius for " rsubj ": ")))))
         (setq roff rrad))
        ((= rtype "Cut")
         ;; the offset and the cut face are the two legs and the
         ;; hypotenuse of the same 45 degree triangle, so either one
         ;; gives the other; cutgiven says which one treat-sz is
         (if (null (setq fkey (ns-fkw 'cutgiven "Offset Cut" "Offset")))
           (progn
             (initget "Offset Cut")
             (setq fkey (getkword
                          (strcat "\nIs the cut given as its"
                                  " [Offset/Cut] <Offset>: ")))))
         (if (= "Cut" fkey)
           (progn
             (if (ns-fhas 'treat-sz) (setq rcut (ns-fnum 'treat-sz)))
             (if (not (numberp rcut))
               (progn
                 (initget 7)
                 (setq rcut (getdist (strcat "\nCut face length for "
                                             rsubj ": ")))))
             (setq roff (/ rcut (sqrt 2.0))))
           (progn
             (if (ns-fhas 'treat-sz) (setq roff (ns-fnum 'treat-sz)))
             (if (not (numberp roff))
               (progn
                 (initget 7)
                 (setq roff (getdist "\nOffset back along each line: "))))
             (setq rcut (* roff (sqrt 2.0)))))
         (princ (strcat "\n  A 45 degree cut on " rsubj ": offset "
                        (rtos roff) " each way, cut face "
                        (rtos rcut) ".")))
        ((= rtype "NotGiven")
         (princ (strcat "\n  Not Given: " rsubj " are drawn square, and"
                        " a note on the drawing says the treatment was"
                        " never recorded."))))
      ;; a U has its arms already, so the corner is built into the sides
      ;; the treads trim to - and drawn once the run is done.  NotGiven
      ;; is not cut in: its geometry is square, like Square's.
      (if (and (= mode "U") (member rtype '("Radius" "Cut")))
        (progn
          (setq bc1 (ns-ucorner base arm1 rtype roff)
                bc2 (ns-ucorner base arm2 rtype roff))
          (if (and bc1 bc2)
            (setq side1 (cons bc1 side1)
                  side2 (cons bc2 side2))
            (progn
              (princ (strcat "\n  That back corner does not fit inside the"
                             " U - the corners are left square."))
              (setq bc1 nil bc2 nil rtype "Square")))))))

  ;; ---- 4. dimension the steps? -----------------------------------------
  (if (null (setq fkey (ns-fkw 'dims "Yes No" "Yes")))
    (progn
      (initget "Yes No")
      (setq fkey (getkword "\nDimension the steps? [Yes/No] <Yes>: "))))
  (setq dimflag (/= "No" fkey))
  (if dimflag
    (progn
      (setq oldstyle (getvar "DIMSTYLE")) ; restored when the command ends
      (if (not (tblsearch "DIMSTYLE" *cs-depth-dimstyle*))
        (princ (strcat "\nNote: dim style \"" *cs-depth-dimstyle*
                       "\" not found - step treads use the current style.")))
      (if (not (tblsearch "DIMSTYLE" *cs-width-dimstyle*))
        (princ (strcat "\nNote: dim style \"" *cs-width-dimstyle*
                       "\" not found - the step width uses the current style.")))
      (if (and *cs-dim-layer* (not (cal:layer-usable-p *cs-dim-layer*)))
        (princ (strcat "\nNote: dim layer \"" *cs-dim-layer*
                       "\" is missing or not drawable - using the"
                       " current layer.")))))
  ;; The step-tread chain runs just off the run's axis, the way the corner
  ;; and hemisphere routines (and the shop's own example drawings) do -
  ;; NOT outside the whole run, which would drag every chain dim's
  ;; extension lines across the entire step field.
  (setq offd   (* 2.0 txth)
        dimoff (ns-scl u offd))

  ;; ---- 5. step treads, one per step ------------------------------------
  (command "_.UNDO" "_Begin")
  (setq undoflag T cum 0.0 n 1 drawn 0
        pprev sp
        oldce (getvar "CMDECHO"))
  (setvar "CMDECHO" 0)

  (while
    (and (not stopf)
         (progn
           (setq dep 'RETRY)
           (while (eq dep 'RETRY)
             (cond
               ;; the form gave the step COUNT: past it the run stops
               ;; itself - the auto-done no prompt ever offered
               ((and fsteps (> n fsteps)) (setq dep nil))
               ;; this step's tread from the form, spent as it is
               ;; read - a Back onto it re-asks at the keyboard
               ((ns-fhas (ns-fnkey "tread" n))
                (setq dep (ns-fnum (ns-fnkey "tread" n))))
               (T
                ;; Undo is the old keyword, kept as a hidden synonym
                (initget 6 (strcat "Back" (if lastdep " Same" "") " Undo"))
                (setq dep (getdist
                            (strcat "\nStep " (itoa n)
                                    " - step tread [Back"
                                    (if lastdep "/Same" "") "]"
                                    (if lastdep
                                      (strcat " <Enter = done, Same = "
                                              (rtos lastdep) ">: ")
                                      " <Enter = done>: "))))
                (if (= (type dep) 'STR)
                  (cond
                    ((or (= dep "Back") (= dep "Undo"))
                     (ns-popstep) (setq dep 'RETRY))
                    ((= dep "Same")
                     (if lastdep
                       (setq dep lastdep)
                       (progn (princ "\n  No previous step tread.")
                              (setq dep 'RETRY))))
                    (T (setq dep 'RETRY)))))))
           dep))
    (setq mark (entlast)
          svcum cum svp pprev svn n
          lastdep dep
          ;; each tread sits DEP past the PREVIOUS one, never a total
          p    (ns-add pprev (ns-scl dir dep))
          e1   nil
          e2   nil)
    (cond
      ;; centered on the base line
      ((= mode "LINE")
       (setq e1 (ns-add p (ns-scl u (* 0.5 wid)))
             e2 (ns-add p (ns-scl u (* -0.5 wid)))))
      ;; from the side line outward by the width
      ((= mode "CORNER")
       (setq inn (inters p (ns-add p u) (car side) (cadr side) nil))
       (if (null inn)
         (princ (strcat "\n  Step " (itoa n)
                        ": cannot reach the side line - step skipped."))
         (setq e1  inn
               e2  (ns-add inn (ns-scl u wid))
               bey (ns-beyond inn (car side) (cadr side)))))
      ;; trimmed to the sides of the U - arm, diagonal or fillet,
      ;; whichever the tread actually lands on
      (T
       (setq e1  (ns-sidehit p u side1 fuzz)
             e2  (ns-sidehit p u side2 fuzz)
             bey 0.0)
       ;; nothing on-piece on a side: fall back to the arm extended
       (if (null e1)
         (progn
           (setq e1 (inters p (ns-add p u) (car arm1) (cadr arm1) nil))
           (if e1 (setq bey (ns-beyond e1 (car arm1) (cadr arm1))))))
       (if (null e2)
         (progn
           (setq e2 (inters p (ns-add p u) (car arm2) (cadr arm2) nil))
           (if e2 (setq bey (max bey (ns-beyond e2 (car arm2)
                                                (cadr arm2)))))))
       (cond
         ;; out past the open end of the U: the run is full
         ((and (< (ns-dot (ns-vec p f1) dir) 0.0)
               (< (ns-dot (ns-vec p f2) dir) 0.0))
          (princ (strcat "\n  Step " (itoa n) " would fall past the open"
                         " end of the U - stopping."))
          (setq e1 nil e2 nil stopf T))
         ((or (null e1) (null e2))
          (princ (strcat "\n  Step " (itoa n)
                         ": cannot reach both sides - step skipped."))
          (setq e1 nil e2 nil)))))
    (if (and e1 e2)
      (progn
        (setq cum (+ cum dep))
        (if (and bey (> bey 1e-6))
          (princ (strcat "\n    (note: a line had to be extended "
                         (rtos bey) " to meet this tread)")))
        (ns-mkline e1 e2)
        (princ (strcat "\n  Step " (itoa n) ": width " (rtos (distance e1 e2))
                       ", " (rtos dep) " past the previous tread ("
                       (rtos cum) " from the start)."))
        (if (null first1) (setq first1 e1 first2 e2))
        (if dimflag
          (ns-dim *cs-depth-dimstyle* pprev p
                  (ns-add (ns-mid2 pprev p) dimoff)))
        (setq pprev p drawn (1+ drawn)
              slog  (cons (list (ns-since mark) svcum svp svn) slog)
              tlist (cons cum tlist))))
    (setq n (1+ n)))

  ;; ---- 6. sides of the run, the corner treatment, and the width dim ---
  (if (> drawn 0)
    (progn
      (setq bmark (entlast))               ; the side geometry starts here
      (cond
        ;; both sides of a centered run: plain side walls, square off
        ;; the base wall, running to the last tread - the treatment sits
        ;; on the last step's corners, so the last tread gives up the
        ;; offset at each end and a corner piece bridges each side wall
        ;; to it
        ((= mode "LINE")
         ;; resolve the corner offset once for the whole run
         (setq coff (cond ((and (= rtype "Cut") roff) roff)
                          ((and (= rtype "Radius") rrad) rrad)
                          (0.0)))
         (cond
           ((<= coff 0.0))
           ((>= coff cum)
            (princ (strcat "\n  Note: the corner (" (rtos coff)
                           ") is deeper than the whole run (" (rtos cum)
                           ") - the last step is drawn square."))
            (setq coff 0.0))
           ((>= (* 2.0 coff) wid)
            (princ (strcat "\n  Note: two corners of " (rtos coff)
                           " would meet across the last tread ("
                           (rtos wid) " wide) - the last step is drawn"
                           " square."))
            (setq coff 0.0)))
         ;; trim the last tread by the offset at each end - the step
         ;; loop drew it full width and logged it with its step
         (if (> coff 0.0)
           (progn
             (setq te1  (ns-add pprev (ns-scl u (* 0.5 wid)))
                   te2  (ns-add pprev (ns-scl u (* -0.5 wid)))
                   tent nil)
             (foreach e (car (car slog))
               (if (and (null tent) e (setq ed (entget e))
                        (= "LINE" (cdr (assoc 0 ed)))
                        (or (and (equal (cdr (assoc 10 ed)) te1 1e-6)
                                 (equal (cdr (assoc 11 ed)) te2 1e-6))
                            (and (equal (cdr (assoc 10 ed)) te2 1e-6)
                                 (equal (cdr (assoc 11 ed)) te1 1e-6))))
                 (setq tent e)))
             (if tent
               (progn
                 (setq ed (entget tent)
                       p  (ns-add pprev (ns-scl u (- (* 0.5 wid) coff)))
                       pt (ns-add pprev (ns-scl u (- coff (* 0.5 wid)))))
                 (if (equal (cdr (assoc 10 ed)) te1 1e-6)
                   (setq ed (subst (cons 10 p)  (assoc 10 ed) ed)
                         ed (subst (cons 11 pt) (assoc 11 ed) ed))
                   (setq ed (subst (cons 10 pt) (assoc 10 ed) ed)
                         ed (subst (cons 11 p)  (assoc 11 ed) ed)))
                 (entmod ed))
               (progn
                 (princ (strcat "\n  Note: the last tread was not found"
                                " to trim - the sides are drawn square."))
                 (setq coff 0.0)))))
         ;; the side walls start ON the wall and stop one offset short
         ;; of the last tread (a square run goes the whole way); then
         ;; the corner pieces
         (setq e (ns-add sp (ns-scl u (* 0.5 wid))))
         (ns-mkline e (ns-add e (ns-scl dir (- cum coff))))
         (if (> coff 0.0)
           (ns-outer e (ns-scl u -1.0) dir cum rtype coff))
         (setq e (ns-add sp (ns-scl u (* -0.5 wid))))
         (ns-mkline e (ns-add e (ns-scl dir (- cum coff))))
         (if (> coff 0.0)
           (ns-outer e u dir cum rtype coff)))
        ;; The outer side only - the steps run outward from the
        ;; corner, so the line they sit against closes the inner side
        ;; already.  That outer side is the line they sit against
        ;; OFFSET by the step width, NOT a line square to the base:
        ;; the treads all start on the leaning line and run outward
        ;; from it, so a square side wall would lean into the run and
        ;; miss every tread end but the first.  PPREV is the last
        ;; tread that actually landed, so a step taken Back cannot
        ;; leave this pointing at one that was undone.
        ((= mode "CORNER")
         (setq lastinn (inters pprev (ns-add pprev u)
                               (car side) (cadr side) nil))
         (if (null lastinn)
           (princ (strcat "\n  Note: the run does not reach the line it"
                          " sits against - no outer side drawn."))
           (ns-side (ns-add corner (ns-scl u wid))
                    u
                    (ns-unit (ns-vec corner lastinn))
                    (distance corner lastinn)
                    rtype roff rrad)))
        ;; a U has its arms drawn already - only a back corner asked for
        ;; here is new geometry
        ((and (= mode "U") bc1 bc2)
         (ns-drawpc bc1)
         (ns-drawpc bc2)))
      ;; ... and ends here: the sides and their corner pieces, which is
      ;; what AUTOBEAD wants alongside the treads.  Taken before the
      ;; note and the width dim, which are annotation, not pool lines.
      (setq bsides (ns-since bmark))
      ;; A corner nobody recorded is drawn square, so the drawing must
      ;; say so or it reads as a measured 90.  One note carries both
      ;; corners - they share the one answer - and it sits just outside
      ;; the corner it speaks for.
      (if (= rtype "NotGiven")
        (progn
          (cond
            ((= mode "LINE")
             (setq ngp  (ns-add (ns-add sp (ns-scl u (* 0.5 wid)))
                                (ns-scl dir cum))
                   ngv  (ns-unit (ns-add u dir))))
            ((= mode "CORNER")
             (setq ngp (ns-add corner (ns-scl u wid))
                   ngv u))
            (T
             (setq ngp (ns-mid2 (car base) (cadr base))
                   ngv (ns-scl dir -1.0))))
          (ns-note (ns-add ngp (ns-scl ngv (* 2.0 txth))) txth
                   "CORNERS NOT GIVEN - DRAWN SQUARE")))
      (if dimflag
        (ns-dim *cs-width-dimstyle* first1 first2
                (ns-add sp (ns-scl dir (- (+ (* 0.5 (distance first1 first2))
                                             (* 1.5 txth)))))))))

  ;; ---- 6b. side profile ------------------------------------------------
  ;; The plan run gave each step's STEP TREAD; here each step's STEP
  ;; DEPTH - its vertical drop - is asked, top step first, and the
  ;; staircase silhouette is drawn in world X/Y off a picked wall-top
  ;; point.  Still inside the command's undo group, and its dims use
  ;; the depth dim style like the tread chain.
  (if (> drawn 0)
    (progn
      (if (null (setq fkey (ns-fkw 'profile "Yes No" "Yes")))
        (progn
          (initget "Yes No")
          (setq fkey (getkword "\nAdd a side profile? [Yes/No] <Yes>: "))))
      (if (/= "No" fkey)
        (progn
          ;; the treads, top step first: sort the recorded distances
          ;; from the run start ascending - the first is the first
          ;; tread, each successive difference the next
          (setq svals  (vl-sort tlist '<)
                prevv  0.0
                treads nil)
          (foreach tt svals
            (if (> (- tt prevv) 1e-6)
              (setq treads (cons (- tt prevv) treads)))
            (setq prevv tt))
          (setq treads (reverse treads)
                nsteps (length treads))
          ;; the depths, top step first, with Back (Undo, the old
          ;; keyword, is a hidden synonym): one per step PLUS one
          ;; more for the drop after the last tread, so 3 steps
          ;; take 4 depths
          (setq drops nil k 1)
          (while (<= k (1+ nsteps))
            ;; depth1..depthN and depthafter can come off the form,
            ;; spent as they are read; nil reads as Enter, which the
            ;; first depth refuses - that one falls back to the
            ;; keyboard, its key now spent
            (setq fkey (if (> k nsteps) 'depthafter (ns-fnkey "depth" k)))
            (setq dv (if (ns-fhas fkey) (ns-fnum fkey) 'RETRY))
            (if (or (eq dv 'RETRY) (and (null dv) (= k 1)))
              (if (= k 1)
                (progn
                  (initget 7 "Back Undo")
                  (setq dv (getdist "\nStep 1 - step depth (the drop): ")))
                (progn
                  (initget 6 "Back Undo")
                  (setq dv (getdist
                             (if (> k nsteps)
                               (strcat "\nDepth after the last tread [Back] <"
                                       (rtos (car drops)) ">: ")
                               (strcat "\nStep " (itoa k)
                                       " - step depth [Back] <"
                                       (rtos (car drops)) ">: ")))))))
            (cond
              ((and (= (type dv) 'STR)
                    (or (= dv "Back") (= dv "Undo")))
               (if (= k 1)
                 (princ "\n  Already at the first step.")
                 (progn
                   (setq k (1- k) drops (cdr drops))
                   (princ "\n  Stepping back one step."))))
              ((null dv)                         ; Enter = same as previous
               (setq drops (cons (car drops) drops) k (1+ k)))
              (T
               (setq drops (cons dv drops) k (1+ k)))))
          (setq drops (reverse drops))
          ;; Where the profile goes.  It always runs DOWN AND TO THE
          ;; LEFT from the pick, so there is no side to ask about.
          (setq wpu (getpoint (strcat "\nPick the top of the first tread"
                                      " for the side profile: ")))
          (if (null wpu)
            (princ "\nNo point picked - no side profile drawn.")
            (progn
              ;; The alternating drop/tread silhouette in world X/Y,
              ;; keeping the corner down its high side at every level:
              ;; the pick, then the foot of each drop.  Those corners
              ;; are what the dims bind to.
              (setq wpt     (ns-flat (trans wpu 1 0))
                    totrun  (apply '+ treads)
                    totdrop (apply '+ drops)
                    px0     (car wpt)
                    cx      px0
                    cy      (cadr wpt)
                    k       0
                    cnrs    (list (list cx cy 0.0)))
              (foreach tt treads
                (setq dv (nth k drops))
                ;; the drop, straight down ...
                (ns-mkline (list cx cy 0.0) (list cx (- cy dv) 0.0))
                (setq cy   (- cy dv)
                      cnrs (cons (list cx cy 0.0) cnrs))
                ;; ... then the tread, running left - no dim of its
                ;; own: the depths and the overall depth say it all
                (ns-mkline (list cx cy 0.0) (list (- cx tt) cy 0.0))
                (setq cx (- cx tt)
                      k  (1+ k)))
              ;; the last depth: the drop after the last tread
              (setq dv (nth k drops))
              (ns-mkline (list cx cy 0.0) (list cx (- cy dv) 0.0))
              (setq cy   (- cy dv)
                    cnrs (reverse (cons (list cx cy 0.0) cnrs)))
              (if dimflag
                (progn
                  ;; Every depth dim stands the same distance right of
                  ;; the corner its drop lands on, so the dims climb up
                  ;; and to the right with the steps instead of stacking
                  ;; in one chain.  Clearing the widest tread is what
                  ;; keeps BOTH extension lines running forward, out of
                  ;; the flight; the gap on top of that is what makes
                  ;; the fan readable, and *cs-profile-dimgap* sets it.
                  ;; four text heights, or three quarters of a tread -
                  ;; whichever is more, so the fan keeps its proportions
                  ;; whether or not the drawing has a dim scale set up
                  (setq pgap (cond ((numberp *cs-profile-dimgap*)
                                    *cs-profile-dimgap*)
                                   ((max (* 4.0 txth)
                                         (* 0.75 (apply 'max treads)))))
                        pfo  (+ (apply 'max treads) pgap)
                        k    1)
                  (while (< k (length cnrs))
                    (setq ca (nth (1- k) cnrs)
                          cb (nth k cnrs))
                    (ns-dimv *cs-depth-dimstyle* ca cb
                             (list (+ (car cb) pfo)
                                   (* 0.5 (+ (cadr ca) (cadr cb))) 0.0))
                    (setq k (1+ k)))
                  ;; the overall depth, further out again - the whole
                  ;; diagonal, top corner to bottom corner
                  (ns-dimv *cs-depth-dimstyle* (car cnrs) (last cnrs)
                           (list (+ px0 pfo pgap)
                                 (- (cadr wpt) (* 0.5 totdrop)) 0.0))))
              (princ (strcat "\nSide profile drawn: " (itoa nsteps)
                             " step(s), " (itoa (length drops))
                             " depths, down to the left; total run "
                             (rtos totrun) ", overall depth "
                             (rtos totdrop) "."))))))))

  ;; ---- 7. done ---------------------------------------------------------
  (if (zerop drawn)
    (princ "\nNo steps drawn.")
    (princ (strcat "\n" (itoa drawn) " step(s) drawn"
                   (if (/= mode "U")
                     (strcat ", all " (rtos wid) " wide")
                     " between the arms of the U")
                   ".")))
  (redraw)
  (if oldstyle (ns-setstyle oldstyle))
  (command "_.UNDO" "_End")
  (if oldce (setvar "CMDECHO" oldce))
  (if oldlu (setvar "LUNITS" oldlu))
  (setq undoflag nil)

  ;; ---- 8. bead the steps -----------------------------------------------
  ;; AUTOBEAD does the beading, on its own rules and in its own undo
  ;; group - which is why this sits outside ours: AutoCAD does not nest
  ;; undo groups, so one U undoes the beads and the next undoes the
  ;; steps.  Every tread is beaded; the only question left is which
  ;; steps carry the bead along their side walls, and that is answered
  ;; by step number here instead of by clicking each one.
  (if (> drawn 0)
    (if (not (boundp 'autobead-build))
      (princ (strcat "\nAUTOBEAD is not loaded - APPLOAD AUTOBEAD.lsp"
                     " if you want these steps beaded."))
      (progn
        (if (null (setq fkey (ns-fkw 'bead "Yes No" "Yes")))
          (progn
            (initget "Yes No")
            (setq fkey (getkword "\nBead the steps? [Yes/No] <Yes>: "))))
        (if (/= "No" fkey)
          (progn
            (setq btreads (ns-treadents slog)
                  bnums   nil)
            (if (null btreads)
              (princ "\nNo tread lines to bead.")
              (progn
                ;; every tread is beaded - the side walls are the question
                (initget "All Some")
                (setq bside (cond ((getkword (strcat "\nWhich steps have"
                                                     " beaded side walls?"
                                                     " [All/Some] <All>: ")))
                                  ("All")))
                (if (= bside "Some")
                  (progn
                    (princ (strcat "\n  Steps drawn: "
                                   (ns-numsay btreads)))
                    (setq bnums (ns-numlist
                                  (getstring T (strcat "\nStep numbers with"
                                                       " beaded sides: "))))
                    (setq bnums (vl-remove-if-not
                                  '(lambda (k) (assoc k btreads)) bnums))
                    (if (null bnums)
                      (progn
                        (princ (strcat "\n  No step numbers recognized -"
                                       " beading every side wall full"
                                       " length."))
                        (setq bside "All")))))
                (setq bdir (getpoint "\nClick the side to bead toward: "))
                (if (null bdir)
                  (princ "\nNo direction picked - nothing beaded.")
                  (progn
                    ;; the treads, the sides and their corner pieces, and
                    ;; the line(s) the run came off: the pool lines of
                    ;; this pocket, which is what AUTOBEAD beads
                    (setq bss (ssadd))
                    (foreach pr btreads (ssadd (cdr pr) bss))
                    (foreach be bsides
                      (if (and be (entget be)) (ssadd be bss)))
                    (setq i 0)
                    (while (< i (sslength ss))
                      (ssadd (ssname ss i) bss)
                      (setq i (1+ i)))
                    (autobead-ensure-layer *autobead-layer*)
                    (autobead-build
                      bss bdir
                      (= bside "Some")
                      (if (= bside "Some")
                        (mapcar '(lambda (k)
                                   (ns-entmid (cdr (assoc k btreads))))
                                bnums)
                        nil)))))))))))
  (ns-fclear)                       ; both exits clear the form store
  (princ))

;;; --------------------------- tutorial ---------------------------------

(defun ns-tut-pause ( )
  (princ "\n      --- press Enter to continue ---")
  (getstring)
  (princ))

(defun ns-tut-text (pt h s)
  (entmake (list '(0 . "TEXT")
                 (cons 10 (list (car pt) (cadr pt) 0.0))
                 (cons 40 h)
                 (cons 1 s))))

;; Walkthrough for new users: pages of what NORMIESTEP does and checks,
;; then a live demonstration drawn step by step with the same geometry
;; code the real command uses.
(defun c:TUTORIALNORMIESTEP ( / *error* undoflag oldce oldstyle org sp u dir
                                txth pt wid off n lst dep cum pprev p e1 e2
                                offd first1 first2 hw)
  (defun *error* (msg)
    (if undoflag (command-s "_.UNDO" "_End"))
    (if oldstyle (ns-setstyle oldstyle))
    (if oldce (setvar "CMDECHO" oldce))
    (princ))

  (princ (strcat "\n================ NORMIESTEP TUTORIAL " *ns-version*
                 " ================"))
  (princ "\nNORMIESTEP draws the most normal steps of all: straight,")
  (princ "\nparallel treads, every one the SAME width.")
  (ns-tut-pause)
  (princ "\nWHAT YOU SELECT DECIDES THE MODE")
  (princ "\n  ONE LINE ........ steps centered on it, on the side you pick")
  (princ "\n  TWO LINES ....... a corner: the steps sit against it and run")
  (princ "\n                    OUTWARD, off the line you pick")
  (princ "\n  A U ............. the outline is drawn; treads fill in,")
  (princ "\n                    trimmed to its arms.  The BASE of the U is")
  (princ "\n                    the wall: the run starts there and marches")
  (princ "\n                    out to the open end.  Its back corners may")
  (princ "\n                    already be drawn square, diagonal (5 lines)")
  (princ "\n                    or rounded (arcs / bulged polyline corners)")
  (princ "\nTHE PROMPTS, IN ORDER")
  (princ "\n  1. The step width, ONCE (skipped for a U - its arms set it)")
  (princ "\n  2. How should the corners be treated? - the one question")
  (princ "\n     every Calofin tool asks the same way:")
  (princ "\n       Square   a true 90 degree corner")
  (princ "\n       Radius   a fillet arc, you give the radius")
  (princ "\n       Cut      a 45 degree diagonal, given as its Offset or")
  (princ "\n                its Cut face length (cut = offset x root 2)")
  (princ "\n       NotGiven never recorded: drawn square, and noted on")
  (princ "\n                the drawing so it is not read as a real 90")
  (princ "\n     In one-line mode the treatment sits on the corners of")
  (princ "\n     the LAST step, where the side walls meet the last tread;")
  (princ "\n     in corner mode on the BACK corners at the wall; a U cuts")
  (princ "\n     it into its base corners (one already drawn is not")
  (princ "\n     asked).  The old words still work typed in full: 90,")
  (princ "\n     ROUNDED, DIAG and DIAGONAL.")
  (princ "\n  3. Dimension the steps? [Yes/No]")
  (princ "\n  4. Step treads, one per step, each from the previous")
  (princ "\n     tread.  Enter = done, Back = step back one (removes")
  (princ "\n     it), Same = repeat the previous step tread.")
  (princ "\n  5. Add a side profile? [Yes/No] - the STEP DEPTHS, top")
  (princ "\n     step first: one per step plus the drop after the last")
  (princ "\n     tread (3 steps take 4 depths).  Then pick the top of")
  (princ "\n     the first tread - the flight always runs down and to")
  (princ "\n     the LEFT from there, so the steps rise to the right")
  (princ "\n     and the dims climb with them: each depth beside its")
  (princ "\n     own step, the overall further out, treads not dimmed.")
  (princ "\n  6. Bead the steps? [Yes/No] - every tread is beaded, so")
  (princ "\n     the only question is which steps have beaded SIDE")
  (princ "\n     WALLS: [All/Some], and Some takes the step numbers")
  (princ "\n     (\"1 3 4\").  Then click the side to bead toward, and")
  (princ "\n     AUTOBEAD does the rest on its own rules.  It has to be")
  (princ "\n     loaded for this - the run says so if it is not.")
  (ns-tut-pause)
  (princ "\nWHAT IT CHECKS AND HANDLES FOR YOU")
  (princ "\n  - warns on tilted UCS / non-flat lines / unusable layer")
  (princ "\n  - bare numbers read as inches; 1'4 style works anywhere")
  (princ "\n  - corner mode keeps step treads square to the picked line,")
  (princ "\n    so a skewed corner still measures true")
  (princ "\n  - U treads trim to whatever the side is at that distance -")
  (princ "\n    arm, diagonal or arc - and the run stops at the open end")
  (princ "\n  - a corner deeper than the run - or two that would meet")
  (princ "\n    across the last tread - falls back to square")
  (princ "\n  - notes when a line had to be extended to meet a tread")
  (princ "\n  - dims: the step-tread chain plus the width once; all one undo")
  (princ "\n  - beads go to AUTOBEAD, so they follow ITS rules and land")
  (princ "\n    in their own undo group - a U of their own")
  (ns-tut-pause)

  (initget "Yes No")
  (if (= "No" (getkword (strcat "\nDraw a demonstration in this drawing?"
                                " [Yes/No] <Yes>: ")))
    (progn (princ "\nTutorial done - type NORMIESTEP to use it for real.")
           (exit)))
  (setq pt (getpoint "\nPick a clear spot (about 250 x 120 needed): "))
  (if (null pt)
    (progn (princ "\nNo spot picked - tutorial done.") (exit)))
  (setq org  (trans pt 1 0)
        txth (ns-txth)
        sp   org
        u    '(1.0 0.0 0.0)
        dir  '(0.0 1.0 0.0)
        wid  120.0
        off  9.0)
  (command "_.UNDO" "_Begin")
  (setq undoflag T
        oldce (getvar "CMDECHO")
        oldstyle (getvar "DIMSTYLE"))
  (setvar "CMDECHO" 0)

  (ns-mkline (ns-add sp (ns-scl u -110.0)) (ns-add sp (ns-scl u 110.0)))
  (ns-tut-text (ns-add org '(-105.0 -14.0 0.0)) (* 1.2 txth)
               "NORMIESTEP demo: one-line mode - select this wall line")
  (princ "\n[1] The WALL drawn - one-line mode.  The steps center on its")
  (princ "\n    middle, all 120 wide, marching up from it.")
  (ns-tut-pause)

  (setq pprev sp cum 0.0 n 1
        offd  (ns-scl u (+ (* 0.5 wid) (* 2.0 txth))))
  (foreach lst '(12.0 12.0 12.0)
    ;; the LAST tread gives up the corner offset at each end - the real
    ;; command draws it full width and trims it once the run is known
    (setq dep  lst
          p    (ns-add pprev (ns-scl dir dep))
          cum  (+ cum dep)
          hw   (if (= n 3) (- (* 0.5 wid) off) (* 0.5 wid))
          e1   (ns-add p (ns-scl u hw))
          e2   (ns-add p (ns-scl u (- hw))))
    (ns-mkline e1 e2)
    (if (null first1) (setq first1 e1 first2 e2))
    (ns-dim *cs-depth-dimstyle* pprev p
            (ns-add (ns-mid2 pprev p) offd))
    (princ (strcat "\n[" (itoa (1+ n)) "] Step " (itoa n)
                   ": 12 past the previous tread (" (rtos cum)
                   " from the wall), "
                   (if (= n 3)
                     "trimmed to 102 - 9 goes to each corner."
                     "width 120 like every other.")))
    (ns-tut-pause)
    (setq pprev p n (1+ n)))

  ;; the side walls - square off the wall, one offset short of the last
  ;; tread - and the diagonal corners on the last step
  (setq e1 (ns-add sp (ns-scl u (* 0.5 wid))))
  (ns-mkline e1 (ns-add e1 (ns-scl dir (- cum off))))
  (ns-outer e1 (ns-scl u -1.0) dir cum "Cut" off)
  (setq e2 (ns-add sp (ns-scl u (* -0.5 wid))))
  (ns-mkline e2 (ns-add e2 (ns-scl dir (- cum off))))
  (ns-outer e2 u dir cum "Cut" off)
  (ns-dim *cs-width-dimstyle* first1 first2
          (ns-add sp (ns-scl dir (- (+ (* 0.5 wid) (* 1.5 txth))))))
  (princ "\n[5] The SIDE WALLS close the run - square off the wall, from")
  (princ "\n    the wall to the LAST step, whose corners take the")
  (princ "\n    treatment: here CUT, so each one runs 9 back along")
  (princ "\n    its side wall and 9 in along the last tread (cut length")
  (princ "\n    9 x root 2, about 12.73).  Radius would put a fillet arc")
  (princ "\n    there instead; Square keeps the full corner.  The width")
  (princ "\n    is dimensioned once - it is the same for every step.")
  (ns-tut-pause)

  (if oldstyle (ns-setstyle oldstyle))
  (command "_.UNDO" "_End")
  (setq undoflag nil)
  (setvar "CMDECHO" oldce)
  (princ "\n[6] Done.  One U removes the demo.  Try the other modes too:")
  (princ "\n    two lines of a corner, or a U outline (even one with")
  (princ "\n    rounded or diagonal back corners) - NORMIESTEP fills it in.")
  (princ))

(princ (strcat "\nNORMIESTEP.lsp " *ns-version*
               " loaded - NORMIESTEP to draw plain steps,"
               " TUTORIALNORMIESTEP to learn it."))
(princ)


;;; ======================================================================
;;; >>> LAZSTEP.lsp
;;; ======================================================================

;;; ======================================================================
;;; LAZSTEP.lsp  --  say how many steps, then fill the drawing in
;;; ----------------------------------------------------------------------
;;; For AutoCAD 2018 and later (plain AutoLISP, no external libraries).
;;;
;;; Commands:  LAZSTEP        pick a step type, say how many steps, fill
;;;                           the drawing in and run the step routine
;;;            LAZSTEPVER     print the loaded version
;;;
;;; SHARED BUILD: requires CALOFIN-LIB.lsp (load via CALOFIN-LOADER.lsp).
;;; Generic helpers live there under cal: - see STANDARDS.md.
;;;
;;; TWO PAGES, AND THE SECOND ONE IS BUILT FROM THE FIRST.  Page one
;;; asks which of the three step routines this is -- CORNERSTP,
;;; HEMISTEP or NORMIESTEP -- HOW MANY STEPS, and the handful of
;;; questions that routine asks once for the whole run.  Page two is a
;;; DRAWING GENERATED FOR THAT COUNT: three steps draw three treads,
;;; eight draw eight, and every dimension the count implies is on it
;;; with a box against it.  Nothing here is a stored picture; the chart
;;; is built by lzt:chart from the type and the number.
;;;
;;; That is the whole point.  At the command line the step count is
;;; never a question -- the tread loop repeats until Enter -- so the
;;; number of steps is emergent and the operator finds out what the
;;; sheet needs by being asked for it, one prompt at a time.  A form
;;; has the number as a field, so the routines' stores give it a key of
;;; its own (steps . N): the loop stops itself after N steps instead of
;;; waiting for an Enter nobody typed, and a form of N rows drives a
;;; run of N steps.
;;;
;;; WHAT THE DRAWING SHOWS.  A plan view of the type picked, and under
;;; it the side profile every one of the three draws the same way --
;;; the flight in elevation, reading down and to the left, N risers and
;;; N treads with N+1 depth dimensions: depth1..depthN against each
;;; drop and depthafter against the drop after the last tread.  The
;;; depth chain is the part that is hardest to hold in your head at the
;;; command line, and it is exactly what the routines ask for.
;;;
;;; ZERO INSTALL, like LAZFORM and LAZPANEL: the dialog is plain DCL
;;; written to the temp folder at run time and the chart is drawn with
;;; vector_image, so there is no artwork file to ship and nothing to
;;; NETLOAD.  Unlike LAZFORM the file is rewritten each time a page is
;;; opened, because page two's DCL depends on the count -- N rows of
;;; boxes cannot be a static dialog.
;;;
;;; DCL HEIGHT IS A HARD FAILURE MODE.  A dialog taller than the screen
;;; does not open, and nothing here can measure a screen: N rows of
;;; boxes grow the page linearly, so the count is capped (lzt:*max-
;;; steps*, 8) and the depth boxes are packed two to a row.  A larger
;;; number is refused on page one with a message rather than opening a
;;; page that might not fit.
;;;
;;; WHY THE BOXES SIT WHERE THEY DO.  DCL packs tiles into rows and
;;; columns -- no absolute positioning, no overlapping, no z-order --
;;; so an edit box cannot sit on an image tile.  The chart is therefore
;;; CUT INTO BANDS at the heights where its horizontal dimension rows
;;; run, and those rows are real edit boxes wedged between the bands,
;;; pushed to their letters' positions by spacers.  The tread chain is
;;; horizontal, so it becomes those rows; the widths and the depths run
;;; the other way and a box cannot stand sideways, so they keep boxes
;;; in the side column with their values drawn onto the chart in the
;;; letter's place.
;;;
;;; The chart is a PASSIVE image tile and must stay one.  A DCL image
;;; tile is not retained by AutoCAD: any repaint clears it to its own
;;; colour attribute and there is no expose callback to redraw from.
;;; An image_button repaints on mouse-enter and mouse-leave, so the
;;; drawing would vanish the first time the cursor crossed it.
;;;
;;; THE THREE STATES, which are LAZFORM's and STANDARDS.md's:
;;;
;;;    box left empty   the key is not sent  -> the routine asks
;;;    NA typed in it   (key . nil) is sent  -> what Enter means there
;;;    a measurement    (key . 84.0) is sent -> taken, no prompt
;;;
;;; For a step width NA means "fit to the walls" or "fit to the curve";
;;; for wallwidth and crown it means "none"; for a depth it means "the
;;; same as the one above".  A TREAD IS THE EXCEPTION: nil at a tread
;;; prompt is what ends the run, so NA there would stop the flight short
;;; of the count that built the drawing -- it counts as an empty box
;;; instead.  Anything that is neither NA nor a distance AutoCAD can
;;; read counts as empty too: a typo must leave the routine asking
;;; rather than quietly feeding it a nil that means something else.
;;;
;;; WHAT NEVER COMES OFF THE FORM.  The selections and the point picks:
;;; the two walls, the curve or base line, the side to draw toward, the
;;; profile's top-of-tread pick and the bead direction.  Those live in
;;; the drawing where the operator's own snaps are live, and the three
;;; routines ask for them there as always.
;;; ======================================================================

(vl-load-com)

(setq *lazstep-version* "v1.0")

;;; -------------------- the three routines -------------------------------
;;;  Name, what the tab calls it, and the entry point its store feeds.
;;;  The routines load together as one bundle, so in practice it is all
;;;  three or none -- but the gate is per type anyway, because that is
;;;  the one the operator picked.

(setq lzt:*types*
  '(("CORNERSTP"  "Corner steps"   "cs-run-with-answers")
    ("HEMISTEP"   "Hemi steps"     "hs-run-with-answers")
    ("NORMIESTEP" "Straight steps" "ns-run-with-answers")))

(defun lzt:title (ty / p)
  (if (setq p (assoc ty lzt:*types*)) (cadr p) ty))

;; Is that routine in this session?  An unbound symbol reads as nil, so
;; this is the same test LAZFORM makes of POOL.
(defun lzt:loaded (ty)
  (cond ((= ty "CORNERSTP")  (if cs-run-with-answers T))
        ((= ty "HEMISTEP")   (if hs-run-with-answers T))
        ((= ty "NORMIESTEP") (if ns-run-with-answers T))))

(defun lzt:first-loaded ( / out d)
  (foreach d lzt:*types*
    (if (and (not out) (lzt:loaded (car d))) (setq out (car d))))
  out)

;; Hand the chosen routine what the form collected.
(defun lzt:run (ty form)
  (cond
    ((= ty "CORNERSTP")  (cs-run-with-answers form))
    ((= ty "HEMISTEP")   (hs-run-with-answers form))
    ((= ty "NORMIESTEP") (ns-run-with-answers form))))

;;; -------------------- the stroke font ---------------------------------
;;;  DCL has no way to draw text into an image tile -- vector_image draws
;;;  line segments and that is the whole of it -- so the letters and the
;;;  numbers on the chart are stroked out of segments here.
;;;
;;;  One entry per character: the glyph as a list of polylines, each a
;;;  flat list of x y x y ... in TENTHS of a font unit, on a cell 4 wide
;;;  and 6 tall with y running DOWN the way image-tile pixels do.
;;;  Integers, so nothing here depends on float formatting.

(setq lzt:*font* '(
    ("A" (0 60 20 0 40 60) (8 40 32 40))
    ("B" (0 0 0 60) (0 0 30 0 40 10 40 20 30 30 0 30) (30 30 40 40 40 50 30 60 0 60))
    ("C" (40 10 30 0 10 0 0 10 0 50 10 60 30 60 40 50))
    ("D" (0 0 0 60) (0 0 30 0 40 10 40 50 30 60 0 60))
    ("E" (40 0 0 0 0 60 40 60) (0 30 30 30))
    ("F" (40 0 0 0 0 60) (0 30 30 30))
    ("G" (40 10 30 0 10 0 0 10 0 50 10 60 30 60 40 50 40 30 20 30))
    ("H" (0 0 0 60) (40 0 40 60) (0 30 40 30))
    ("I" (10 0 30 0) (20 0 20 60) (10 60 30 60))
    ("J" (30 0 30 50 20 60 10 60 0 50))
    ("K" (0 0 0 60) (40 0 0 35) (14 25 40 60))
    ("L" (0 0 0 60 40 60))
    ("M" (0 60 0 0 20 30 40 0 40 60))
    ("N" (0 60 0 0 40 60 40 0))
    ("O" (10 0 30 0 40 10 40 50 30 60 10 60 0 50 0 10 10 0))
    ("P" (0 60 0 0 30 0 40 10 40 20 30 30 0 30))
    ("Q" (10 0 30 0 40 10 40 50 30 60 10 60 0 50 0 10 10 0) (25 45 40 60))
    ("R" (0 60 0 0 30 0 40 10 40 20 30 30 0 30) (20 30 40 60))
    ("S" (40 10 30 0 10 0 0 10 0 20 10 30 30 30 40 40 40 50 30 60 10 60 0 50))
    ("T" (0 0 40 0) (20 0 20 60))
    ("U" (0 0 0 50 10 60 30 60 40 50 40 0))
    ("V" (0 0 20 60 40 0))
    ("W" (0 0 10 60 20 20 30 60 40 0))
    ("X" (0 0 40 60) (40 0 0 60))
    ("Y" (0 0 20 30 40 0) (20 30 20 60))
    ("Z" (0 0 40 0 0 60 40 60))
    ("0" (10 0 30 0 40 10 40 50 30 60 10 60 0 50 0 10 10 0) (5 55 35 5))
    ("1" (10 10 20 0 20 60) (10 60 30 60))
    ("2" (0 10 10 0 30 0 40 10 40 20 0 60 40 60))
    ("3" (0 0 40 0 20 25) (20 25 40 35 40 50 30 60 10 60 0 50))
    ("4" (30 60 30 0 0 40 40 40))
    ("5" (40 0 0 0 0 25 30 25 40 35 40 50 30 60 10 60 0 50))
    ("6" (40 0 20 0 0 20 0 50 10 60 30 60 40 50 40 40 30 30 10 30 0 40))
    ("7" (0 0 40 0 15 60))
    ("8" (10 30 0 20 0 10 10 0 30 0 40 10 40 20 30 30 10 30 0 40 0 50 10 60 30 60 40 50 40 40 30 30))
    ("9" (0 60 20 60 40 40 40 10 30 0 10 0 0 10 0 20 10 30 30 30 40 20))
    ("." (17 54 23 54 23 60 17 60 17 54))
    ("-" (5 30 35 30))
    ("'" (20 0 20 16))
    ("\"" (13 0 13 16) (27 0 27 16))
    ("/" (0 60 40 0))
    (":" (20 16 20 22) (20 40 20 46))
    ("%" (0 60 40 0) (5 5 12 5) (28 55 35 55))
    ("#" (10 0 6 60) (30 0 26 60) (0 20 40 20) (0 40 40 40))
    (" ")
))

(setq lzt:*font-w* 40)          ; glyph cell width, tenths
(setq lzt:*font-h* 60)          ; glyph cell height, tenths
(setq lzt:*font-adv* 56)        ; pen advance per character, tenths

;;; -------------------- the frame the chart is drawn in ------------------
;;;  Everything is in PER-MILLE of the picture, x and y, y down -- the
;;;  same convention as an image tile, so the only conversion at draw
;;;  time is a multiply.  Integers, so nothing depends on float
;;;  formatting and two runs of the generator agree to the unit.
;;;
;;;  The picture is one tall frame with the PLAN in the top third, the
;;;  tread dimension row(s) under it, and the SIDE PROFILE below that.
;;;  One coordinate space, one drawing engine, one set of bands.

(setq lzt:*plan-x0*   100)      ; the wall, or the corner
(setq lzt:*plan-x1*   860)      ; the far end of the run
(setq lzt:*plan-yc*   180)      ; the run's centre line
(setq lzt:*plan-hh*   120)      ; half the plan's opening at the far end
(setq lzt:*width-x*   930)      ; where a whole-run width dim stands
(setq lzt:*chord-x1*  860)      ; the last chord across a hemi curve
(setq lzt:*curve-rx*  840)      ; ...whose crown sits beyond it, at x0 + this
(setq lzt:*tread-y0*  385)      ; the tread dimension row
(setq lzt:*tread-y1*  445)      ; ...and the second one, when N needs it
(setq lzt:*one-row*     4)      ; treads that fit one row of boxes
(setq lzt:*prof-x*    860)      ; top of the flight
(setq lzt:*prof-y*    540)
(setq lzt:*prof-w*    760)      ; the flight's whole run...
(setq lzt:*prof-h*    450)      ; ...and its whole drop
(setq lzt:*prof-gap*   40)      ; how far a depth dim stands off its step

;;  THE CEILING.  DCL will not scroll and a dialog taller than the
;;  screen does not open at all, so the count has to stop somewhere.
;;  Eight steps is one row of eight width boxes plus five rows of
;;  paired depth boxes beside a twenty-cell chart, which fits a laptop
;;  screen; nine does not reliably, and nothing here can ask the screen
;;  how tall it is.
(setq lzt:*max-steps* 8)

;;; -------------------- generating the chart -----------------------------
;;;  A chart is (type title (outline ...) (dimension ...) (cut ...)).
;;;
;;;  A dimension is (letter key x1 y1 x2 y2 side label), where side is
;;;  "h" or "v" -- which way the measurement runs, and so where its text
;;;  sits.  The arrow, the letter and the typed value all come off those
;;;  two endpoints, so there is no separate position table that could
;;;  fall out of step with the drawing.
;;;
;;;  A cut is a per-mille y that lands EXACTLY on a horizontal
;;;  dimension's line; every "h" dimension at that y becomes a wedge box
;;;  and loses its drawn arrow, because the row of boxes IS that row of
;;;  the drawing now.

;; The i'th step boundary along a run of N, per-mille x.
(defun lzt:runx (i n x1)
  (+ lzt:*plan-x0* (/ (* (- x1 lzt:*plan-x0*) i) n)))

;; Half the corner fan's opening at per-mille x: nothing at the corner,
;; the full half-height at the far end.
(defun lzt:fanh (x)
  (/ (* lzt:*plan-hh* (- x lzt:*plan-x0*))
     (- lzt:*plan-x1* lzt:*plan-x0*)))

;; Half the hemi curve's opening at per-mille x -- the ellipse the
;; chords are drawn across, so a chord always lands ON the curve.
(defun lzt:curveh (x / u)
  (setq u (/ (- x lzt:*plan-x0*) (float lzt:*curve-rx*)))
  (if (>= u 1.0) 0 (fix (* lzt:*plan-hh* (sqrt (- 1.0 (* u u)))))))

;; Which dimension row step I's tread is drawn on.  One row while the
;; boxes fit across the chart; past that they STAGGER onto two, the way
;; a tight dimension chain is drawn on paper -- eight boxes on one line
;; run about 96 character cells against a chart of 58, and a row that
;; wide drags the whole dialog past the screen.
(defun lzt:tready (i n)
  (if (or (<= n lzt:*one-row*) (= 1 (rem i 2)))
      lzt:*tread-y0*
      lzt:*tread-y1*))

(defun lzt:cutlist (n)
  (if (> n lzt:*one-row*)
      (list lzt:*tread-y0* lzt:*tread-y1*)
      (list lzt:*tread-y0*)))

;; The tread chain: one horizontal dimension per step, end to end.
(defun lzt:treaddims (n x1 / i out y)
  (setq i 1)
  (while (<= i n)
    (setq y (lzt:tready i n)
          out (cons (list (strcat "T" (itoa i))
                          (strcat "tread" (itoa i))
                          (lzt:runx (1- i) n x1) y
                          (lzt:runx i n x1) y
                          "h"
                          (strcat "Step " (itoa i) " tread"))
                    out)
          i (1+ i)))
  (reverse out))

;; The x of the corner at the foot of drop I, per-mille.  The flight
;; reads DOWN AND TO THE LEFT, so each drop stands one tread further
;; left than the one above it -- which is how all three routines draw
;; the profile, and why the depth dims fan out rather than stacking.
(defun lzt:profx (i n)
  (- lzt:*prof-x* (/ (* lzt:*prof-w* (max 0 (1- i))) n)))

;; ...and the y of the level J drops down to.
(defun lzt:profy (j n)
  (+ lzt:*prof-y* (/ (* lzt:*prof-h* j) (1+ n))))

;; The silhouette: N+1 drops with a tread off the foot of each but the
;; last, exactly as the routines draw it.
(defun lzt:profile (n / i out x1 x2 y0 y1)
  (setq i 1)
  (while (<= i (1+ n))
    (setq x1 (lzt:profx i n)
          y0 (lzt:profy (1- i) n)
          y1 (lzt:profy i n)
          out (cons (list x1 y0 x1 y1) out))
    (if (<= i n)
      (setq x2  (lzt:profx (1+ i) n)
            out (cons (list x1 y1 x2 y1) out)))
    (setq i (1+ i)))
  (reverse out))

;; N+1 depth dimensions: depth1..depthN against each drop, depthafter
;; against the drop after the last tread.  Each stands a fixed gap off
;; its own step, so they climb with the flight.
(defun lzt:depthdims (n / i out x ya yb ltr key lbl)
  (setq i 1)
  (while (<= i (1+ n))
    (setq x   (+ (lzt:profx i n) lzt:*prof-gap*)
          ya  (lzt:profy (1- i) n)
          yb  (lzt:profy i n)
          ltr (if (> i n) "DA" (strcat "D" (itoa i)))
          key (if (> i n) "depthafter" (strcat "depth" (itoa i)))
          lbl (if (> i n) "after the last tread"
                          (strcat "Step " (itoa i) " drop"))
          out (cons (list ltr key x ya x yb "v" lbl) out)
          i   (1+ i)))
  (reverse out))

;; ---- CORNERSTP: two walls meeting at a corner, treads fanning out ----
;;  The bisector runs to the right, so the tread chain measured along it
;;  is horizontal and becomes a row of real boxes.  Each step's width is
;;  the length of its own tread line, dimensioned on the line itself.
(defun lzt:chart-corner (n / out i x h dims)
  (setq out (list (list lzt:*plan-x0* lzt:*plan-yc*
                        lzt:*plan-x1* (- lzt:*plan-yc* lzt:*plan-hh*))
                  (list lzt:*plan-x0* lzt:*plan-yc*
                        lzt:*plan-x1* (+ lzt:*plan-yc* lzt:*plan-hh*)))
        i 1)
  (while (<= i n)
    (setq x    (lzt:runx i n lzt:*plan-x1*)
          h    (lzt:fanh x)
          out  (append out (list (list x (- lzt:*plan-yc* h)
                                       x (+ lzt:*plan-yc* h))))
          dims (cons (list (strcat "W" (itoa i))
                           (strcat "width" (itoa i))
                           x (- lzt:*plan-yc* h) x (+ lzt:*plan-yc* h) "v"
                           (strcat "Step " (itoa i) " width"))
                     dims)
          i    (1+ i)))
  (list "CORNERSTP" "Corner steps"
        (append out (lzt:profile n))
        (append (lzt:treaddims n lzt:*plan-x1*)
                (reverse dims)
                (lzt:depthdims n))
        (lzt:cutlist n)))

;; ---- HEMISTEP: a curve with N chords across it ----------------------
;;  The wall is the left edge, the curve bulges away from it, and tread
;;  I is measured between chord I-1 and chord I along the axis.
(defun lzt:chart-hemi (n / out i x h dims)
  (setq out (list (list lzt:*plan-x0* (- lzt:*plan-yc* lzt:*plan-hh*)
                        lzt:*plan-x0* (+ lzt:*plan-yc* lzt:*plan-hh*))
                  (list "A" lzt:*plan-x0* lzt:*plan-yc*
                        lzt:*curve-rx* lzt:*plan-hh* 90 -90))
        i 1)
  (while (<= i n)
    (setq x    (lzt:runx i n lzt:*chord-x1*)
          h    (lzt:curveh x)
          out  (append out (list (list x (- lzt:*plan-yc* h)
                                       x (+ lzt:*plan-yc* h))))
          dims (cons (list (strcat "W" (itoa i))
                           (strcat "width" (itoa i))
                           x (- lzt:*plan-yc* h) x (+ lzt:*plan-yc* h) "v"
                           (strcat "Step " (itoa i) " width"))
                     dims)
          i    (1+ i)))
  (list "HEMISTEP" "Hemi steps"
        (append out (lzt:profile n))
        (append (lzt:treaddims n lzt:*chord-x1*)
                (reverse dims)
                (lzt:depthdims n))
        (lzt:cutlist n)))

;; ---- NORMIESTEP: a straight run, ONE width for the whole of it ------
(defun lzt:chart-normie (n / out i x ytop ybot)
  (setq ytop (- lzt:*plan-yc* lzt:*plan-hh*)
        ybot (+ lzt:*plan-yc* lzt:*plan-hh*)
        out  (list (list lzt:*plan-x0* ytop lzt:*plan-x1* ytop)
                   (list lzt:*plan-x0* ybot lzt:*plan-x1* ybot))
        i    0)
  (while (<= i n)
    (setq x   (lzt:runx i n lzt:*plan-x1*)
          out (append out (list (list x ytop x ybot)))
          i   (1+ i)))
  (list "NORMIESTEP" "Straight steps"
        (append out (lzt:profile n))
        (append (lzt:treaddims n lzt:*plan-x1*)
                (list (list "W" "width" lzt:*width-x* ytop
                            lzt:*width-x* ybot "v"
                            "One width, the whole run"))
                (lzt:depthdims n))
        (lzt:cutlist n)))

;; The chart for a type and a count.  This is the whole of the "drawing
;; generated from the count" -- everything downstream reads it as data.
(defun lzt:chart (ty n)
  (cond
    ((= ty "CORNERSTP")  (lzt:chart-corner n))
    ((= ty "HEMISTEP")   (lzt:chart-hemi n))
    ((= ty "NORMIESTEP") (lzt:chart-normie n))))

;;; -------------------- chart access ------------------------------------

(defun lzt:c-type (c) (nth 0 c))
(defun lzt:c-title (c) (nth 1 c))
(defun lzt:c-outline (c) (nth 2 c))
(defun lzt:c-dims (c) (nth 3 c))
(defun lzt:c-cuts (c) (nth 4 c))

;; Is this key a tread?  A depth?  Both are asked in loops, so they are
;; recognised by their stem rather than listed twice.
(defun lzt:treadkey (k) (= (substr k 1 5) "tread"))
(defun lzt:depthkey (k) (= (substr k 1 5) "depth"))

;; The horizontal dims whose line IS this cut.
(defun lzt:cutdims (c y / d out)
  (foreach d (lzt:c-dims c)
    (if (and (= (nth 6 d) "h") (= (nth 3 d) y) (= (nth 5 d) y))
        (setq out (cons d out))))
  (reverse out))

;; Keys of every dim that lives in a wedge row rather than the column.
(defun lzt:wedge-keys (c / y d out)
  (foreach y (lzt:c-cuts c)
    (foreach d (lzt:cutdims c y)
      (setq out (cons (cadr d) out))))
  (reverse out))

;; The bands between the cuts: ((y0 . y1) ...).
(defun lzt:bands (c / ys prev out y)
  (setq ys   (append (list 0) (lzt:c-cuts c) (list 1000))
        prev (car ys))
  (foreach y (cdr ys)
    (setq out  (cons (cons prev y) out)
          prev y))
  (reverse out))

;; Every key the chart can answer, in drawing order.
(defun lzt:keys (c / d out)
  (foreach d (lzt:c-dims c) (setq out (cons (cadr d) out)))
  (reverse out))

;;; -------------------- page one's questions ----------------------------
;;;  The once-only answers, per type: what a routine asks before the
;;;  step loop starts, and what it asks after it ends.  A row is
;;;  (key kind label (choices ...)); kind is LIST (a dropdown), DIST (a
;;;  distance box) or INT (a whole number).
;;;
;;;  A dropdown's first entry is "(ask)" -- the form's version of an
;;;  empty box, and the only honest default, since the routines offer a
;;;  keyboard default of their own at every one of these prompts.
;;;
;;;  MEASURE AND TREADMODE ARE OFFERED ON EVERY CORNER RUN, and are not
;;;  greyed.  CORNERSTP asks them only when the selection turned up a
;;;  corner diagonal or fillet, which is a fact about the drawing and
;;;  not about the form -- so they are offered, an answer the live
;;;  prompt does not list falls through to the prompt anyway, and the
;;;  hint says they are ignored on a plain corner.

(setq lzt:*ask-common*
  '(("dims"    "LIST" "Dimension the steps"   ("(ask)" "Yes" "No"))
    ("profile" "LIST" "Add a side profile"    ("(ask)" "Yes" "No"))
    ("bead"    "LIST" "Bead the steps"        ("(ask)" "Yes" "No"))))

(setq lzt:*asks*
  '(("CORNERSTP"
     ("direction"   "LIST" "Draw steps"
      ("(ask)" "Inside" "Outside"))
     ("measure"     "LIST" "Measure treads from"
      ("(ask)" "Middle" "True"))
     ("treadmode"   "LIST" "Steps run"
      ("(ask)" "Parallel" "True" "Equidistant"))
     ("outerwidth"  "DIST" "Outermost step width" ())
     ("bench"       "LIST" "Bench along a wall"
      ("(ask)" "Yes" "No"))
     ("benchoffset" "DIST" "Bench offset off the wall" ())
     ("benchstep"   "INT"  "Bench ends on step number" ()))
    ("HEMISTEP"
     ("wallwidth"   "DIST" "Width at the wall (NA = none)" ())
     ("crown"       "DIST" "Last step to the crown (NA = none)" ())
     ("boundary"    "LIST" "Draw the boundary"
      ("(ask)" "Yes" "No")))
    ("NORMIESTEP"
     ("width"       "DIST" "Step width, the whole run" ())
     ("treat"       "LIST" "Corner treatment"
      ("(ask)" "Square" "Radius" "Cut" "NotGiven"))
     ("treat-sz"    "DIST" "Treatment size" ())
     ("cutgiven"    "LIST" "The cut is given as"
      ("(ask)" "Offset" "Cut")))))

(defun lzt:asks-of (ty)
  (append (cdr (assoc ty lzt:*asks*)) lzt:*ask-common*))

(defun lzt:asks ( ) (lzt:asks-of lzt:*type*))

;;; -------------------- the answers -------------------------------------
;;;  What is typed is kept as the STRING the user typed, so the chart can
;;;  show it back exactly as entered -- 2'6" stays 2'6" -- and it is only
;;;  turned into a number when the routine is handed the form.

(setq lzt:*vals* nil)           ; ((key . "typed") ...)
(setq lzt:*sel* nil)            ; ((stem . index) ...) for the dropdowns
(setq lzt:*type* "CORNERSTP")   ; which routine is being filled in
(setq lzt:*steps* nil)          ; the count, once it has been accepted
(setq lzt:*chart* nil)          ; the chart generated for that count
(setq lzt:*focus* nil)          ; the key whose box has the caret
(setq lzt:*pos* nil)            ; where the dialog was last standing
(setq lzt:*page* 1)             ; which page is open
(setq lzt:*go* nil)             ; the type a tab click asked for
(setq lzt:*msg* "")             ; what page one has to say about the count

(defun lzt:get (key / p)
  (if (setq p (assoc key lzt:*vals*)) (cdr p) ""))

(defun lzt:put (key v / out p)
  (foreach p lzt:*vals* (if (/= (car p) key) (setq out (cons p out))))
  (setq lzt:*vals* (reverse (cons (cons key v) out))))

(defun lzt:sel (stem / p)
  (if (setq p (assoc stem lzt:*sel*)) (cdr p) 0))

(defun lzt:sput (stem i / out p)
  (foreach p lzt:*sel* (if (/= (car p) stem) (setq out (cons p out))))
  (setq lzt:*sel* (reverse (cons (cons stem i) out))))

;; The word a dropdown is standing on, or nil when it is still on
;; "(ask)" -- which sends nothing at all.
(defun lzt:selword (stem / d i)
  (if (setq d (assoc stem (lzt:asks)))
    (if (> (setq i (lzt:sel stem)) 0) (nth i (nth 3 d)))))

(defun lzt:trim (s / i n)
  (setq i 1 n (strlen s))
  (while (and (<= i n) (= (substr s i 1) " ")) (setq i (1+ i)))
  (while (and (>= n i) (= (substr s n 1) " ")) (setq n (1- n)))
  (if (> i n) "" (substr s i (1+ (- n i)))))

;;  The three states, decided here.  Anything that is neither NA nor a
;;  distance AutoCAD can read is treated as an empty box: a typo must
;;  leave the routine asking rather than quietly feeding it a nil that
;;  means something else entirely.  distof reads the architectural
;;  spellings, so 2'6" and 2'-6-1/2" arrive as the numbers they look
;;  like.
(defun lzt:answer (v / n)
  (cond
    ((or (null v) (= v "")) 'SKIP)
    ((= (strcase (lzt:trim v)) "NA") nil)
    ((setq n (distof (lzt:trim v) 4)) n)
    ((setq n (distof (lzt:trim v) 2)) n)
    (t 'SKIP)))

;; A box that has to hold a whole number.  The step count and the bench
;; step both refuse anything else, so a typo has to read as "not
;; answered" rather than as a zero.
(defun lzt:int (s / i c ok n)
  (setq s  (lzt:trim s)
        ok (> (strlen s) 0)
        i  1)
  (while (and ok (<= i (strlen s)))
    (setq c (substr s i 1))
    (if (or (< (ascii c) 48) (> (ascii c) 57)) (setq ok nil))
    (setq i (1+ i)))
  (if ok (setq n (atoi s)))
  (if (and n (> n 0)) n))

;;; -------------------- what does not apply ------------------------------
;;;  A question a run will never reach is greyed, and a greyed answer
;;;  does not travel: a number sitting in the store unread is harder to
;;;  reason about than one that was never sent.
;;;
;;;    outerwidth   only outside in places the outermost step by width
;;;    bench        a bench is an inside-out feature; outside in walks
;;;                 toward the corner without knowing its step count
;;;    benchoffset  }  no bench, no offset and no attachment step
;;;    benchstep    }
;;;    measure      the measuring choice is an inside-out question
;;;    treat-sz     only Radius and Cut take a size
;;;    cutgiven     only a Cut can be given as an offset or a face
;;;    depth1..DA   a run with no side profile asks for no depths

(defun lzt:skip ( / out d tr dd)
  (setq d  (lzt:selword "direction")
        tr (lzt:selword "treat"))
  (if (= lzt:*type* "CORNERSTP")
    (if (= d "Outside")
      (setq out (append (list "measure" "bench" "benchoffset" "benchstep")
                        out))
      (setq out (cons "outerwidth"
                      (if (= (lzt:selword "bench") "Yes")
                          out
                          (append (list "benchoffset" "benchstep") out))))))
  (if (= lzt:*type* "NORMIESTEP")
    (progn
      (if (not (member tr '("Radius" "Cut")))
        (setq out (cons "treat-sz" out)))
      (if (not (= tr "Cut")) (setq out (cons "cutgiven" out)))))
  (if (and lzt:*chart* (= (lzt:selword "profile") "No"))
    (foreach dd (lzt:c-dims lzt:*chart*)
      (if (lzt:depthkey (cadr dd)) (setq out (cons (cadr dd) out)))))
  out)

;; Grey what page one carries and this run will not ask about.  Only
;; keys ON this page are touched -- mode_tile on a key the dialog does
;; not have would error.
(defun lzt:p1grey ( / noask d)
  (setq noask (lzt:skip))
  (foreach d (lzt:asks)
    (mode_tile (car d) (if (member (car d) noask) 1 0))))

(defun lzt:p2grey ( / noask d)
  (setq noask (lzt:skip))
  (foreach d (lzt:keys lzt:*chart*)
    (mode_tile d (if (member d noask) 1 0))))

;; A dropdown changed: remember it, and re-grey what that answer opens
;; or closes.
(defun lzt:p1pick (stem v)
  (lzt:sput stem (atoi v))
  (lzt:p1grey)
  (princ))

;;; -------------------- what the routine is handed -----------------------

;;  THE COUNT GOES FIRST AND IS AN INTEGER.  It is the one answer the
;;  prompts never ask for: with it in hand the tread loop stops itself
;;  after that many steps instead of waiting for an Enter nobody typed,
;;  which is what lets a form of N rows drive a run of N steps.
(defun lzt:form ( / out noask k v a ck)
  (setq noask (lzt:skip)
        out   (list (cons 'steps lzt:*steps*)))
  (foreach k (lzt:asks)
    (if (not (member (car k) noask))
      (cond
        ((= (cadr k) "LIST")
         (if (setq v (lzt:selword (car k)))
           (setq out (cons (cons (read (car k)) v) out))))
        ((= (cadr k) "INT")
         (if (setq v (lzt:int (lzt:get (car k))))
           (setq out (cons (cons (read (car k)) v) out))))
        (t
         (setq a (lzt:answer (lzt:get (car k))))
         (if (not (eq a 'SKIP))
           (setq out (cons (cons (read (car k)) a) out)))))))
  (foreach k (lzt:c-dims lzt:*chart*)
    (setq ck (cadr k))
    (if (and (not (member ck noask)) (not (assoc (read ck) out)))
      (progn
        (setq a (lzt:answer (lzt:get ck)))
        ;; NA at a tread is what ENDS the run, so it would stop the
        ;; flight short of the count that built this drawing -- it
        ;; counts as an empty box instead
        (if (and (null a) (lzt:treadkey ck)) (setq a 'SKIP))
        (if (not (eq a 'SKIP))
          (setq out (cons (cons (read ck) a) out))))))
  (reverse out))

;;; -------------------- drawing the chart -------------------------------
;;;  Pixel coordinates, origin top-left, y down -- image-tile convention,
;;;  which is why the per-mille data is generated that way too and needs
;;;  no flipping here.  dimx_tile / dimy_tile report the LARGEST legal
;;;  coordinate, not the size, and are only answerable while the dialog
;;;  is up, so everything below runs between new_dialog and start_dialog.

(setq lzt:*dx* 0)               ; the tile's extent this time round
(setq lzt:*dy* 0)
(setq lzt:*y0* 0)               ; the band being drawn, in per-mille
(setq lzt:*y1* 1000)

(setq lzt:*col-line* -16)       ; dialog foreground: the outline
(setq lzt:*col-back* -15)       ; dialog background: the clear
(setq lzt:*col-dim* 8)          ; grey: the dimension arrows
(setq lzt:*col-val* 30)         ; orange: a value that has been typed
(setq lzt:*col-hi* 5)           ; blue: the box round the active one

(defun lzt:px (v) (fix (/ (* v lzt:*dx*) 1000.0)))
(defun lzt:py (v)
  (fix (/ (* (- v lzt:*y0*) lzt:*dy*) (float (- lzt:*y1* lzt:*y0*)))))

(defun lzt:iny (v) (and (<= lzt:*y0* v) (<= v lzt:*y1*)))

;; The segment, clipped to the band, or nil when none of it is inside.
;; Everything the bands draw goes through this, so a cut is one rule
;; applied everywhere rather than per-shape case work.
(defun lzt:clipseg (x1 y1 x2 y2 / ta tb lo hi)
  (cond
    ((= y1 y2)
     (if (lzt:iny y1) (list x1 y1 x2 y2)))
    (t
     (setq ta (/ (- lzt:*y0* y1) (float (- y2 y1)))
           tb (/ (- lzt:*y1* y1) (float (- y2 y1)))
           lo (max 0.0 (min ta tb))
           hi (min 1.0 (max ta tb)))
     (if (< lo hi)
         (list (+ x1 (* (- x2 x1) lo)) (+ y1 (* (- y2 y1) lo))
               (+ x1 (* (- x2 x1) hi)) (+ y1 (* (- y2 y1) hi)))))))

;;  An outline element is either a POLYLINE -- a flat list of per-mille
;;  numbers, x y x y ... -- or an ARC, written
;;
;;      ("A" cx cy rx ry from to)
;;
;;  with the centre and both radii in per-mille and the angles in
;;  degrees, 0 due east and counting anticlockwise ON SCREEN.  Since
;;  image-tile y runs DOWN, that is a minus on the y term and nowhere
;;  else.  Two radii rather than one because the hemi curve wants half
;;  of an ellipse more often than half of a circle.
(defun lzt:arcpts (a / cx cy rx ry f to n i ang out)
  (setq cx (nth 1 a) cy (nth 2 a) rx (nth 3 a) ry (nth 4 a)
        f (nth 5 a) to (nth 6 a))
  (setq n (fix (/ (abs (- to f)) 6.0)))
  (if (< n 4) (setq n 4))
  (setq i 0)
  (while (<= i n)
    ;; NB: the angle local is not called t -- a local of that name would
    ;; shadow TRUE for the length of the call
    (setq ang (/ (* pi (+ f (/ (* (- to f) i) (float n)))) 180.0)
          out (cons (fix (- cy (* ry (sin ang))))
                    (cons (fix (+ cx (* rx (cos ang)))) out))
          i (1+ i)))
  (reverse out))

;; An outline element as a flat per-mille polyline, whichever it was.
(defun lzt:flatten (e)
  (if (= (type (car e)) 'STR) (lzt:arcpts e) e))

;; A polyline given as a flat per-mille list, clipped to the band.
(defun lzt:pline (flat col / s)
  (while (and flat (cddr flat))
    (if (setq s (lzt:clipseg (car flat) (cadr flat)
                             (caddr flat) (cadddr flat)))
        (vector_image (lzt:px (car s)) (lzt:py (cadr s))
                      (lzt:px (caddr s)) (lzt:py (cadddr s)) col))
    (setq flat (cddr flat))))

;; A polyline already in pixels, given as (x y x y ...).
(defun lzt:plinepx (flat col)
  (while (and flat (cddr flat))
    (vector_image (car flat) (cadr flat) (caddr flat) (cadddr flat) col)
    (setq flat (cddr flat))))

(defun lzt:glyph (ch / p)
  (if (setq p (assoc (strcase ch) lzt:*font*)) (cdr p)))

;; The width one string will occupy, in pixels, at SC tenths per unit.
(defun lzt:textw (s sc)
  (if (= s "") 0
      (fix (/ (* (- (* (strlen s) lzt:*font-adv*)
                    (- lzt:*font-adv* lzt:*font-w*))
                 sc)
              100.0))))

(defun lzt:texth (sc) (fix (/ (* lzt:*font-h* sc) 100.0)))

;; The size to letter the chart at.  Derived from the tile rather than
;; fixed: an image tile's pixel size falls out of the user's dialog font
;; and display DPI, and is not knowable until the dialog is up.
(defun lzt:basesc ( / sc)
  (setq sc (/ (* lzt:*dy* 100) 1560))
  (if (< sc 12) 12 sc))

;; Stroke S with its top-left corner at pixel X Y.  SC is a percentage
;; of the font's own tenth-units, so the caller can size text to fit.
(defun lzt:text (s x y sc col / i ch pen poly out n)
  (setq i 1 pen x)
  (while (<= i (strlen s))
    (setq ch (substr s i 1))
    (foreach poly (lzt:glyph ch)
      (setq out nil n poly)
      (while n
        (setq out (cons (+ y (fix (/ (* (cadr n) sc) 100.0)))
                        (cons (+ pen (fix (/ (* (car n) sc) 100.0))) out))
              n (cddr n)))
      (lzt:plinepx (reverse out) col))
    (setq pen (+ pen (fix (/ (* lzt:*font-adv* sc) 100.0)))
          i (1+ i)))
  pen)

;; The dimension line with an arrowhead at each end, in per-mille,
;; clipped to the band.  A head is drawn only when its own end is
;; inside the band -- the shaft of a vertical dimension can run through
;; several bands, and each draws just its stretch.
(defun lzt:arrow (x1 y1 x2 y2 col / s a b p q)
  (if (setq s (lzt:clipseg x1 y1 x2 y2))
      (vector_image (lzt:px (car s)) (lzt:py (cadr s))
                    (lzt:px (caddr s)) (lzt:py (cadddr s)) col))
  (setq a 6 b 3)
  (cond
    ((= y1 y2)                          ; horizontal: heads point in
     (if (lzt:iny y1)
         (progn
           (setq p (list (lzt:px (min x1 x2)) (lzt:py y1))
                 q (list (lzt:px (max x1 x2)) (lzt:py y1)))
           (vector_image (car p) (cadr p) (+ (car p) a) (- (cadr p) b) col)
           (vector_image (car p) (cadr p) (+ (car p) a) (+ (cadr p) b) col)
           (vector_image (car q) (cadr q) (- (car q) a) (- (cadr q) b) col)
           (vector_image (car q) (cadr q) (- (car q) a) (+ (cadr q) b) col))))
    (t                                  ; vertical
     (if (lzt:iny (min y1 y2))
         (progn
           (setq p (list (lzt:px x1) (lzt:py (min y1 y2))))
           (vector_image (car p) (cadr p) (- (car p) b) (+ (cadr p) a) col)
           (vector_image (car p) (cadr p) (+ (car p) b) (+ (cadr p) a) col)))
     (if (lzt:iny (max y1 y2))
         (progn
           (setq q (list (lzt:px x1) (lzt:py (max y1 y2))))
           (vector_image (car q) (cadr q) (- (car q) b) (- (cadr q) a) col)
           (vector_image (car q) (cadr q) (+ (car q) b) (- (cadr q) a) col))))))

;; Where one dimension's text belongs, and what it says: the LETTER
;; until a value is typed, then the value in the letter's place.  A
;; value too wide for its own span is shrunk to fit rather than allowed
;; to run into its neighbours -- eight treads sit shoulder to shoulder
;; along the chain and every one of them can carry a feet-and-inches
;; number.
(defun lzt:label (d / letter key x1 y1 x2 y2 side txt sc w h lx ly span mx my)
  (setq letter (car d) key (cadr d)
        x1 (lzt:px (nth 2 d)) y1 (lzt:py (nth 3 d))
        x2 (lzt:px (nth 4 d)) y2 (lzt:py (nth 5 d))
        side (nth 6 d)
        txt (lzt:get key)
        mx (/ (+ x1 x2) 2) my (/ (+ y1 y2) 2))
  (if (= txt "")
      (setq txt letter sc (lzt:basesc))
      (setq sc (/ (* (lzt:basesc) 90) 100)))
  (setq w (lzt:textw txt sc))
  (if (and (= side "h") (> w 0))
      (progn
        (setq span (abs (- x2 x1)))
        (if (> w span)
            (progn
              (setq sc (/ (* sc span) w))
              (if (< sc (/ (* (lzt:basesc) 55) 100))
                  (setq sc (/ (* (lzt:basesc) 55) 100)))
              (setq w (lzt:textw txt sc))))))
  (setq h (lzt:texth sc))
  (if (= side "h")
      (setq lx (- mx (/ w 2)) ly (- y1 h 4))
      ;; a vertical dimension labels at the TOP of its span, centred on
      ;; its own line, EXCEPT when that would run off the left edge
      (progn
        (setq ly (+ (min y1 y2) 5))
        (setq lx (if (< (- mx (/ w 2)) 2) (+ mx 4) (- mx (/ w 2))))))
  ;; and nothing is allowed off the edge of the picture
  (if (< lx 2) (setq lx 2))
  (if (> (+ lx w) (- lzt:*dx* 2)) (setq lx (- lzt:*dx* w 2)))
  (if (< ly 2) (setq ly 2))
  (if (> (+ ly h) (- lzt:*dy* 2)) (setq ly (- lzt:*dy* h 2)))
  ;; blank the strip behind it so the dimension line does not run
  ;; through the characters
  (fill_image (- lx 3) (- ly 2) (+ w 6) (+ h 4) lzt:*col-back*)
  (if (= key lzt:*focus*)
      (lzt:plinepx (list (- lx 3) (- ly 2) (+ lx w 3) (- ly 2)
                         (+ lx w 3) (+ ly h 2) (- lx 3) (+ ly h 2)
                         (- lx 3) (- ly 2))
                   lzt:*col-hi*))
  (lzt:text txt lx ly sc
            (if (= (lzt:get key) "") lzt:*col-line* lzt:*col-val*)))

;; The band a dimension's TEXT belongs to.
(defun lzt:anchor (d)
  (if (= (nth 6 d) "h")
      (nth 3 d)
      (min (nth 3 d) (nth 5 d))))

(defun lzt:inband (v) (and (<= lzt:*y0* v) (< v lzt:*y1*)))

;; The whole picture: every band painted once, each between its own
;; start_image and end_image.  Wedge dims draw nothing at all -- their
;; row of the drawing IS a row of real boxes now -- while every other
;; dim draws its clipped arrow in every band it crosses and its text in
;; the band its anchor falls in.
(defun lzt:redraw ( / c wk bands b i key poly d)
  (setq c     lzt:*chart*
        wk    (lzt:wedge-keys c)
        bands (lzt:bands c)
        i     0)
  (foreach b bands
    (setq key       (strcat "chart" (itoa i))
          lzt:*y0*  (car b)
          lzt:*y1*  (cdr b)
          lzt:*dx*  (dimx_tile key)
          lzt:*dy*  (dimy_tile key))
    (start_image key)
    (fill_image 0 0 lzt:*dx* lzt:*dy* lzt:*col-back*)
    (foreach poly (lzt:c-outline c)
      (lzt:pline (lzt:flatten poly) lzt:*col-line*))
    (foreach d (lzt:c-dims c)
      (if (not (member (cadr d) wk))
          (lzt:arrow (nth 2 d) (nth 3 d) (nth 4 d) (nth 5 d)
                     lzt:*col-dim*)))
    (foreach d (lzt:c-dims c)
      (if (and (not (member (cadr d) wk))
               (lzt:inband (lzt:anchor d)))
          (lzt:label d)))
    (end_image)
    (setq i (1+ i)))
  (setq lzt:*y0* 0
        lzt:*y1* 1000)
  (princ))

;;; -------------------- the generated DCL --------------------------------

(setq lzt:*chart-w* 58)         ; the chart column, in character cells
(setq lzt:*chart-h* 20)         ; its total height, spread over the bands
(setq lzt:*wedge-ed* 5)         ; a wedge box's edit_width

;; character cells across for a per-mille x
(defun lzt:cellx (v) (/ (* v lzt:*chart-w*) 1000.0))

;; One wedge row: the cut's dims as real edit boxes, pushed to their
;; letters' positions by spacers.  Positions are in character cells and
;; a box has its own minimum size, so this is honest about being
;; approximate: a box lands within a cell or so of its letter, and two
;; that would collide get pushed apart rather than overlapped.
(defun lzt:wedgerow (c y / out d lbl w want pos)
  (setq out (list "      : row {")
        pos 0.0)
  ;; LEFT TO RIGHT, whatever order the chart lists them in: the row is
  ;; built by walking a cursor across it, and a dim listed before its
  ;; left-hand neighbour would shove that neighbour to the wrong side
  (foreach d (vl-sort (lzt:cutdims c y)
                      '(lambda (p q)
                         (< (+ (nth 2 p) (nth 4 p))
                            (+ (nth 2 q) (nth 4 q)))))
    (setq lbl  (car d)
          w    (+ (strlen lbl) 4.0 lzt:*wedge-ed*)
          want (- (lzt:cellx (/ (+ (nth 2 d) (nth 4 d)) 2)) (/ w 2)))
    (if (< want (+ pos 0.5)) (setq want (+ pos 0.5)))
    (setq out (cons (strcat "        : spacer { width = "
                            (rtos (- want pos) 2 1) "; }")
                    out))
    (setq out (cons (strcat "        : edit_box { key = \"" (cadr d)
                            "\"; label = \"" lbl
                            "\"; edit_width = " (itoa lzt:*wedge-ed*)
                            "; fixed_width = true; }")
                    out))
    (setq pos (+ want w)))
  (setq out (cons "        spacer;" out))
  (reverse (cons "      }" out)))

;; The chart as a stack: an image tile per band, a wedge row at every
;; cut, heights split in proportion to the bands they show.
(defun lzt:bandtiles (c / out bands b i h)
  (setq i     0
        bands (lzt:bands c))
  (foreach b bands
    (setq h (/ (* (- (cdr b) (car b)) lzt:*chart-h*) 1000.0))
    (if (< h 0.8) (setq h 0.8))
    (setq out (append out
                      (list (strcat "      : image { key = \"chart" (itoa i)
                                    "\"; width = " (itoa lzt:*chart-w*)
                                    "; height = " (rtos h 2 1)
                                    "; fixed_width = true; "
                                    "fixed_height = true; color = -15; }"))))
    (if (< (1+ i) (length bands))
        (setq out (append out (lzt:wedgerow c (cdr b)))))
    (setq i (1+ i)))
  out)

;; The DCL name of a page.
(defun lzt:dlgname (p ty)
  (strcat "lazstep_p" (itoa p) "_" (strcase ty t)))

;; One page-one field.
(defun lzt:p1tile (d)
  (if (= (cadr d) "LIST")
      (strcat "    : popup_list { key = \"" (car d) "\"; label = \""
              (caddr d) "\"; edit_width = 12; }")
      (strcat "    : edit_box { key = \"" (car d) "\"; label = \""
              (caddr d) "\"; edit_width = 8; }")))

;; PAGE ONE: the type, the count, and the questions asked once.
(defun lzt:dcl-p1 (ty / out d)
  ;; out is consed newest-first and reversed once at the end, so this
  ;; seed list reads BACKWARDS: the label second here puts it second in
  ;; the file, after the line that opens the dialog.  The other way
  ;; round emits an attribute before its own dialog, which is not DCL.
  (setq out (list (strcat "  label = \"LazStep - " (lzt:title ty) "\";")
                  (strcat (lzt:dlgname 1 ty) " : dialog {")))
  (setq out (cons "  : row {" out))
  (foreach d lzt:*types*
    (setq out (cons (strcat "    : button { key = \"tab_" (car d)
                            "\"; label = \"" (cadr d) "\"; }")
                    out)))
  (setq out (cons "  }" out))
  (setq out (cons "  : boxed_column {" out))
  (setq out (cons "    label = \"How many steps\";" out))
  (setq out (cons (strcat "    : edit_box { key = \"steps\"; label = \""
                          "Number of steps (1-" (itoa lzt:*max-steps*)
                          ")\"; edit_width = 4; fixed_width = true; }")
                  out))
  (setq out (cons (strcat "    : text { key = \"msg\"; width = 60; label = \""
                          "The next page is a drawing built for that many"
                          " steps, with a box on every dimension.\"; }")
                  out))
  (setq out (cons "  }" out))
  (setq out (cons "  : boxed_column {" out))
  (setq out (cons (strcat "    label = \"" (lzt:title ty) " (" ty
                          ") - asked once for the run\";")
                  out))
  (foreach d (lzt:asks-of ty)
    (setq out (cons (lzt:p1tile d) out)))
  (setq out (cons "  }" out))
  (setq out (cons "  spacer;" out))
  (foreach d (lzt:hints ty)
    (setq out (cons (strcat "  : text { width = 60; label = \"" d "\"; }")
                    out)))
  (setq out (cons "  : row {" out))
  (setq out (cons (strcat "    : button { key = \"accept\"; label = \"Next >\";"
                          " is_default = true; fixed_width = true; }")
                  out))
  (setq out (cons (strcat "    : button { key = \"cancel\"; label = \"Cancel\";"
                          " is_cancel = true; fixed_width = true; }")
                  out))
  (setq out (cons "  }" out))
  (reverse (cons "}" out)))

;; What page one has to say, per type.
(defun lzt:hints (ty / out)
  (setq out (list (strcat "The walls, the curve, the side to draw toward and"
                          " the profile's pick all stay")
                  "in the drawing.  Leave a box empty and the routine asks."))
  (if (= ty "CORNERSTP")
    (setq out (append out
                (list (strcat "Measure and Steps-run are asked only when the"
                              " selection turns up a corner diagonal or")
                      "fillet; on a plain corner they are ignored."))))
  (if (= ty "HEMISTEP")
    (setq out (append out
                (list "NA at the wall width or the crown means none."))))
  out)

;; One column row: the letter as a button, then the box.  Clicking the
;; letter puts the caret in that box and rings the dimension on the
;; chart -- which is as close to clicking the drawing itself as DCL
;; allows, and the button sits against the box it fills.
(defun lzt:colcell (d lbl ed)
  (list (strcat "          : button { key = \"pick_" (cadr d)
                "\"; label = \"" (car d) "\"; fixed_width = true; }")
        (strcat "          : edit_box { key = \"" (cadr d)
                "\"; edit_width = " (itoa ed) "; label = \"" lbl "\"; }")))

;; PAGE TWO: the drawing built for the count, with the boxes on it.
(defun lzt:dcl-p2 (c / out d wk widths depths pair l)
  (setq out (list (strcat "  label = \"LazStep - " (lzt:c-title c) ", "
                          (itoa (length (lzt:treads c))) " steps\";")
                  (strcat (lzt:dlgname 2 (lzt:c-type c)) " : dialog {")))
  (setq wk (lzt:wedge-keys c))
  (setq out (cons "  : row {" out))
  ;; PASSIVE image tiles, deliberately, stacked with the wedge rows
  ;; between them -- see the header for what an image_button costs.
  (setq out (cons "    : column {" out))
  (foreach l (lzt:bandtiles c)
    (setq out (cons l out)))
  (setq out (cons "    }" out))
  (setq out (cons "    : column {" out))
  ;; the widths: one row each, labelled, because what a width means
  ;; differs between the three types
  (foreach d (lzt:c-dims c)
    (if (and (not (member (cadr d) wk)) (not (lzt:depthkey (cadr d))))
      (setq widths (cons d widths))))
  (setq widths (reverse widths))
  (if widths
    (progn
      (setq out (cons "      : boxed_column {" out))
      (setq out (cons "        label = \"Step widths\";" out))
      (foreach d widths
        (setq out (cons "        : row {" out))
        (foreach l (lzt:colcell d (nth 7 d) 8) (setq out (cons l out)))
        (setq out (cons "        }" out)))
      (setq out (cons "      }" out))))
  ;; the depths: TWO TO A ROW.  One row each would add N+1 rows to a
  ;; page that already grows with N, and a dialog taller than the
  ;; screen does not open at all.
  (foreach d (lzt:c-dims c)
    (if (lzt:depthkey (cadr d)) (setq depths (cons d depths))))
  (setq depths (reverse depths))
  (if depths
    (progn
      (setq out (cons "      : boxed_column {" out))
      (setq out (cons "        label = \"Depths, top step first\";" out))
      (setq pair nil)
      (foreach d depths
        (if (null pair)
          (setq out  (cons "        : row {" out)
                pair d)
          (setq pair nil))
        (foreach l (lzt:colcell d "" 7) (setq out (cons l out)))
        (if (null pair) (setq out (cons "        }" out))))
      (if pair (setq out (cons "        }" out)))
      (setq out (cons "      }" out))))
  (setq out (cons "    }" out))
  (setq out (cons "  }" out))
  (setq out (cons "  spacer;" out))
  (foreach l (list (strcat "D1 is the drop into step 1; DA is the drop after"
                           " the last tread.")
                   (strcat "NA in a width means fit to the walls or the"
                           " curve.  An empty box is asked for at the")
                   "command line, where the picks and the selections are.")
    (setq out (cons (strcat "  : text { width = 66; label = \"" l "\"; }")
                    out)))
  (setq out (cons "  : row {" out))
  (setq out (cons (strcat "    : button { key = \"accept\"; label = \"Insert\";"
                          " is_default = true; fixed_width = true; }")
                  out))
  (setq out (cons (strcat "    : button { key = \"back\"; label = \"< Back\";"
                          " fixed_width = true; }")
                  out))
  (setq out (cons (strcat "    : button { key = \"cancel\"; label = \"Cancel\";"
                          " is_cancel = true; fixed_width = true; }")
                  out))
  (setq out (cons "  }" out))
  (reverse (cons "}" out)))

;; Every tread on the chart, whichever row it was staggered onto: the
;; step count the drawing was built for, read back off the drawing.
(defun lzt:treads (c / d out)
  (foreach d (lzt:c-dims c)
    (if (lzt:treadkey (cadr d)) (setq out (cons d out))))
  (reverse out))

;; Every page, in one file.  Page one for all three types -- so a tab
;; switch needs nothing from disk -- and page two for the chart the
;; count has generated, when there is one.
(defun lzt:dcl-lines ( / out ty)
  (foreach ty lzt:*types*
    (setq out (append out (lzt:dcl-p1 (car ty)) (list ""))))
  (if lzt:*chart*
    (setq out (append out (lzt:dcl-p2 lzt:*chart*) (list ""))))
  out)

(defun lzt:write-lines (fh / l)
  (foreach l (lzt:dcl-lines) (write-line l fh)))

(defun lzt:write-dcl ( / f fh err)
  (setq f (vl-filename-mktemp "lazstep" nil ".dcl"))
  (if (and f (setq fh (open f "w")))
    (progn
      (setq err (vl-catch-all-apply 'lzt:write-lines (list fh)))
      (close fh)
      (cond
        ((vl-catch-all-error-p err) (vl-file-delete f) nil)
        (t f)))))

;;; -------------------- the pages ---------------------------------------

;; Open a page where the user last had the dialog.  done_dialog reports
;; the position it was closed at and new_dialog takes one back, but only
;; as a 4-argument call -- and a build that answered done_dialog with
;; something other than a point would poison every reopen, so the shape
;; is checked before it is trusted and the plain 2-argument call is the
;; fallback.
(defun lzt:newdlg (name dcl)
  (if (and lzt:*pos* (listp lzt:*pos*) (= (length lzt:*pos*) 2)
           (numberp (car lzt:*pos*)) (numberp (cadr lzt:*pos*)))
      (new_dialog name dcl "" lzt:*pos*)
      (new_dialog name dcl)))

(defun lzt:page1 (dcl / d k)
  (cond
    ((not (lzt:newdlg (lzt:dlgname 1 lzt:*type*) dcl)) 9)
    (t
     ;; the tabs -- each closes this page and names the next.  A type
     ;; whose routine is not in this session is greyed rather than
     ;; offered: its Insert could only fail.
     (foreach d lzt:*types*
       (action_tile (strcat "tab_" (car d))
         (strcat "(setq lzt:*go* \"" (car d) "\" lzt:*pos* (done_dialog 4))"))
       (if (not (lzt:loaded (car d)))
         (mode_tile (strcat "tab_" (car d)) 1)))
     (set_tile "steps" (lzt:get "steps"))
     (action_tile "steps" "(lzt:put \"steps\" $value)")
     (if (/= lzt:*msg* "") (set_tile "msg" lzt:*msg*))
     (foreach d (lzt:asks)
       (cond
         ((= (cadr d) "LIST")
          (start_list (car d))
          (foreach k (nth 3 d) (add_list k))
          (end_list)
          (set_tile (car d) (itoa (lzt:sel (car d))))
          (action_tile (car d)
            (strcat "(lzt:p1pick \"" (car d) "\" $value)")))
         (t
          (set_tile (car d) (lzt:get (car d)))
          (action_tile (car d)
            (strcat "(lzt:put \"" (car d) "\" $value)")))))
     (action_tile "accept" "(setq lzt:*pos* (done_dialog 1))")
     (action_tile "cancel" "(setq lzt:*pos* (done_dialog 0))")
     (lzt:p1grey)
     (start_dialog))))

(defun lzt:page2 (dcl / d wk)
  (cond
    ((not (lzt:newdlg (lzt:dlgname 2 lzt:*type*) dcl)) 9)
    (t
     (setq wk (lzt:wedge-keys lzt:*chart*))
     ;; put back what was typed the last time this count was on screen
     (foreach d (lzt:keys lzt:*chart*)
       (set_tile d (lzt:get d))
       (action_tile d
         (strcat "(lzt:put \"" d "\" $value) (setq lzt:*focus* \"" d "\")"
                 " (lzt:redraw)")))
     ;; a wedge dim has no pick button -- its box already sits on the
     ;; drawing where the letter was
     (foreach d (lzt:c-dims lzt:*chart*)
       (if (not (member (cadr d) wk))
         (action_tile (strcat "pick_" (cadr d))
           (strcat "(setq lzt:*focus* \"" (cadr d) "\") (lzt:redraw)"
                   " (mode_tile \"" (cadr d) "\" 2)"
                   " (mode_tile \"" (cadr d) "\" 3)"))))
     ;; the chart takes no action at all -- it is a passive image tile
     (action_tile "back" "(setq lzt:*pos* (done_dialog 5))")
     (action_tile "accept" "(setq lzt:*pos* (done_dialog 1))")
     (action_tile "cancel" "(setq lzt:*pos* (done_dialog 0))")
     (lzt:redraw)
     (lzt:p2grey)
     (start_dialog))))

;; The count, checked before a page is built for it.  Nothing here can
;; measure a screen and N rows of boxes grow the page linearly, so a
;; number past the ceiling is refused with a message rather than
;; opening a dialog that might not fit on it.
(defun lzt:count-ok ( / n)
  (setq n (lzt:int (lzt:get "steps")))
  (cond
    ((null n)
     (setq lzt:*msg* (strcat "How many steps?  A whole number from 1 to "
                             (itoa lzt:*max-steps*) ", please."))
     (princ (strcat "\nLAZSTEP: " lzt:*msg*))
     nil)
    ((> n lzt:*max-steps*)
     (setq lzt:*msg* (strcat (itoa lzt:*max-steps*)
                             " steps is the ceiling - a taller dialog"
                             " will not open.  Run the rest by hand."))
     (princ (strcat "\nLAZSTEP: " lzt:*msg*))
     nil)
    (t (setq lzt:*steps* n) T)))

;;; -------------------- the run -----------------------------------------
;;  A helper rather than the command body, so its localized *error* is
;;  out of scope by the time the step routine is started: each of the
;;  three installs its own, and a CORNERSTP that fails must report as
;;  CORNERSTP.

(defun lzt:show ( / *error* f dcl rc done out)
  (defun *error* (msg)
    (term_dialog)
    (if (and dcl (>= dcl 0)) (unload_dialog dcl))
    (setq dcl nil)
    (if f (vl-file-delete f))
    (setq f nil)
    (if (and msg (not (wcmatch (strcase msg)
                               "*BREAK*,*CANCEL*,*QUIT*,*EXIT*")))
      (princ (strcat "\nLAZSTEP error: " msg)))
    (princ))
  (setq lzt:*vals*  nil
        lzt:*sel*   nil
        lzt:*steps* nil
        lzt:*chart* nil
        lzt:*focus* nil
        lzt:*pos*   nil
        lzt:*msg*   ""
        lzt:*page*  1)
  ;; THE PAGE LOOP.  DCL has no tab tile and no way to rebuild a dialog
  ;; that is already up, so a page change closes this one and opens the
  ;; next -- and because done_dialog hands back where the dialog was
  ;; standing, it reopens exactly there instead of wandering off to the
  ;; middle of the screen.  Everything typed lives in lzt:*vals*, keyed,
  ;; so it survives the switch: change the count, come back, and the
  ;; steps that still exist still carry what was typed against them.
  (while (not done)
    (setq f (lzt:write-dcl))
    (cond
      ((null f)
       (princ "\nLAZSTEP error: could not write the dialog file.")
       (setq done T))
      ((< (setq dcl (load_dialog f)) 0)
       (princ "\nLAZSTEP error: could not load the dialog file.")
       (vl-file-delete f)
       (setq f nil done T))
      (t
       (setq rc (if (= lzt:*page* 1) (lzt:page1 dcl) (lzt:page2 dcl)))
       (unload_dialog dcl)
       (setq dcl nil)
       (vl-file-delete f)
       (setq f nil)
       (cond
         ((= rc 9)
          (princ "\nLAZSTEP error: could not open the form.")
          (setq done T))
         ((= rc 0) (setq done T))
         ((and (= lzt:*page* 1) (= rc 4))
          (setq lzt:*type* lzt:*go* lzt:*msg* ""))
         ((and (= lzt:*page* 1) (= rc 1))
          ;; the drawing is generated HERE, from the count that was
          ;; just accepted -- come back with a different number and a
          ;; different drawing is built for it
          (if (lzt:count-ok)
            (setq lzt:*chart* (lzt:chart lzt:*type* lzt:*steps*)
                  lzt:*focus* nil
                  lzt:*msg*   ""
                  lzt:*page*  2)))
         ((and (= lzt:*page* 2) (= rc 5))
          (setq lzt:*page* 1 lzt:*msg* "" lzt:*focus* nil))
         ((and (= lzt:*page* 2) (= rc 1))
          (setq out (lzt:form) done T))
         (t (setq done T))))))
  out)

;;; -------------------- commands ----------------------------------------

;; The form, then the step routine with what it collected.  The chart
;; fills that routine's answers in, so it has to be here to receive
;; them -- say so plainly rather than opening a form whose Insert
;; button could only fail.  The three load together as one bundle, so
;; the gate is checked per TYPE: the one the operator picked.
(defun c:LAZSTEP ( / form ty)
  (cond
    ((not (lzt:first-loaded))
     (princ "\nLAZSTEP: no step routine is loaded in this session -- APPLOAD")
     (princ "\n         lisp/cornerstp/CORNERSTP.lsp, HEMISTEP.lsp and")
     (princ "\n         NORMIESTEP.lsp, or LAZPASS.lsp, which has all three."))
    (t
     (if (not (lzt:loaded lzt:*type*))
       (setq lzt:*type* (lzt:first-loaded)))
     (setq form (lzt:show)
           ty   lzt:*type*)
     (cond
       ((null form) (princ "\nLAZSTEP: cancelled, nothing drawn."))
       ((not (lzt:loaded ty))
        (princ (strcat "\nLAZSTEP: " ty " is not loaded in this session"
                       " -- nothing drawn.")))
       (t
        (princ (strcat "\nLAZSTEP: " (itoa (length form)) " answers to " ty
                       " for " (itoa lzt:*steps*)
                       " steps; it will ask for whatever is left."))
        (lzt:run ty form)))))
  (princ))

(defun c:LAZSTEPVER ()
  (princ (strcat "\nLAZSTEP " *lazstep-version* " (LAZSTEP.lsp) - "
                 (itoa (length lzt:*types*)) " step routine(s), up to "
                 (itoa lzt:*max-steps*) " steps."))
  (princ))

(princ (strcat "\nLAZSTEP " *lazstep-version*
               " loaded.  Type LAZSTEP to fill a step drawing in."))
(princ)


;;; ======================================================================
;;; >>> covercheck.lsp
;;; ======================================================================

;;; ------------------------------------------------------------------
;;;  covercheck.lsp — COVERCHECK: interactive dimension & arc QA review
;;;
;;;  Based on dimcheck.lsp (DIMCHECK), reworked into the cover
;;;  review: the same guided, one-at-a-time audit of dimensions,
;;;  arcs and overlapping lines, with COVER's own rules in place of
;;;  DIMCHECK's step, wall-height and liner checks.
;;;
;;;  VERSIONING. This file is distributed under two names at once:
;;;    - covercheck.lsp             the STATIC name, unchanged forever
;;;                                 so it stays a one-time entry in
;;;                                 everyone's AutoCAD app autoloader.
;;;    - covercheck_MMDDYY_REV##.lsp  a byte-identical copy saved under
;;;                                 a name that records exactly which
;;;                                 revision it is, so opening someone
;;;                                 else's support folder tells you at
;;;                                 a glance what they have loaded.
;;;  The two files must always carry the same content. Whenever
;;;  covercheck.lsp changes, bump *cchk-version* below and regenerate
;;;  the dated twin with python3 tools/release_lisp.py (the twin's
;;;  REV## is the version with the dot dropped, v0.2 -> REV02; git
;;;  history keeps the earlier dated copies).
;;;  *cchk-version* is also stamped into the load banner, into every
;;;  COVERCHECK/COVERSCAN report's title line, and is available on
;;;  demand via the COVERCHECKVER command - so even a renamed or
;;;  copy-pasted file always tells you which revision produced it.
;;;
;;;  Type COVERCHECK, then:
;;;
;;;  1. You are asked to highlight the drawing (any selection).
;;;     Everything selected is greyed out so only the item under
;;;     review stands out.
;;;
;;;  2. Dimensions are reviewed ONE AT A TIME, in a fixed marching
;;;     order: grouped by dimension style — "STANDARD", then "SIDE
;;;     STANDARD", then "STANDARD INCHES", then "CROSS DIMENSIONS",
;;;     then whatever styles are left (tune *cchk-style-order*) —
;;;     and inside each group left to right, top to bottom (row by
;;;     row, like reading). Each dimension is zoomed to, shown in
;;;     its own colour and highlighted while the rest stays grey.
;;;     For linear/aligned dimensions the two definition points are
;;;     audited first: a point that does not sit on any object is
;;;     shown where COVERCHECK thinks it belongs, with BOTH spots
;;;     marked on screen and spelled out so there is no doubt which
;;;     is which —
;;;         a RED X   where you drew it,
;;;         a GREEN + where we would move it, joined by a line.
;;;     You then choose, one point at a time:
;;;         Enter / M  ->  MOVE it onto the nearest object (green +)
;;;         K          ->  KEEP it exactly where you drew it (red X);
;;;                        the point is put back and nothing changes
;;;         P          ->  PICK the spot yourself
;;;     A construction line (XLINE) is drawn through the dimension's
;;;     original points on layer COVERCHECK-CONSTRUCTION so you can see
;;;     where it used to measure — only when a point actually moved.
;;;     Then the overall question for every dimension:
;;;         "Is this dimension correct?"
;;;         Enter / Y  ->  correct, the dimension is left alone
;;;         N          ->  the dimension is recoloured RED so it is
;;;                        easy to find and fix afterwards
;;;
;;;  3. Arcs are reviewed the same way, one endpoint at a time, with
;;;     the same Move / Keep / Pick choice. An endpoint not attached
;;;     to the end of another object is snapped there and both spots
;;;     are marked; Keep puts the arc back exactly as you drew it
;;;     (its original shape is restored, not re-fitted), Pick re-fits
;;;     it through your spot. Arcs whose endpoints actually changed
;;;     are recoloured MAGENTA — an arc you kept is left alone.
;;;
;;;  4. OVERLAPPING LINES are hunted down: two straight LINE entities
;;;     that are collinear and run on top of each other (a leftover
;;;     from drawing over an existing line to continue it and never
;;;     cleaning it up). Each overlapping pair is zoomed to and
;;;     highlighted, the overlapping stretch is marked with crosses,
;;;     and you choose:
;;;         Enter / M  ->  MERGE the two into one line spanning both
;;;                        (only when they share a layer; the merged
;;;                        line turns CYAN so you can see it changed)
;;;         F          ->  FLAG both lines CYAN to fix by hand
;;;         L          ->  LEAVE them as drawn (intentional)
;;;     Lines that merely touch end-to-end are fine and not reported.
;;;
;;;  5. COVER CHECKS — nothing here rewrites the drawing; every
;;;     disagreement is only SUGGESTED against, in the report:
;;;     - TECH TITLE DATE. The Date attribute of the "Tech Title"
;;;       block (tune *cchk-title-block* / *cchk-date-tag*) must read
;;;       TODAY, written MM/DD/YYYY - a sheet going out under an old
;;;       date is the mistake this catches. The block is looked for in
;;;       the selection and then across the drawing; with none in
;;;       reach the report says the date was not checked rather than
;;;       flagging it. LITECOVERSCAN keeps this one.
;;;     - FEET AND INCHES. Every text box in the selection - TEXT,
;;;       MTEXT and the ATTRIB values on blocks - must state its
;;;       inches wherever it states feet: 5' is flagged, 5'-0",
;;;       3'-2" and a plain 40" are fine. A feet mark is an
;;;       apostrophe straight after a digit, so "Water's Edge" is
;;;       prose and never flagged. LITECOVERSCAN keeps this one.
;;;     - DIMENSION LAYER. Every dimension must sit on the
;;;       "DIMENSION" layer (tune *cchk-dim-layer*). Any that do not
;;;       are counted, the layers they landed on are named, and the
;;;       report tells you to run CDIM (tune *cchk-dimfix-cmd*) to
;;;       move them. This one runs in LITECOVERSCAN too.
;;;     - POOL OUTLINE & AREA. Everything in the selection on layer
;;;       "POOL" (tune *cchk-pool-layer*) whose properties are all
;;;       ByLayer is the pool outline: a closed (lw)polyline, a
;;;       CIRCLE, or the same shape exploded into lines and arcs —
;;;       touching ends are chained back together and the largest
;;;       closed loop wins; leftover open chains or other closed loops
;;;       are reported as AMBIGUOUS. Its area (sq ft) and its straight
;;;       / arc segment split are given in the report on the side.
;;;     - COVER DETAILS. A block named (or containing) "Cover
;;;       Details" holds an OVERLAP value ("Overlap: 12''" — only
;;;       12"/15"/18" exist) and a SPACING tag ("Spacing: 5x5" —
;;;       NxN). What they SHOULD say comes from the outline:
;;;         more arcs than straights           -> 18" overlap, 3x3
;;;         mostly straights, under 1,200 sqft -> 12" overlap, 5x5
;;;         mostly straights, 1,200-2,000      -> 15" overlap, 3x3
;;;         mostly straights, over 2,000       -> 18" overlap, 3x3
;;;       A value that disagrees, is blank or is unreadable gets a
;;;       SUGGEST line; the block itself is never touched.
;;;     - POOL SIZE SHOWN. With nothing drawn on the cover layer
;;;       (tune *cchk-cover-layer*) the note "Pool Size Shown" must
;;;       appear somewhere in the highlighted area — missing is
;;;       suggested. With a cover drawn the note must NOT be there —
;;;       present suggests taking it off; absent is all good. If both
;;;       "Pool Size Shown" and "Spa Size Shown" (tune
;;;       *cchk-spa-note*) turn up in the same selection, that is
;;;       flagged as an error — ONLY ONE SIZE CAN BE SHOWN.
;;;     - COVER LAYER = POLYLINES. Anything drawn on the cover layer
;;;       that is not a polyline is called out.
;;;     - OVERLAP NA <-> DASHED OUTLINE. Overlap reading NA means no
;;;       dashed polyline may sit on the pool layer; a stated overlap
;;;       demands one and its absence is reported - UNLESS the "Pool
;;;       Size Shown" note (above) is in the selection, in which case
;;;       this demand is skipped entirely.
;;;     - REPLACEMENT. A "Replacement Disclaimer" block should be in
;;;       the selection. Without one - and without a "Pool Size Shown"
;;;       note either - COVERCHECK asks whether the drawing is a
;;;       replacement; answering Yes asks you to point at the block,
;;;       and not finding it is reported. A "Pool Size Shown" note
;;;       skips the question outright (a full pool size drawing is
;;;       never a replacement). COVERSCAN cannot ask and just notes
;;;       the block is not there.
;;;     - Under any of these - a replacement, an NA overlap, or a
;;;       cover drawn on the cover layer - PADDLE pads are NOT
;;;       suggested.
;;;     - PADS. The pool outline is run through PADDLE's concave-
;;;       feature hunt at 36" pads (PADDLE v1.2 rules): an inside
;;;       corner gets a pad centered dead on the corner, a concave
;;;       radius of 4'-6" or less gets a row of pads starting on the
;;;       middle of the radius and marching flush (36" on center)
;;;       toward both ends, and geometry that bends 10 degrees or
;;;       less - a semi-straight kink, a gently sweeping arc - is
;;;       passed over. Suggested pads never overlap each other: a
;;;       pad on a sharp point holds its spot, the ones along curves
;;;       slide flush alongside or drop out. Every spot with no pad
;;;       already nearby (existing pads = *cchk-pad-blocks* inserts,
;;;       or any insert on *cchk-pads-layer*) is circled on the
;;;       construction layer and SUGGESTED in the report.
;;;
;;;  6. A COVERCHECK REPORT (MTEXT) is placed to the RIGHT of the
;;;     drawing on layer COVERCHECK-REPORT, sized from the drawing's
;;;     extents so it sits to scale next to it.  The MAIN sheet leads
;;;     with what matters to the cover itself: a large title, the
;;;     date and version, a verdict line (ALL CLEAR, or the count of
;;;     red lines), the colour legend, a SUMMARY dashboard, then the
;;;     COVER CHECKS findings under underlined section headings.
;;;     The DIMCHECK-style findings — every dimension with its
;;;     measured distance, every arc, every overlapping line pair
;;;     with its overlap length — go in a separate DIMENSION AUDIT
;;;     column to the RIGHT of the main sheet, so the cover verdicts
;;;     lead and the mechanical audit reads alongside.  Any line
;;;     describing something questionable or that needs looking over
;;;     (a flagged/wrong item, a missing block, a "NOT" find, an
;;;     "add ..." note, a skipped check) is coloured RED in the
;;;     report; everything that checked out stays the report's
;;;     normal colour and is drawn at *cchk-green-scale* (3/4) of
;;;     the red text's height, so the problems are the big lines on
;;;     the sheet.
;;;
;;;  LITECOVERSCAN is COVERSCAN minus the DIMCHECK-style pass: no
;;;     dimension, arc or overlap audit and no DIMENSION AUDIT
;;;     column - just the cover rules, for a drawing DIMCHECK
;;;     already went over.
;;;
;;;  All original colours are restored when the review ends — except
;;;  the red "fix me" dimensions, magenta moved arcs and cyan
;;;  merged/flagged lines, which stay marked on purpose. Everything
;;;  (including the report) runs inside one UNDO group, so a single U
;;;  reverts the whole review.
;;;
;;;  SAFETY NETS
;;;  - Locked layers in the selection are announced up front with an
;;;    offer to unlock for the run (re-locked afterwards, even on
;;;    error); left locked, their items are reported but untouched.
;;;  - Object-associative dimensions are warned about before their
;;;    points are moved — an associative point may re-anchor on its
;;;    own — and their report line says so in red.
;;;  - Rerunning COVERCHECK replaces the previous report and marker
;;;    lines instead of stacking a second copy on top.
;;;  - Original colours are stashed in xdata before greying. If a
;;;    crash or kill ever leaves the drawing grey, COVERCHECKRESCUE
;;;    restores every stashed colour and clears COVERCHECK's report
;;;    and markers (flag colours included — it is the full reset).
;;; ------------------------------------------------------------------
;;; SHARED BUILD: requires CALOFIN-LIB.lsp (load via CALOFIN-LOADER.lsp).
;;; Generic helpers live there under cal: - see STANDARDS.md.

(vl-load-com)

;; --- version ---------------------------------------------------------
;; bump this on every change that reaches covercheck.lsp; see the
;; VERSIONING note above the file header for the two-file convention
(setq *cchk-version* "v1.1")

;; --- tunables ------------------------------------------------------
(setq *cchk-tol*          1.0e-4)  ; max gap (drawing units) that still counts as attached
(setq *cchk-grey-color*   8)       ; grey used to fade out everything not under review
(setq *cchk-flag-color*   1)       ; red: dimensions you answered "No" to
(setq *cchk-arc-color*    6)       ; magenta: arcs whose endpoints were moved
(setq *cchk-olap-color*   4)       ; cyan: merged or flagged overlapping lines
(setq *cchk-olap-fuzz*    1.0e-4)  ; max sideways offset that still counts as "same line"

;; dimension styles are reviewed in this order; styles not listed
;; come afterwards ("whatever else is left"), still left-to-right
(setq *cchk-style-order*
      '("STANDARD" "SIDE STANDARD" "STANDARD INCHES" "CROSS DIMENSIONS"))
;; every dimension belongs on this layer; CDIM is the command that
;; moves the strays there, and is what the report tells you to run
(setq *cchk-dim-layer*   "DIMENSION")
;; the sheet's title block, and the attribute in it carrying the date;
;; the date must read today, written MM/DD/YYYY
(setq *cchk-title-block* "Tech Title")  ; spaces optional in the name
(setq *cchk-date-tag*    "Date")
(setq *cchk-dimfix-cmd*  "CDIM")
(setq *cchk-constr-layer* "COVERCHECK-CONSTRUCTION")
(setq *cchk-constr-color* 2)       ; yellow
(setq *cchk-green-scale*  0.75)    ; report: all-clear text height, as a fraction of the red text
(setq *cchk-block-depth*  3)       ; how many levels of nested blocks to search for names/text
(setq *cchk-orig-color*   1)       ; red X: where you drew the point
(setq *cchk-sugg-color*   3)       ; green +: where COVERCHECK would move it
(setq *cchk-report-layer* "COVERCHECK-REPORT")
(setq *cchk-report-color* 3)       ; green
(setq *cchk-zoom-margin*  0.75)    ; empty space around the zoomed item (fraction of its size)
(setq *cchk-report-chars* 45.0)    ; report column width, in text heights
(setq *cchk-ask-all-arc-ends* nil) ; T = confirm EVERY arc endpoint, even already-attached ones

;; entity types dimension points and arc ends may attach to
(setq *cchk-curve-types*
      '("LINE" "ARC" "CIRCLE" "ELLIPSE" "LWPOLYLINE" "POLYLINE" "SPLINE"))

;; --- cover tunables ------------------------------------------------
(setq *cchk-pool-layer*  "POOL")   ; layer the pool outline is drawn on (ByLayer properties)
(setq *cchk-cover-layer* "COVER")  ; layer a drawn cover lives on
(setq *cchk-pool-note*   "Pool Size Shown") ; note demanded when no cover is drawn
(setq *cchk-spa-note*    "Spa Size Shown")  ; the pool note's spa counterpart - both together is an error
(setq *cchk-details-block* "Cover Details") ; block carrying Overlap & Spacing
(setq *cchk-overlap-vals* '(12.0 15.0 18.0)) ; the only overlaps that exist
(setq *cchk-area-small*  1200.0)   ; sq ft: under this -> 12" overlap, 5x5
(setq *cchk-area-large*  2000.0)   ; sq ft: over this -> 18" overlap, 3x3
(setq *cchk-pad-size*    36.0)     ; pads are suggested at 36" (PADDLE's big pad)
(setq *cchk-pad-blocks*  '("Pad36x36" "Pad24x24")) ; blocks that count as an existing pad
(setq *cchk-pads-layer*  "PADS")   ; layer existing pads sit on
(setq *cchk-pad-near*    18.0)     ; a pad center within this (Chebyshev) covers a spot
(setq *cchk-pad-maxrad*  54.0)     ; 4'-6": largest concave radius needing pads (PADDLE)
(setq *cchk-chain-fuzz*  0.05)     ; max gap when chaining an exploded outline
(setq *cchk-pad-angtol*  (/ (* 10.0 pi) 180.0)) ; 10 deg: a corner - or a whole arc - bending this little is semi-straight (PADDLE)
(setq *cchk-repl-block*  "Replacement Disclaimer") ; block demanded on replacement drawings
(setq *cchk-dashed-pat*  "*DASH*,*HIDDEN*") ; linetype names that count as dashed
(setq *cchk-tut-layer*   "TUTORIAL-COVERCHECK-DEMO") ; layer for TUTORIALCOVERCHECK's non-pool demo geometry

;; --- safety: xdata tags, colour stash, layer locks -----------------

(defun cchk:regapp ()
  (if (not (tblsearch "APPID" "COVERCHECK"))
    (regapp "COVERCHECK")))

(defun cchk:xd (ent / g)
  ;; COVERCHECK's xdata groups on ent, nil when none
  (setq g (assoc -3 (entget ent '("COVERCHECK"))))
  (if g (cdadr g)))

(defun cchk:tag (ent kind / ed)
  ;; stamp a COVERCHECK-created entity (report, marker line) so a rerun
  ;; or COVERCHECKRESCUE can find and clear it
  (cchk:regapp)
  (setq ed (entget ent '("COVERCHECK")))
  (if (and ed (not (assoc -3 ed)))
    (entmod (append ed (list (list -3 (list "COVERCHECK" (cons 1000 kind))))))))

(defun cchk:stash-color (ent col / ed)
  ;; remember the entity's own colour in xdata so COVERCHECKRESCUE can
  ;; put it back even after a crash; an existing stash (from an
  ;; interrupted run - the TRUE original) is never overwritten
  (cchk:regapp)
  (setq ed (entget ent '("COVERCHECK")))
  (if (and ed (not (assoc -3 ed)))
    (entmod (append ed (list (list -3 (list "COVERCHECK"
                                            '(1000 . "COLOR")
                                            (cons 1071 col))))))))

(defun cchk:unstash (ent / ed)
  ;; drop COVERCHECK's xdata once the run has restored things itself
  (setq ed (entget ent '("COVERCHECK")))
  (if (and ed (assoc -3 ed))
    (entmod (subst (list -3 (list "COVERCHECK")) (assoc -3 ed) ed))))

(defun cchk:clear-old (/ ss2 i e xd n)
  ;; erase the report and marker lines left by an earlier COVERCHECK
  ;; run, so a rerun replaces them instead of stacking on top
  (setq ss2 (ssget "_X" '((-3 ("COVERCHECK")))) n 0 i 0)
  (if ss2
    (repeat (sslength ss2)
      (setq e  (ssname ss2 i)
            i  (1+ i)
            xd (cchk:xd e))
      (if (member (cdr (assoc 1000 xd)) '("REPORT" "XLINE" "MARKER"))
        (progn (entdel e) (setq n (1+ n))))))
  (if (> n 0)
    (princ (strcat "\n(Removed " (itoa n)
                   " report/marker item(s) from an earlier COVERCHECK run.)"))))

(defun cchk:layer-locked-p (name / ld)
  (setq ld (tblsearch "LAYER" name))
  (and ld (= 4 (logand 4 (cdr (assoc 70 ld))))))

(defun cchk:set-layer-lock (name lock / ed old new)
  ;; set or clear a layer's locked flag; T when it actually changed
  (setq ed  (entget (tblobjname "LAYER" name))
        old (cdr (assoc 70 ed))
        new (if lock (logior old 4) (logand old (~ 4))))
  (if (/= old new)
    (progn (entmod (subst (cons 70 new) (assoc 70 ed) ed)) T)))

(defun cchk:dim-assoc-p (ent / found g)
  ;; T when the dimension carries persistent reactors - the mark of
  ;; an object-associative dim, whose definition points may re-anchor
  ;; on their own after being moved
  (foreach g (entget ent)
    (if (and (= 102 (car g)) (= "{ACAD_REACTORS" (cdr g)))
      (setq found T)))
  found)

(defun c:COVERCHECKRESCUE ( / ss i e xd n)
  ;; the way out after a crash or interrupted run: puts back every
  ;; colour COVERCHECK stashed (flag colours included) and removes its
  ;; report and marker lines
  (setq ss (ssget "_X" '((-3 ("COVERCHECK")))) n 0 i 0)
  (if ss
    (repeat (sslength ss)
      (setq e  (ssname ss i)
            i  (1+ i)
            xd (cchk:xd e))
      (cond
        ((member (cdr (assoc 1000 xd)) '("REPORT" "XLINE" "MARKER"))
         (entdel e)
         (setq n (1+ n)))
        ((assoc 1071 xd)
         (cchk:set-color e (cdr (assoc 1071 xd)))
         (cchk:unstash e)
         (setq n (1+ n))))))
  (if (> n 0)
    (princ (strcat "\nCOVERCHECKRESCUE: restored or removed " (itoa n) " item(s)."))
    (princ "\nCOVERCHECKRESCUE: nothing to restore - no COVERCHECK markers in the drawing."))
  (princ))

;; --- small helpers -------------------------------------------------

(defun cchk:ent-color (ent / c)
  ;; the entity's explicit colour, 256 (ByLayer) when it has none
  (setq c (cdr (assoc 62 (entget ent))))
  (if c c 256))

(defun cchk:set-color (ent color / ed old)
  (setq ed  (entget ent)
        old (assoc 62 ed))
  (entmod (if old
            (subst (cons 62 color) old ed)
            (append ed (list (cons 62 color)))))
  (entupd ent))

(defun cchk:make-xline (p1 p2 / len)
  ;; infinite construction line through p1-p2 on the check layer,
  ;; tagged so reruns and COVERCHECKRESCUE can clear it
  (setq len (distance p1 p2))
  (if (and (> len 1e-8)
           (entmake (list '(0 . "XLINE")
                          '(100 . "AcDbEntity")
                          (cons 8 *cchk-constr-layer*)
                          '(100 . "AcDbXline")
                          (cons 10 p1)
                          (cons 11 (mapcar '(lambda (x) (/ x len))
                                           (mapcar '- p2 p1))))))
    (cchk:tag (entlast) "XLINE")))

(defun cchk:closest-on (ent pt / res)
  ;; closest point on ent to pt; nil when ent is not curve-like
  (setq res (vl-catch-all-apply 'vlax-curve-getClosestPointTo (list ent pt)))
  (if (vl-catch-all-error-p res) nil res))

(defun cchk:nearest-curve (pt exclude cands / best bestd cp d e)
  ;; (ent closest-point distance) for the candidate closest to pt
  (foreach e cands
    (if (and (not (eq e exclude)) (setq cp (cchk:closest-on e pt)))
      (progn
        (setq d (distance pt cp))
        (if (or (null bestd) (< d bestd))
          (setq bestd d
                best  (list e cp d))))))
  best)

(defun cchk:curve-ends (ent / cl sp ep)
  ;; the curve's two endpoints; nil when closed (or not a curve)
  (setq cl (vl-catch-all-apply 'vlax-curve-isClosed (list ent)))
  (if (or (vl-catch-all-error-p cl) cl)
    nil
    (progn
      (setq sp (vl-catch-all-apply 'vlax-curve-getStartPoint (list ent))
            ep (vl-catch-all-apply 'vlax-curve-getEndPoint (list ent)))
      (if (or (vl-catch-all-error-p sp) (vl-catch-all-error-p ep))
        nil
        (list sp ep)))))

(defun cchk:closest-of (pt pts / best bestd d q)
  (foreach q pts
    (setq d (distance pt q))
    (if (or (null bestd) (< d bestd)) (setq bestd d best q)))
  best)

(defun cchk:nearest-end (pt exclude cands / best bestd d e q)
  ;; closest endpoint over every open candidate curve
  (foreach e cands
    (if (not (eq e exclude))
      (foreach q (cchk:curve-ends e)
        (setq d (distance pt q))
        (if (or (null bestd) (< d bestd)) (setq bestd d best q)))))
  best)

(defun cchk:ptstr (p)
  ;; formatted with the drawing's own unit settings (LUNITS/LUPREC),
  ;; same as every measurement elsewhere in the report
  (strcat "(" (rtos (car p)) ", " (rtos (cadr p)) ")"))

(defun cchk:zoom-ent (ent / bb p1 p2 m)
  ;; zoom the current view onto ent with some breathing room
  (setq bb (cal:bbox-ent ent))
  (if bb
    (progn
      (setq p1 (car bb)
            p2 (cadr bb)
            m  (* *cchk-zoom-margin*
                  (max (- (car p2) (car p1)) (- (cadr p2) (cadr p1)) 1e-6)))
      (command "_.ZOOM" "_Window"
               (trans (list (- (car p1) m) (- (cadr p1) m) 0.0) 0 1)
               (trans (list (+ (car p2) m) (+ (cadr p2) m) 0.0) 0 1)))))

(defun cchk:zoom-2ents (e1 e2 / b1 b2 p1 p2 m)
  ;; zoom onto the combined box of two entities
  (setq b1 (cal:bbox-ent e1)
        b2 (cal:bbox-ent e2))
  (cond
    ((and b1 b2)
     (setq p1 (list (min (caar b1) (caar b2))
                    (min (cadar b1) (cadar b2)))
           p2 (list (max (caadr b1) (caadr b2))
                    (max (cadadr b1) (cadadr b2)))
           m  (* *cchk-zoom-margin*
                 (max (- (car p2) (car p1)) (- (cadr p2) (cadr p1)) 1e-6)))
     (command "_.ZOOM" "_Window"
              (trans (list (- (car p1) m) (- (cadr p1) m) 0.0) 0 1)
              (trans (list (+ (car p2) m) (+ (cadr p2) m) 0.0) 0 1)))
    (b1 (cchk:zoom-ent e1))
    (b2 (cchk:zoom-ent e2))))

(defun cchk:stage (ent saved keep)
  ;; bring an entity back to its own colour for review — unless it
  ;; already wears a COVERCHECK marker colour it must not lose
  (if (and (entget ent) (not (member ent keep)))
    (cchk:set-color ent (cdr (assoc ent saved)))))

(defun cchk:unstage (ent keep)
  ;; send a reviewed entity back into the grey background
  (if (and (entget ent) (not (member ent keep)))
    (cchk:set-color ent *cchk-grey-color*)))

(defun cchk:mark-x (pt col / p s)
  ;; diagonal cross - marks WHERE YOU DREW IT
  (setq p (trans pt 0 1)
        s (* 0.02 (getvar "VIEWSIZE")))
  (grdraw (list (- (car p) s) (- (cadr p) s)) (list (+ (car p) s) (+ (cadr p) s)) col 1)
  (grdraw (list (- (car p) s) (+ (cadr p) s)) (list (+ (car p) s) (- (cadr p) s)) col 1))

(defun cchk:mark-plus (pt col / p s)
  ;; upright cross - marks WHERE COVERCHECK WOULD PUT IT
  (setq p (trans pt 0 1)
        s (* 0.02 (getvar "VIEWSIZE")))
  (grdraw (list (- (car p) s) (cadr p)) (list (+ (car p) s) (cadr p)) col 1)
  (grdraw (list (car p) (- (cadr p) s)) (list (car p) (+ (cadr p) s)) col 1))

(defun cchk:mark-point (pt)
  ;; both strokes, for a point that is simply being pointed out
  (cchk:mark-x pt 2)
  (cchk:mark-plus pt 2))

(defun cchk:confirm-move (label orig sugg / ans newp)
  ;; The point has been put where COVERCHECK thinks it belongs, but BOTH
  ;; spots are marked and spelled out so there is no doubt which is
  ;; which: a red X where you drew it, a green + where we would move
  ;; it, joined by a line. Returns
  ;;   'move - take our suggestion
  ;;   'keep - put it back exactly where you drew it
  ;;   <point> - a spot you picked yourself (current UCS)
  (cchk:mark-x    orig *cchk-orig-color*)
  (cchk:mark-plus sugg *cchk-sugg-color*)
  (if (> (distance orig sugg) 1e-8)
    (grdraw (trans orig 0 1) (trans sugg 0 1) *cchk-sugg-color* 1))
  (princ (strcat "\n  " label " - which spot is right?"
                 "\n    Keep = where you drew it   " (cchk:ptstr orig)
                 "  (red X)"
                 "\n    Move = onto nearest object " (cchk:ptstr sugg)
                 "  (green +), " (rtos (distance orig sugg) 2 4) " away"
                 "\n    Pick = somewhere else you point at"))
  (initget "Move Keep Pick")
  (setq ans (getkword
              "\n  [Move/Keep/Pick] <Move>: "))
  (cond
    ((or (null ans) (= ans "Move")) 'move)
    ((= ans "Keep") 'keep)
    (t (setq newp (getpoint (strcat "\n  Pick the spot for " label
                                    " <Move to the green +>: ")))
       (if newp newp 'move))))

(defun cchk:mtext (ins height width text layer / e)
  ;; entmake an MTEXT, splitting text into 250-char DXF chunks
  (if (setq e (cal:mtext ins height width text layer))
    (cchk:tag e "REPORT")))

(defun cchk:attn-p (s)
  ;; T when a report line describes something questionable or that
  ;; needs looking over / fixing, so the report renders it in red
  (wcmatch (strcase s)
    "*FLAGGED*,*WRONG*,*SKIPPED*,*MAGENTA*,*MISSING*,*NOTHING*,*NO BLOCK*,*WORD NOT*,*WORD ERROR*,* ADD *,*MISMATCH*,*NOT CONFIRMED*,*NOT ATTACHED*,*OVERLAP*,*ASSOCIATIVE*,*DISAGREE*,*SUGGEST*,*BLANK*,*UNREADABLE*,*NOT A POLYLINE*,*LOOK AT*,*NO DASHED*,*AMBIGUOUS*,*ONLY ONE SIZE*,*NO INCHES*,*NOT TODAY*,*EXPECTED MM/DD/YYYY*"))

(defun cchk:red (s)
  ;; wrap an MTEXT run so it renders in the flag colour, reverting
  ;; to the surrounding colour after (braces scope the change)
  (strcat "{\\C" (itoa *cchk-flag-color*) ";" s "}"))

(defun cchk:small (s)
  ;; all-clear text renders at *cchk-green-scale* of the height the
  ;; red attention text gets, so problems stand out on the sheet
  (strcat "{\\H" (rtos *cchk-green-scale* 2 4) "x;" s "}"))

(defun cchk:big (s)
  ;; the report's title line: half again the base height
  (strcat "{\\H1.5x;" s "}"))

(defun cchk:hdg (s)
  ;; a section heading: underlined, with a thin blank line above it
  ;; so the sections read as blocks (the \P inside the first group is
  ;; a paragraph break at 0.4x height - a narrow gap, not a full line)
  (strcat "{\\H0.4x;\\P}{\\L" s "}"))

(defun cchk:linegrp (s)
  ;; which underlined section a report line files under, keyed on the
  ;; fixed prefixes the review gives its lines
  (cond ((wcmatch s "Dim *,Dimensions:*") "DIMENSIONS")
        ((wcmatch s "Arc *")              "ARCS")
        ((wcmatch s "Lines *")            "OVERLAPPING LINES")
        ((wcmatch s "Text *")             "TEXT & UNITS")
        (t                                "COVER CHECKS")))

(defun cchk:dimline-p (s)
  ;; T for a line that belongs to the DIMENSION AUDIT column - the
  ;; DIMCHECK-style findings, as opposed to the cover's own checks
  (member (cchk:linegrp s) '("DIMENSIONS" "ARCS" "OVERLAPPING LINES")))

;; Every dimension belongs on the dimension layer.  This is the one
;; dimension check the lite scan keeps: it costs a layer read apiece,
;; and a sheet whose dimensions sit on the wrong layer plots wrong
;; however sound the dimensions themselves are - so the verdict, and
;; the suggestion to run CDIM over them, belong on the main sheet
;; rather than in the DIMENSION AUDIT column.  The offending layers
;; are named, since that is what you need to go fix them.
;; Returns (sentence . needs-attention).
(defun cchk:dimlayer-verdict (dims / n off lays lay e)
  (setq n 0 off 0 lays nil)
  (foreach e dims
    (if (entget e)
      (progn
        (setq n   (1+ n)
              lay (cdr (assoc 8 (entget e))))
        (if (/= (strcase lay) (strcase *cchk-dim-layer*))
          (progn
            (setq off (1+ off))
            (if (not (member (strcase lay) lays))
              (setq lays (cons (strcase lay) lays))))))))
  (cond
    ((= n 0)
     (cons "no dimensions in the selection" nil))
    ((= off 0)
     (cons (strcat "all " (itoa n) " on " *cchk-dim-layer*) nil))
    (t
     (cons (strcat (itoa off) " of " (itoa n) " NOT on layer "
                   *cchk-dim-layer* " ("
                   (cchk:join (reverse lays) ", ")
                   ") - run " *cchk-dimfix-cmd* " to move them")
           T))))

;; --- feet-and-inch text ----------------------------------------------
;; A distance written in feet must state its inches too: 5' is wrong,
;; 5'-0" (or 5'-0'') is right, and a plain 40" is right as it stands.
;;
;; A FEET MARK is an apostrophe standing straight after a DIGIT, and
;; that is what keeps prose out of this: "Water's Edge", "Owner's" and
;; "don't" are possessives, not measurements, and are never flagged.
;; Two apostrophes together are the inch mark AutoCAD text often uses
;; in place of ", so 5'-0'' closes exactly as 5'-0" does.
;;
;; T when some feet mark in s is never closed by an inch mark before
;; the next feet mark or the end of the string -- so "5' and 7'-0"" is
;; caught on its first value while "3'-2"" passes.
(defun cchk:feet-open-p (s / lst n i c prev open found)
  (setq lst   (vl-string->list s)
        n     (length lst)
        i     0
        prev  0
        open  nil
        found nil)
  (while (< i n)
    (setq c (nth i lst))
    (cond
      ((= c 34)                                    ; " closes it
       (setq open nil i (1+ i)))
      ((and (= c 39) (< (1+ i) n) (= (nth (1+ i) lst) 39))
       (setq open nil i (+ i 2)))                  ; '' closes it too
      ((and (= c 39) (>= prev 48) (<= prev 57))    ; digit then ' = feet
       (if open (setq found T))                    ; the one before never closed
       (setq open T i (1+ i)))
      (t (setq i (1+ i))))
    (setq prev (nth (1- i) lst)))
  (or found open))

;; MTEXT reads \, { and } as formatting, so a snippet quoted out of the
;; drawing has them blanked before it goes anywhere near the report.
(defun cchk:mtsafe (s)
  (vl-list->string
    (mapcar '(lambda (c) (if (member c '(92 123 125)) 32 c))
            (vl-string->list s))))

;; The text an entity carries: TEXT and ATTRIB keep it in group 1,
;; MTEXT spills the overflow into group 3 chunks ahead of that.
(defun cchk:ent-text (ent / ed g head tail)
  (setq ed (entget ent) head "" tail "")
  (foreach g ed
    (cond ((= 3 (car g)) (setq head (strcat head (cdr g))))
          ((= 1 (car g)) (setq tail (cdr g)))))
  (strcat head tail))

;; Every text box in the selection: TEXT and MTEXT, plus the ATTRIB
;; values on blocks -- the parts of a block someone types into.  Text
;; baked into a block DEFINITION is left alone: it reads the same on
;; every insert and is not fixable from this drawing.
;; Returns ((handle . string) ...).
(defun cchk:text-items (ss / i e ed et out a ad)
  (setq i 0)
  (if ss
    (repeat (sslength ss)
      (setq e  (ssname ss i)
            i  (1+ i)
            ed (entget e)
            et (if ed (cdr (assoc 0 ed))))
      (cond
        ((member et '("TEXT" "MTEXT"))
         (setq out (cons (cons (cdr (assoc 5 ed)) (cchk:ent-text e)) out)))
        ((and (= et "INSERT") (assoc 66 ed) (= 1 (cdr (assoc 66 ed))))
         (setq a (entnext e))
         (while (and a (setq ad (entget a)) (= "ATTRIB" (cdr (assoc 0 ad))))
           (setq out (cons (cons (cdr (assoc 5 ad)) (cchk:ent-text a)) out)
                 a   (entnext a)))))))
  (reverse out))

;; The verdict over every text box, plus one report line per offender.
;; Returns (sentence needs-attention (line ...)).
(defun cchk:audit-units (ss / items it s n bad lines)
  (setq items (cchk:text-items ss) n 0 bad 0 lines nil)
  (foreach it items
    (setq s (cdr it))
    (if (and s (/= s ""))
      (progn
        (setq n (1+ n))
        (if (cchk:feet-open-p s)
          (setq bad   (1+ bad)
                lines (cons (strcat "Text " (car it) ": \""
                                    (cchk:mtsafe (cchk:clip s 40))
                                    "\" gives feet with NO INCHES"
                                    " - write it 5'-0\" not 5'")
                            lines))))))
  (list
    (cond
      ((= n 0) "no text in the selection")
      ((= bad 0) (strcat "all " (itoa n) " text item"
                         (if (= 1 n) "" "s") " OK"))
      (t (strcat (itoa bad) " of " (itoa n) " text item"
                 (if (= 1 n) "" "s") " give feet with NO INCHES"
                 " - write 5'-0\" not 5'")))
    (> bad 0)
    (reverse lines)))

;; --- the Tech Title date ---------------------------------------------
;; The sheet's Tech Title block carries a Date attribute, and it must
;; read TODAY in MM/DD/YYYY form.  A sheet going out under an old date
;; is the mistake this catches: the drawing was reworked and the title
;; block never caught up.

(defun cchk:datenorm (s)
  ;; a value may arrive labelled ("Date = 05/01/2024"); the date is
  ;; whatever follows the last "="
  (cchk:after-eq (if s s "")))

(defun cchk:all-digits-p (s / i n c ok)
  (setq n (strlen s) ok (> n 0) i 1)
  (while (and ok (<= i n))
    (setq c (ascii (substr s i 1)))
    (if (or (< c 48) (> c 57)) (setq ok nil))
    (setq i (1+ i)))
  ok)

(defun cchk:days-in-month (mo yr)
  (cond
    ((member mo '(1 3 5 7 8 10 12)) 31)
    ((member mo '(4 6 9 11)) 30)
    ((and (= 0 (rem yr 4)) (or (/= 0 (rem yr 100)) (= 0 (rem yr 400)))) 29)
    (t 28)))

(defun cchk:today-mdy ( / d)
  ;; (month day year) off the computer clock.  CDATE is
  ;; YYYYMMDD.HHMMSSmsec, decoded arithmetically so DIMZIN (which trims
  ;; rtos output) cannot mangle it.
  (setq d (fix (getvar "CDATE")))
  (list (rem (fix (/ d 100)) 100) (rem d 100) (fix (/ d 10000))))

(defun cchk:mdy-str (mdy)
  (strcat (cal:zeropad2 (car mdy)) "/" (cal:zeropad2 (cadr mdy)) "/"
          (itoa (caddr mdy))))

;; nil when raw is today's date written MM/DD/YYYY; otherwise a short
;; string saying what is wrong with it.
(defun cchk:date-verdict (raw / s mo dd yr now)
  (setq s (vl-string-trim " \t" (cchk:datenorm raw)))
  (cond
    ((= s "") "is blank - expected MM/DD/YYYY")
    ((or (/= (strlen s) 10)
         (/= (substr s 3 1) "/")
         (/= (substr s 6 1) "/")
         (not (cchk:all-digits-p (substr s 1 2)))
         (not (cchk:all-digits-p (substr s 4 2)))
         (not (cchk:all-digits-p (substr s 7 4))))
     (strcat "'" s "' is not in MM/DD/YYYY format - expected MM/DD/YYYY"))
    (t
     (setq mo (atoi (substr s 1 2))
           dd (atoi (substr s 4 2))
           yr (atoi (substr s 7 4)))
     (cond
       ((or (< mo 1) (> mo 12))
        (strcat "'" s "' - " (substr s 1 2)
                " is not a month (01-12) - expected MM/DD/YYYY"))
       ((or (< dd 1) (> dd (cchk:days-in-month mo yr)))
        (strcat "'" s "' - " (substr s 4 2)
                " is not a valid day for that month - expected MM/DD/YYYY"))
       ((progn (setq now (cchk:today-mdy))
               (not (and (= mo (car now)) (= dd (cadr now))
                         (= yr (caddr now)))))
        (strcat "'" s "' is NOT TODAY'S DATE (" (cchk:mdy-str now)
                ") - update it"))
       (t nil)))))

;; The Tech Title block: the first INSERT whose name carries it, looked
;; for in the selection and then across the drawing, since the title
;; block sits outside the area someone highlights as often as not.
(defun cchk:find-title (ss / pat i e ed out ss2)
  (setq pat (strcat "*" (cchk:squash *cchk-title-block*) "*") i 0)
  (if ss
    (repeat (sslength ss)
      (setq e  (ssname ss i)
            i  (1+ i)
            ed (entget e))
      (if (and (null out) ed (= "INSERT" (cdr (assoc 0 ed)))
               (wcmatch (cchk:squash (cchk:block-name e)) pat))
        (setq out e))))
  (if (null out)
    (progn
      (setq ss2 (ssget "_X" '((0 . "INSERT"))) i 0)
      (if ss2
        (repeat (sslength ss2)
          (setq e (ssname ss2 i) i (1+ i))
          (if (and (null out)
                   (wcmatch (cchk:squash (cchk:block-name e)) pat))
            (setq out e))))))
  out)

;; The verdict: (sentence . needs-attention).  With no Tech Title in
;; reach there is nothing to read, and that is said plainly rather than
;; flagged -- a cover or spa sheet may well be checked on its own.
(defun cchk:audit-date (ss / blk ed raw bad)
  (setq blk (cchk:find-title ss))
  (if (null blk)
    (cons (strcat "no '" *cchk-title-block* "' block in reach - date NOT CHECKED")
          nil)
    (progn
      (setq ed  (entget blk)
            raw (if (and (assoc 66 ed) (= 1 (cdr (assoc 66 ed))))
                  (cchk:ins-attrib blk *cchk-date-tag*))
            bad (if raw
                  (cchk:date-verdict raw)
                  (strcat "is missing from the block"
                          " - expected MM/DD/YYYY")))
      (if bad
        (cons (strcat *cchk-date-tag* " " bad) T)
        (cons (strcat *cchk-date-tag* " = '"
                      (vl-string-trim " \t" (cchk:datenorm raw)) "' - OK")
              nil)))))

;; The whole report: the cover checks on the MAIN sheet - a large
;; title, the date and version, a verdict line, the colour legend, a
;; SUMMARY dashboard, then the findings under underlined headings -
;; and the DIMCHECK-style findings (dimensions, arcs, overlapping
;; lines) in a DIMENSION AUDIT column to its right.  A lite run
;; writes the main sheet alone.
;;   title   the report's big first line ("COVERCHECK REPORT", ...)
;;   note    extra legend sentence(s) up front, or nil
;;   hdr     (text . attn) pairs for the SUMMARY dashboard
;;   dhdr    (text . attn) pairs for the dimension column's dashboard
;;   lines   every finding line, report order
;;   lite    T = skip the dimension column
;; Returns the x of the report's right edge, for the caller's zoom.
(defun cchk:write-report (title note hdr dhdr lines lite
                          minx miny maxx maxy
                          / mainl diml l pr nred nmain ndim nlin grps grp
                            ref h ins ins2 txt right)
  (cal:ensure-layer *cchk-report-layer* *cchk-report-color*)
  (foreach l lines
    (if (cchk:dimline-p l)
      (setq diml (cons l diml))
      (setq mainl (cons l mainl))))
  (setq mainl (reverse mainl)
        diml  (reverse diml))
  ;; the verdict counts every line that will render red, either column
  (setq nred 0)
  (foreach pr (append hdr dhdr)
    (if (cdr pr) (setq nred (1+ nred))))
  (foreach l lines
    (if (cchk:attn-p l) (setq nred (1+ nred))))
  ;; sizing: weighted line count per column - the head is ~4.5 lines,
  ;; a heading is a line plus its 0.4 gap - and the taller column
  ;; drives the text height, clamped as before
  (setq nmain 4.5 grps nil)
  (foreach l mainl
    (if (not (member (cchk:linegrp l) grps))
      (setq grps (cons (cchk:linegrp l) grps))))
  (setq nmain (+ nmain (* 1.4 (1+ (length grps)))))   ; SUMMARY + sections
  (setq nmain (+ nmain (* (length hdr) *cchk-green-scale*)))
  (foreach l mainl
    (setq nmain (+ nmain (if (cchk:attn-p l) 1.0 *cchk-green-scale*))))
  (setq ndim 0.0)
  (if (not lite)
    (progn
      (setq ndim 2.5 grps nil)                        ; column title + legend
      (foreach l diml
        (if (not (member (cchk:linegrp l) grps))
          (setq grps (cons (cchk:linegrp l) grps))))
      (setq ndim (+ ndim (* 1.4 (length grps))))
      (setq ndim (+ ndim (* (length dhdr) *cchk-green-scale*)))
      (foreach l diml
        (setq ndim (+ ndim (if (cchk:attn-p l) 1.0 *cchk-green-scale*))))))
  (setq nlin (max nmain ndim))
  (if (and minx (> (max (- maxy miny) (- maxx minx)) 1e-8))
    (progn
      (setq ref (max (- maxy miny) (* 0.25 (- maxx minx)))
            h   (/ ref (* 1.66 nlin)))
      (if (> h (/ ref 30.0))  (setq h (/ ref 30.0)))
      (if (< h (/ ref 200.0)) (setq h (/ ref 200.0))))
    (progn
      (setq h (* (getvar "DIMTXT") (getvar "DIMSCALE")))
      (if (or (null h) (<= h 0.0)) (setq h 2.5))))
  (setq ins (if minx
              (list (+ maxx (* 0.05 (max (- maxx minx) 1.0))) maxy 0.0)
              (list 0.0 0.0 0.0)))
  ;; --- the main sheet
  (setq txt (strcat (cchk:big title)
                    "\\P"
                    (cchk:small (strcat (cal:datestr)
                                        "  -  COVERCHECK "
                                        *cchk-version*))
                    "\\P"
                    "{\\H1.2x;"
                    (if (> nred 0)
                      (cchk:red (strcat (itoa nred) " LINE"
                                        (if (= 1 nred) "" "S")
                                        " NEED"
                                        (if (= 1 nred) "S" "")
                                        " ATTENTION"))
                      "ALL CLEAR - every check passed")
                    "}"
                    "\\P"
                    (cchk:small
                      (strcat (if note note "")
                              "Lines needing attention are in "
                              (cchk:red "red")
                              " at full size; lines that checked out"
                              " are smaller."))))
  (setq txt (strcat txt "\\P" (cchk:hdg "SUMMARY")))
  (foreach pr hdr
    (setq txt (strcat txt "\\P"
                      (if (cdr pr)
                        (cchk:red (strcat "  " (car pr)))
                        (cchk:small (strcat "  " (car pr)))))))
  (setq grp nil)
  (foreach l mainl
    (if (/= grp (cchk:linegrp l))
      (setq grp (cchk:linegrp l)
            txt (strcat txt "\\P" (cchk:hdg grp))))
    (setq txt (strcat txt "\\P"
                      (if (cchk:attn-p l)
                        (cchk:red (strcat "  " l))
                        (cchk:small (strcat "  " l))))))
  (cchk:mtext ins h (* *cchk-report-chars* h) txt *cchk-report-layer*)
  (setq right (+ (car ins) (* *cchk-report-chars* h)))
  ;; --- the DIMENSION AUDIT column
  (if (not lite)
    (progn
      (setq ins2 (list (+ (car ins) (* (+ *cchk-report-chars* 2.0) h))
                       (cadr ins) 0.0)
            txt  (strcat "{\\H1.2x;DIMENSION AUDIT}"
                         "\\P"
                         (cchk:small
                           (strcat "Dimensions, arcs and overlapping"
                                   " lines - DIMCHECK's ground, kept"
                                   " off the main sheet."))))
      (foreach pr dhdr
        (setq txt (strcat txt "\\P"
                          (if (cdr pr)
                            (cchk:red (strcat "  " (car pr)))
                            (cchk:small (strcat "  " (car pr)))))))
      (setq grp nil)
      (foreach l diml
        (if (/= grp (cchk:linegrp l))
          (setq grp (cchk:linegrp l)
                txt (strcat txt "\\P" (cchk:hdg grp))))
        (setq txt (strcat txt "\\P"
                          (if (cchk:attn-p l)
                            (cchk:red (strcat "  " l))
                            (cchk:small (strcat "  " l))))))
      (cchk:mtext ins2 h (* *cchk-report-chars* h) txt *cchk-report-layer*)
      (setq right (+ (car ins2) (* *cchk-report-chars* h)))))
  right)

;; --- geometry ------------------------------------------------------

(defun cchk:planar-arc-p (ed / n)
  ;; only arcs drawn in the world XY plane are handled
  (setq n (cdr (assoc 210 ed)))
  (or (null n)
      (and (< (abs (car n)) 1e-9)
           (< (abs (cadr n)) 1e-9)
           (> (caddr n) 0.0))))

(defun cchk:rebuild-arc (ent which fixed mid target / c r a1 a2 am tmp ed pair)
  ;; re-fit the arc through its fixed end, its old midpoint and the
  ;; target point; returns T on success
  (if (and (> (distance target fixed) 1e-8)
           (setq c (cal:circumcenter fixed mid target)))
    (progn
      (setq r  (distance c target)
            a1 (angle c (if (eq which 'start) target fixed))
            a2 (angle c (if (eq which 'start) fixed target))
            am (angle c mid))
      ;; ARC entities always sweep counter-clockwise from start to
      ;; end; keep the sweep that contains the old midpoint
      (if (> (cal:angnorm (- am a1)) (cal:angnorm (- a2 a1)))
        (setq tmp a1
              a1  a2
              a2  tmp))
      (setq ed (entget ent))
      (foreach pair (list (cons 10 c) (cons 40 r) (cons 50 a1) (cons 51 a2))
        (setq ed (subst pair (assoc (car pair) ed) ed)))
      (if (entmod ed)
        (progn (entupd ent) T)))))

(defun cchk:move-arc-end (ent which target / mid other)
  ;; re-fit the arc so the chosen endpoint lands on target (WCS)
  (setq mid   (vlax-curve-getPointAtDist
                ent
                (/ (vlax-curve-getDistAtParam ent (vlax-curve-getEndParam ent)) 2.0))
        other (if (eq which 'start)
                (vlax-curve-getEndPoint ent)
                (vlax-curve-getStartPoint ent)))
  (cchk:rebuild-arc ent which other mid target))

(defun cchk:overlap-info (la lb / a1 a2 b1 b2 u lena s1 s2 tmp lo hi)
  ;; when segments la and lb are collinear (within *cchk-olap-fuzz*)
  ;; and run on top of each other for more than *cchk-tol*, returns
  ;;   (ov-start ov-end ov-length union-start union-end)
  ;; nil when they do not overlap (touching end-to-end is fine)
  (setq a1 (cchk:seg-p1 la)
        a2 (cchk:seg-p2 la)
        b1 (cchk:seg-p1 lb)
        b2 (cchk:seg-p2 lb)
        u  (cal:unitn (mapcar '- a2 a1)))
  (if (and u
           (<= (cal:pt-line-dist b1 a1 u) *cchk-olap-fuzz*)
           (<= (cal:pt-line-dist b2 a1 u) *cchk-olap-fuzz*))
    (progn
      (setq lena (distance a1 a2)
            s1   (cal:proj-param b1 a1 u)
            s2   (cal:proj-param b2 a1 u))
      (if (> s1 s2) (setq tmp s1 s1 s2 s2 tmp))
      (setq lo (max 0.0 s1)
            hi (min lena s2))
      (if (> (- hi lo) *cchk-tol*)
        (list (cal:axis-pt a1 u lo)
              (cal:axis-pt a1 u hi)
              (- hi lo)
              (cal:axis-pt a1 u (min 0.0 s1))
              (cal:axis-pt a1 u (max lena s2)))))))

(defun cchk:merge-lines (la lb info / ed)
  ;; stretch la's LINE over the union of both, delete lb's LINE
  (setq ed (entget (cchk:seg-ent la))
        ed (subst (cons 10 (nth 3 info)) (assoc 10 ed) ed)
        ed (subst (cons 11 (nth 4 info)) (assoc 11 ed) ed))
  (entmod ed)
  (entupd (cchk:seg-ent la))
  (entdel (cchk:seg-ent lb)))

(defun cchk:whole-line-p (s / ed)
  ;; T when the segment IS its owner entity - only whole LINEs can be
  ;; merged; a polyline edge has to be fixed by hand
  (setq ed (entget (cchk:seg-ent s)))
  (= "LINE" (cdr (assoc 0 ed))))

(defun cchk:find-overlaps (segs / atol fams a placed fam recs e p1 p2 dx dy
                                off s1 s2 tmp rest r q pairs seen key)
  ;; every overlapping segment pair, without comparing all pairs:
  ;; segments are bucketed by direction, then swept in offset order so
  ;; only genuinely collinear neighbours are ever tested. Segments of
  ;; the same entity are skipped (a polyline meeting itself is not a
  ;; duplicate), as are pairs already found through another segment.
  (setq atol  (* 0.5 (/ pi 180.0))              ; 0.5 deg is ample at this fuzz
        fams  nil
        pairs nil
        seen  nil)
  (foreach e segs
    (setq a      (cchk:seg-dir-ang e)
          placed nil)
    (foreach fam fams
      (if (and (not placed)
               (or (<= (cal:ang-diff a (car fam)) atol)))
        (setq fams   (subst (cons (car fam) (cons e (cdr fam))) fam fams)
              placed T)))
    (if (not placed) (setq fams (cons (list a e) fams))))
  (foreach fam fams
    (if (cdr (cdr fam))                          ; two or more to compare
      (progn
        (setq a  (car fam)
              dx (cos a)
              dy (sin a)
              recs nil)
        (foreach e (cdr fam)
          (setq p1  (cchk:seg-p1 e)
                p2  (cchk:seg-p2 e)
                off (- (* (cadr p1) dx) (* (car p1) dy))
                s1  (+ (* (car p1) dx) (* (cadr p1) dy))
                s2  (+ (* (car p2) dx) (* (cadr p2) dy)))
          (if (> s1 s2) (setq tmp s1 s1 s2 s2 tmp))
          (setq recs (cons (list off s1 s2 e) recs)))
        (setq recs (cchk:sort-recs recs))
        ;; sorted by offset: only sweep forward while still collinear
        (while recs
          (setq r    (car recs)
                rest (cdr recs))
          (while (and rest
                      (<= (- (car (car rest)) (car r)) *cchk-olap-fuzz*))
            (setq q (car rest))
            (if (and (not (eq (cchk:seg-ent (cadddr r))
                              (cchk:seg-ent (cadddr q))))
                     ;; spans must actually meet before the exact test
                     (> (min (caddr r) (caddr q)) (max (cadr r) (cadr q)))
                     (cchk:overlap-info (cadddr r) (cadddr q)))
              (progn
                (setq key (list (cchk:seg-ent (cadddr r))
                                (cchk:seg-ent (cadddr q))))
                (if (not (member key seen))
                  (setq seen  (cons key (cons (reverse key) seen))
                        pairs (cons (list (cadddr r) (cadddr q)) pairs)))))
            (setq rest (cdr rest)))
          (setq recs (cdr recs))))))
  (reverse pairs))

;; --- segments: lines AND polyline edges ----------------------------
;; Detection works on "segs" - (start end owner-entity) records - so a
;; run of edges drawn as one polyline counts exactly like the same
;; shape drawn as separate LINEs.

(defun cchk:seg-p1 (s) (car s))
(defun cchk:seg-p2 (s) (cadr s))
(defun cchk:seg-ent (s) (caddr s))

(defun cchk:ocs->wcs (p nz)
  (if (and nz (not (equal nz '(0.0 0.0 1.0) 1e-9))) (trans p nz 0) p))

(defun cchk:lwpoly-segs (ent / ed nz elev vs bl cls n i segs g)
  ;; straight edges of an LWPOLYLINE; bulged (arc) edges are skipped
  (setq ed   (entget ent)
        nz   (cdr (assoc 210 ed))
        elev (cdr (assoc 38 ed))
        cls  (= 1 (logand 1 (cdr (assoc 70 ed))))
        vs   nil
        bl   nil)
  (if (null elev) (setq elev 0.0))
  (foreach g ed
    (cond
      ((= 10 (car g))
       (setq vs (cons (cchk:ocs->wcs (list (car (cdr g)) (cadr (cdr g)) elev) nz) vs)
             bl (cons 0.0 bl)))
      ((= 42 (car g))
       (if bl (setq bl (cons (cdr g) (cdr bl)))))))
  (setq vs (reverse vs)
        bl (reverse bl)
        n  (length vs)
        i  0)
  (while (< i (1- n))
    (if (equal 0.0 (nth i bl) 1e-12)
      (setq segs (cons (list (nth i vs) (nth (1+ i) vs) ent) segs)))
    (setq i (1+ i)))
  (if (and cls (> n 2) (equal 0.0 (nth (1- n) bl) 1e-12))
    (setq segs (cons (list (nth (1- n) vs) (car vs) ent) segs)))
  segs)

(defun cchk:heavy-poly-segs (ent / e ed vs bl cls n i segs)
  ;; straight edges of an old-style POLYLINE (VERTEX entities)
  (setq cls (= 1 (logand 1 (cdr (assoc 70 (entget ent)))))
        e   (entnext ent)
        vs  nil
        bl  nil)
  (while (and e (= "VERTEX" (cdr (assoc 0 (setq ed (entget e))))))
    (if (zerop (logand 16 (cdr (assoc 70 ed))))    ; skip spline frame points
      (setq vs (cons (cdr (assoc 10 ed)) vs)
            bl (cons (if (assoc 42 ed) (cdr (assoc 42 ed)) 0.0) bl)))
    (setq e (entnext e)))
  (setq vs (reverse vs)
        bl (reverse bl)
        n  (length vs)
        i  0)
  (while (< i (1- n))
    (if (equal 0.0 (nth i bl) 1e-12)
      (setq segs (cons (list (nth i vs) (nth (1+ i) vs) ent) segs)))
    (setq i (1+ i)))
  (if (and cls (> n 2) (equal 0.0 (nth (1- n) bl) 1e-12))
    (setq segs (cons (list (nth (1- n) vs) (car vs) ent) segs)))
  segs)

(defun cchk:ent-segs (ent / ed et)
  ;; every straight segment an entity contributes, in WCS
  (setq ed (entget ent)
        et (cdr (assoc 0 ed)))
  (cond
    ((= et "LINE")       (list (list (cdr (assoc 10 ed)) (cdr (assoc 11 ed)) ent)))
    ((= et "LWPOLYLINE") (cchk:lwpoly-segs ent))
    ((= et "POLYLINE")   (cchk:heavy-poly-segs ent))))

(defun cchk:collect-segs (ents / segs e s)
  ;; all straight segments of a list of entities, longer than the
  ;; attachment tolerance (zero-length stubs help nothing)
  (foreach e ents
    (if (entget e)
      (foreach s (cchk:ent-segs e)
        (if (> (distance (car s) (cadr s)) *cchk-tol*)
          (setq segs (cons s segs))))))
  (reverse segs))

(defun cchk:seg-dir-ang (s / a)
  ;; segment direction folded into [0, pi)
  (setq a (angle (cchk:seg-p1 s) (cchk:seg-p2 s)))
  (if (>= a pi) (- a pi) a))

(defun cchk:sort-recs (recs / out r pre rest)
  ;; stable insertion sort by (car rec); keeps equal elements
  (setq out nil)
  (foreach r recs
    (setq pre  nil
          rest out)
    (while (and rest (>= (car r) (caar rest)))
      (setq pre  (cons (car rest) pre)
            rest (cdr rest)))
    (setq out (append (reverse pre) (list r) rest)))
  out)

;; --- block & text helpers ------------------------------------------

(defun cchk:norm-text (s)
  ;; uppercase, with every non-alphanumeric squashed to a space, so
  ;; word searches ignore case, punctuation and MTEXT format codes
  (if (null s)
    ""
    (vl-list->string
      (mapcar '(lambda (c)
                 (cond
                   ((and (>= c 48) (<= c 57)) c)         ; 0-9
                   ((and (>= c 65) (<= c 90)) c)         ; A-Z
                   ((and (>= c 97) (<= c 122)) (- c 32)) ; a-z -> A-Z
                   (t 32)))
               (vl-string->list s)))))

(defun cchk:block-name (ent / res)
  ;; effective block name (sees through dynamic blocks)
  (setq res (vl-catch-all-apply
              'vla-get-EffectiveName
              (list (vlax-ename->vla-object ent))))
  (if (vl-catch-all-error-p res)
    (cdr (assoc 2 (entget ent)))
    res))

(defun cchk:blockdef-texts (bname depth / lst e et g)
  ;; TEXT/MTEXT/ATTDEF inside a block definition, following nested
  ;; blocks down to depth so a title wrapped in a wrapper is found
  (setq e (tblobjname "BLOCK" bname))
  (if e
    (progn
      (setq e (entnext e))
      (while (and e (/= "ENDBLK" (setq et (cdr (assoc 0 (entget e))))))
        (cond
          ((member et '("TEXT" "ATTDEF"))
           (setq lst (cons (cdr (assoc 1 (entget e))) lst)))
          ((= et "MTEXT")
           (foreach g (entget e)
             (if (member (car g) '(1 3))
               (setq lst (cons (cdr g) lst)))))
          ((and (= et "INSERT") (> depth 1))
           (setq lst (cons (cdr (assoc 2 (entget e))) lst)  ; nested block NAME
                 lst (append (cchk:blockdef-texts (cdr (assoc 2 (entget e)))
                                                  (1- depth))
                             lst))))
        (setq e (entnext e)))))
  lst)

(defun cchk:ins-texts (ent / ed lst e)
  ;; every piece of text an INSERT shows: its attribute values plus
  ;; the text inside its block definition, nested blocks included
  (setq ed  (entget ent)
        lst nil)
  (if (= 1 (cdr (assoc 66 ed)))               ; attributes follow
    (progn
      (setq e (entnext ent))
      (while (and e (= "ATTRIB" (cdr (assoc 0 (entget e)))))
        (setq lst (cons (cdr (assoc 1 (entget e))) lst)
              e   (entnext e)))))
  (append lst (cchk:blockdef-texts (cdr (assoc 2 ed)) *cchk-block-depth*)))

(defun cchk:block-has-layer-p (bname layer depth / e et found)
  ;; does the block definition (or a block it nests, down to depth)
  ;; draw anything on the given layer?
  (setq e (tblobjname "BLOCK" bname))
  (if e
    (progn
      (setq e (entnext e))
      (while (and e (not found)
                  (/= "ENDBLK" (setq et (cdr (assoc 0 (entget e))))))
        (if (= (strcase (cdr (assoc 8 (entget e)))) (strcase layer))
          (setq found T))
        (if (and (not found) (= et "INSERT") (> depth 1))
          (if (cchk:block-has-layer-p (cdr (assoc 2 (entget e))) layer (1- depth))
            (setq found T)))
        (setq e (entnext e)))))
  found)

(defun cchk:ins-matches (ent phrase / pat found s)
  ;; T when the INSERT's (effective) name or any text it shows
  ;; contains the phrase, ignoring case and punctuation
  (setq pat   (strcat "*" (cchk:norm-text phrase) "*")
        found (wcmatch (cchk:norm-text (cchk:block-name ent)) pat))
  (foreach s (cchk:ins-texts ent)
    (if (wcmatch (cchk:norm-text s) pat)
      (setq found T)))
  found)

(defun cchk:clip (s n)
  (if (> (strlen s) n) (strcat (substr s 1 n) "...") s))

(defun cchk:join (lst sep / out s)
  ;; "A" + "B" + ... joined with sep
  (foreach s lst
    (setq out (if out (strcat out sep s) s)))
  out)

(defun cchk:squash (s)
  ;; norm-text with the spaces removed too, so "Cover Material" finds
  ;; a block that is actually named "CoverMaterial"
  (vl-list->string (vl-remove 32 (vl-string->list (cchk:norm-text s)))))

(defun cchk:ins-attrib (ent tag / e ed val)
  ;; value of the attribute with the given tag on an INSERT; nil
  ;; when the block has no such attribute
  (setq tag (strcase tag))
  (if (= 1 (cdr (assoc 66 (entget ent))))
    (progn
      (setq e (entnext ent))
      (while (and e (null val) (= "ATTRIB" (cdr (assoc 0 (entget e)))))
        (setq ed (entget e))
        (if (= tag (strcase (cdr (assoc 2 ed))))
          (setq val (cdr (assoc 1 ed))))
        (setq e (entnext e)))))
  val)

(defun cchk:parse-num (s / p num den)
  ;; "4", "4.5", "1/2" -> real
  (setq p (vl-string-search "/" s))
  (if p
    (progn
      (setq num (atof (substr s 1 p))
            den (atof (substr s (+ p 2))))
      (if (> den 0.0) (/ num den) 0.0))
    (atof s)))

(defun cchk:after-eq (s / p)
  ;; the part after the last "=", so a label never contributes its
  ;; own digits: "Finished Wall Ht = 40''" -> " 40''"
  (while (setq p (vl-string-search "=" s))
    (setq s (substr s (+ p 2))))
  s)

(defun cchk:len-values (s / lst i n c numstr toks unit vals cur tok)
  ;; every length written in the text, as a list of numbers in inches
  ;; (drawing units). ' = feet, '' or " = inches, a bare number counts
  ;; as inches. Feet and bare numbers carry on into the same value, an
  ;; inch mark closes it, so a compound height stays ONE value while a
  ;; list stays several:
  ;;   "40''"          -> (40.0)
  ;;   "3'-4''"        -> (40.0)
  ;;   "3' 4 1/2\""    -> (40.5)
  ;;   "0'', 40'', 45''" -> (0.0 40.0 45.0)
  ;; A label before the last "=" is ignored, so the attribute may read
  ;; "Finished Wall Ht = 40''" and still measure 40.
  (setq s    (cchk:after-eq s)
        lst  (vl-string->list s)
        i    0
        n    (length lst)
        toks nil)
  (while (< i n)
    (setq c (nth i lst))
    (if (or (and (>= c 48) (<= c 57)) (= c 46) (= c 47))  ; digit . /
      (progn
        (setq numstr "")
        (while (and (< i n)
                    (setq c (nth i lst))
                    (or (and (>= c 48) (<= c 57)) (= c 46) (= c 47)))
          (setq numstr (strcat numstr (chr c))
                i      (1+ i)))
        (setq unit nil)
        (cond
          ((and (< i n) (= (nth i lst) 34))               ; "
           (setq unit 'in
                 i    (1+ i)))
          ((and (< i n) (= (nth i lst) 39))               ; '
           (if (and (< (1+ i) n) (= (nth (1+ i) lst) 39))
             (setq unit 'in                               ; ''
                   i    (+ i 2))
             (setq unit 'ft
                   i    (1+ i)))))
        (setq toks (append toks (list (cons (cchk:parse-num numstr) unit)))))
      (setq i (1+ i))))
  (setq vals nil
        cur  nil)
  (foreach tok toks
    (setq cur (+ (if cur cur 0.0)
                 (if (eq (cdr tok) 'ft) (* 12.0 (car tok)) (car tok))))
    (if (eq (cdr tok) 'in)                     ; inches close the value
      (setq vals (append vals (list cur))
            cur  nil)))
  (if cur (setq vals (append vals (list cur))))
  vals)

(defun cchk:parse-len (s)
  ;; the first length written in the text, in inches; nil when none
  (car (cchk:len-values s)))

;; --- dimension review ----------------------------------------------

(defun cchk:dim-style (ent / s)
  ;; the dimension's style name, "" when it has none
  (setq s (cdr (assoc 3 (entget ent))))
  (if s s ""))

(defun cchk:style-rank (style / i r s)
  ;; position of the style in *cchk-style-order* (exact name match,
  ;; case-blind); unlisted styles land after every listed one
  (setq style (strcase style)
        i     0
        r     nil)
  (foreach s *cchk-style-order*
    (if (and (null r) (= (strcase s) style)) (setq r i))
    (setq i (1+ i)))
  (if r r (length *cchk-style-order*)))

(defun cchk:ent-center (ent / bb)
  ;; (x y) centre of the entity's box; falls back to its group-10 point
  (setq bb (cal:bbox-ent ent))
  (if bb
    (list (* 0.5 (+ (caar bb) (caadr bb)))
          (* 0.5 (+ (cadar bb) (cadadr bb))))
    (progn
      (setq bb (cdr (assoc 10 (entget ent))))
      (if bb (list (car bb) (cadr bb)) (list 0.0 0.0)))))

(defun cchk:dim-order-p (r1 r2 rowtol)
  ;; strict "r1 reviews before r2" for recs (rank cx cy ent):
  ;; style rank first, then row (higher = earlier), then left first
  (cond
    ((< (car r1) (car r2)) T)
    ((> (car r1) (car r2)) nil)
    ((> (- (caddr r1) (caddr r2)) rowtol) T)   ; r1 sits a row above
    ((> (- (caddr r2) (caddr r1)) rowtol) nil) ; r2 sits a row above
    (t (< (cadr r1) (cadr r2)))))              ; same row: left first

(defun cchk:sort-dims (dims rowtol / recs cen r out pre rest e)
  ;; stable insertion sort into review order
  (setq recs nil)
  (foreach e dims
    (setq cen  (cchk:ent-center e)
          recs (cons (list (cchk:style-rank (cchk:dim-style e))
                           (car cen) (cadr cen) e)
                     recs)))
  (setq recs (reverse recs)
        out  nil)
  (foreach r recs
    (setq pre  nil
          rest out)
    (while (and rest (not (cchk:dim-order-p r (car rest) rowtol)))
      (setq pre  (cons (car rest) pre)
            rest (cdr rest)))
    (setq out (append (reverse pre) (list r) rest)))
  (mapcar '(lambda (r) (nth 3 r)) out))

(defun cchk:dim-meas (ent / ed dtype p13 p14 ang v meas)
  ;; the dimension's current measurement as display text, formatted
  ;; with the drawing's unit settings (LUNITS/AUNITS); nil if unknown.
  ;; Linear/aligned dims are recomputed from their definition points
  ;; so the value reflects any point that was just moved.
  (setq ed    (entget ent)
        dtype (logand 7 (cdr (assoc 70 ed)))
        meas  (cdr (assoc 42 ed)))            ; stored actual measurement
  (cond
    ((= dtype 1)                              ; aligned: point-to-point
     (setq p13 (cdr (assoc 13 ed))
           p14 (cdr (assoc 14 ed)))
     (if (and p13 p14) (rtos (distance p13 p14))))
    ((= dtype 0)                              ; rotated/linear: project the
     (setq p13 (cdr (assoc 13 ed))            ; points onto the dim direction
           p14 (cdr (assoc 14 ed))
           ang (cdr (assoc 50 ed)))
     (if (and p13 p14)
       (progn
         (if (null ang) (setq ang 0.0))
         (setq v (mapcar '- p14 p13))
         (rtos (abs (+ (* (car v) (cos ang))
                       (* (cadr v) (sin ang))))))))
    ((member dtype '(2 5))                    ; angular: show the angle
     (if (and meas (>= meas 0.0)) (angtos meas)))
    (t                                        ; radius/diameter/ordinate
     (if (and meas (>= meas 0.0)) (rtos meas)))))

(defun cchk:audit-dim-point (ent gcode label cands / ed pt near sugg ans final how)
  ;; audits one definition point: an off-object point is put where it
  ;; looks like it belongs, then you choose - Move (take it), Keep
  ;; (put it back exactly where you drew it) or Pick your own spot.
  ;; Returns (original final how) when the point was looked at, where
  ;; how is 'auto / 'user / 'kept; nil when the point was already fine.
  (setq ed (entget ent)
        pt (cdr (assoc gcode ed)))
  (if pt
    (progn
      (setq near (cchk:nearest-curve pt nil cands))
      (if (and near (> (caddr near) *cchk-tol*))
        (progn
          (setq sugg (cadr near))
          ;; show the suggestion in place, but keep the original spot
          ;; marked so both are on screen while the question is asked
          (entmod (subst (cons gcode sugg) (assoc gcode ed) ed))
          (entupd ent)
          (princ (strcat "\n  " label " is not on any object - nearest one is "
                         (rtos (caddr near) 2 4) " away."))
          (setq ans (cchk:confirm-move label pt sugg))
          (cond
            ((eq ans 'move)
             (setq final sugg
                   how   'auto)
             (princ (strcat "\n  " label " MOVED onto the nearest object, "
                            (cchk:ptstr final) ".")))
            ((eq ans 'keep)
             (setq ed    (entget ent)
                   final pt
                   how   'kept)
             (entmod (subst (cons gcode pt) (assoc gcode ed) ed))
             (entupd ent)
             (princ (strcat "\n  " label " KEPT where you drew it, "
                            (cchk:ptstr final) " - nothing changed.")))
            (t
             (setq final (trans ans 1 0)
                   how   'user
                   ed    (entget ent))
             (entmod (subst (cons gcode final) (assoc gcode ed) ed))
             (entupd ent)
             (princ (strcat "\n  " label " moved to the spot you picked, "
                            (cchk:ptstr final) "."))))
          (redraw)
          (list pt final how))))))

(defun cchk:review-dim (ent cands num total / ed dtype h sty p13 p14 r1 r2
                                              looked moved kept ok note meas assocnote)
  ;; interactive review of one dimension.
  ;; Returns (handle ok-flag report-note moved-point-count measurement).
  (setq ed    (entget ent)
        h     (cdr (assoc 5 ed))
        sty   (cchk:dim-style ent)
        dtype (logand 7 (cdr (assoc 70 ed))))
  (cchk:zoom-ent ent)
  (redraw ent 3)
  (princ (strcat "\n\nDimension " (itoa num) " of " (itoa total)
                 " (handle " h
                 (if (= sty "") "" (strcat ", style " sty))
                 ")"))
  (if (member dtype '(0 1))                   ; rotated/linear or aligned
    (progn
      (if (cchk:dim-assoc-p ent)
        (princ "\n  Note: this dimension is object-associative - a moved point may re-anchor on its own."))
      (setq p13 (cdr (assoc 13 ed))           ; the two dimmed points
            p14 (cdr (assoc 14 ed))
            r1  (cchk:audit-dim-point ent 13 "dimension point 1" cands)
            r2  (cchk:audit-dim-point ent 14 "dimension point 2" cands))))
  (setq looked (append (if r1 (list r1)) (if r2 (list r2)))
        moved  (vl-remove-if '(lambda (x) (eq (caddr x) 'kept)) looked)
        kept   (vl-remove-if-not '(lambda (x) (eq (caddr x) 'kept)) looked))
  ;; only when something actually moved is there an old position worth
  ;; drawing a construction line through
  (if moved (cchk:make-xline p13 p14))        ; through the ORIGINAL points
  (if (and moved (cchk:dim-assoc-p ent))
    (setq assocnote " (ASSOCIATIVE - verify the moved point holds)"))
  (setq meas (cchk:dim-meas ent))             ; after any point moves
  (if meas (princ (strcat "\n  Measures " meas ".")))
  (redraw ent 3)
  (setq ok (cal:ask-yn-nav "\n  Is this dimension correct?"))
  (redraw ent 4)
  (redraw)
  (if (member ok '(back skip))
    (list h ok nil (length moved) meas)       ; navigation: caller handles it
    (progn
      (setq ok (eq ok 'yes))
      (setq note (strcat
                   (if ok "OK" "FLAGGED to fix (red)")
                   (if moved
                     (strcat " - " (itoa (length moved))
                             " point(s) moved onto the nearest object")
                     "")
                   (if kept
                     (strcat " - " (itoa (length kept))
                             " point(s) kept where you drew them")
                     "")
                   (if assocnote assocnote "")))
      (if (not ok) (cchk:set-color ent *cchk-flag-color*))
      (list h ok note (length moved) meas))))

;; --- arc review ----------------------------------------------------

(defun cchk:arc-end-target (ent which cands / p other near ends target)
  ;; where the attachment audit says this endpoint should go;
  ;; nil when the endpoint is already fine (or nothing to attach to)
  (setq p     (if (eq which 'start)
                (vlax-curve-getStartPoint ent)
                (vlax-curve-getEndPoint ent))
        other (if (eq which 'start)
                (vlax-curve-getEndPoint ent)
                (vlax-curve-getStartPoint ent))
        near  (cchk:nearest-curve p ent cands))
  (cond
    ((null near) nil)                         ; nothing to attach to at all
    ((<= (caddr near) *cchk-tol*)             ; endpoint sits on an object...
     (setq ends (cchk:curve-ends (car near)))
     ;; never snap onto the arc's own other endpoint
     (setq ends (vl-remove-if '(lambda (q) (< (distance q other) 1e-8)) ends))
     (cond
       ((null ends) nil)                      ; closed curve: no ends to demand
       ((vl-some '(lambda (q) (<= (distance p q) *cchk-tol*)) ends)
        nil)                                  ; ...and at one of its ends: OK
       (t (cchk:closest-of p ends))))         ; ...but mid-object: closest end
    (t                                        ; floating: closest end anywhere,
     (setq target (cchk:nearest-end p ent cands))
     (if (or (null target) (< (distance target other) 1e-8))
       (cadr near)                            ; else closest point on closest object
       target))))

(defun cchk:arc-state (ent / ed)
  ;; the groups that define an arc's shape, for an exact put-it-back
  (setq ed (entget ent))
  (list (assoc 10 ed) (assoc 40 ed) (assoc 50 ed) (assoc 51 ed)))

(defun cchk:arc-restore (ent st / ed g)
  ;; restore a saved shape exactly, rather than re-fitting back to it
  (setq ed (entget ent))
  (foreach g st (setq ed (subst g (assoc (car g) ed) ed)))
  (entmod ed)
  (entupd ent))

(defun cchk:review-arc-end (ent which label cands / p target st ans final how)
  ;; audits one arc endpoint: a detached end is snapped where it looks
  ;; like it belongs, then you choose - Move (take it), Keep (put the
  ;; arc back exactly as drawn) or Pick your own spot.
  ;; Returns (original final how) when the end was looked at, where how
  ;; is 'auto / 'user / 'kept; nil when the end was already fine.
  (setq p      (if (eq which 'start)
                 (vlax-curve-getStartPoint ent)
                 (vlax-curve-getEndPoint ent))
        target (cchk:arc-end-target ent which cands)
        st     (cchk:arc-state ent))
  (cond
    (target
     (if (cchk:move-arc-end ent which target)
       (progn
         (princ (strcat "\n  " label " is not attached to an object end - nearest is "
                        (rtos (distance p target) 2 4) " away."))
         (setq ans (cchk:confirm-move label p target))
         (cond
           ((eq ans 'move)
            (setq final target
                  how   'auto)
            (princ (strcat "\n  " label " SNAPPED to the object end, "
                           (cchk:ptstr final) ".")))
           ((eq ans 'keep)
            (cchk:arc-restore ent st)
            (setq final p
                  how   'kept)
            (princ (strcat "\n  " label " KEPT where you drew it, "
                           (cchk:ptstr final) " - the arc is unchanged.")))
           (t
            (setq ans (trans ans 1 0))
            (if (cchk:move-arc-end ent which ans)
              (progn
                (setq final ans
                      how   'user)
                (princ (strcat "\n  " label " moved to the spot you picked, "
                               (cchk:ptstr final) ".")))
              (progn
                (setq final target
                      how   'auto)
                (princ "\n  Could not re-fit the arc through that spot (collinear?); left it on the object end.")))))
         (redraw)
         (list p final how))
       (progn
         (princ (strcat "\n  " label " should attach at " (cchk:ptstr target)
                        " but the arc could not be re-fitted (points collinear?)."))
         nil)))
    (*cchk-ask-all-arc-ends*                  ; optional: confirm attached ends too
     (setq ans (cchk:confirm-move label p p))
     (redraw)
     (if (member ans '(move keep))
       nil
       (progn
         (setq ans (trans ans 1 0))
         (if (cchk:move-arc-end ent which ans)
           (list p ans 'user)
           (progn
             (princ "\n  Could not re-fit the arc through that spot (collinear?); unchanged.")
             nil)))))
    (t nil)))

(defun cchk:review-arc (ent cands num total / ed h planar r1 r2 looked moved kept note)
  ;; interactive review of one arc's endpoints.
  ;; Returns (handle untouched-flag report-note moved-point-count).
  (setq ed     (entget ent)
        h      (cdr (assoc 5 ed))
        planar (cchk:planar-arc-p ed))
  (cchk:zoom-ent ent)
  (redraw ent 3)
  (princ (strcat "\n\nArc " (itoa num) " of " (itoa total)
                 " (handle " h ")"))
  (if planar
    (setq r1 (cchk:review-arc-end ent 'start "arc start point" cands)
          r2 (cchk:review-arc-end ent 'end   "arc end point"   cands))
    (princ "\n  Arc is not in the world XY plane - endpoint audit skipped."))
  (redraw ent 4)
  (redraw)
  (setq looked (append (if r1 (list r1)) (if r2 (list r2)))
        moved  (vl-remove-if '(lambda (x) (eq (caddr x) 'kept)) looked)
        kept   (vl-remove-if-not '(lambda (x) (eq (caddr x) 'kept)) looked))
  (if moved (cchk:set-color ent *cchk-arc-color*))
  (setq note (cond
               ((not planar) "not in world XY plane - skipped")
               ((and moved kept)
                (strcat (itoa (length moved)) " endpoint(s) moved (magenta), "
                        (itoa (length kept)) " kept where you drew them"))
               (moved (strcat (itoa (length moved))
                              " endpoint(s) moved (magenta)"))
               (kept (strcat (itoa (length kept))
                             " endpoint(s) kept where you drew them"))
               (t "endpoints OK")))
  (list h (null moved) note (length moved)))

;; --- overlapping line review ---------------------------------------

(defun cchk:review-olap (la lb num total / info ea eb h1 h2 lay1 lay2 label
                                           ans mergeable kinds)
  ;; interactive review of one overlapping segment pair.
  ;; Returns nil when the pair no longer overlaps (an earlier merge
  ;; absorbed it); otherwise (label report-note action ents...) where
  ;; action is merged / flagged / left and ents keep their cyan.
  (setq ea (cchk:seg-ent la)
        eb (cchk:seg-ent lb))
  (if (and (entget ea) (entget eb) (setq info (cchk:overlap-info la lb)))
    (progn
      (setq h1        (cdr (assoc 5 (entget ea)))
            h2        (cdr (assoc 5 (entget eb)))
            lay1      (cdr (assoc 8 (entget ea)))
            lay2      (cdr (assoc 8 (entget eb)))
            mergeable (and (cchk:whole-line-p la)
                           (cchk:whole-line-p lb)
                           (= (strcase lay1) (strcase lay2)))
            kinds     (if (and (cchk:whole-line-p la) (cchk:whole-line-p lb))
                        "lines"
                        "segments")
            label     (strcat h1 "+" h2 " (overlap " (rtos (caddr info)) ")"))
      (cchk:zoom-2ents ea eb)
      (redraw ea 3)
      (redraw eb 3)
      (cchk:mark-point (car info))
      (cchk:mark-point (cadr info))
      (princ (strcat "\n\nOverlap " (itoa num) " of " (itoa total)
                     ": " kinds " " h1 " + " h2
                     " run on top of each other for " (rtos (caddr info)) "."))
      (if mergeable
        (progn
          (initget "Merge Flag Leave")
          (setq ans (getkword
                      "\n  Merge into one line, Flag to fix, or Leave as is? [Merge/Flag/Leave] <Merge>: "))
          (if (null ans) (setq ans "Merge")))
        (progn
          (princ (if (= (strcase lay1) (strcase lay2))
                   "\n  (Polyline edge - cannot be merged automatically.)"
                   (strcat "\n  (Different layers: " lay1 " / " lay2
                           " - cannot be merged automatically.)")))
          (initget "Flag Leave")
          (setq ans (getkword
                      "\n  Flag to fix, or Leave as is? [Flag/Leave] <Flag>: "))
          (if (null ans) (setq ans "Flag"))))
      (redraw ea 4)
      (redraw eb 4)
      (redraw)
      (cond
        ((= ans "Merge")
         (cchk:merge-lines la lb info)
         (cchk:set-color ea *cchk-olap-color*)
         (princ "\n  Merged into one line (cyan).")
         (list label "merged into one line (cyan)" 'merged ea))
        ((= ans "Flag")
         (cchk:set-color ea *cchk-olap-color*)
         (cchk:set-color eb *cchk-olap-color*)
         (princ "\n  Flagged to fix (cyan).")
         (list label
               (if (cchk:whole-line-p la)
                 (if (= (strcase lay1) (strcase lay2))
                   "flagged to fix (cyan)"
                   "different layers - flagged to fix (cyan)")
                 "polyline edge - flagged to fix (cyan)")
               'flagged ea eb))
        (t
         (princ "\n  Left as drawn.")
         (list label "left as drawn" 'left))))))


;; --- pad geometry (ported from PADDLE.lsp v1.2) ---------------------
;; Keep in step with PADDLE whenever its pad rules change.
;; Bulge-aware outline handling and the concave-feature hunt, used to
;; measure the pool outline and suggest 36" pads along it. Accepts a
;; closed LWPOLYLINE / 2D POLYLINE or the same shape exploded into
;; loose LINEs and ARCs - touching segments (ends within
;; *cchk-chain-fuzz*) are chained back into closed loops.

(defun cchk:pv-dir (a) (list (cos a) (sin a))) ; unit vector at angle a
(defun cchk:pv-arcpt (cen r ang) (cal:v+ cen (cal:v* (cchk:pv-dir ang) r)))
(defun cchk:pv-cheb (v) (max (abs (car v)) (abs (cadr v)))) ; Chebyshev norm

;; Segment data for vertex A -> B with bulge b (b /= 0):
;; returns (theta radius center start-tangent end-tangent)
;; theta = signed included angle (CCW positive), tangents are angles.
(defun cchk:pv-arcdata (a b blg / theta chord r phi ts cen)
  (setq theta (* 4.0 (atan blg))
        chord (distance a b)
        r     (/ chord (* 2.0 (sin (/ (abs theta) 2.0))))
        phi   (angle a b)
        ts    (- phi (/ theta 2.0))
        cen   (cal:v+ a (cal:v* (cchk:pv-dir (+ ts (if (> blg 0.0) (/ pi 2.0) (/ pi -2.0)))) r)))
  (list theta r cen ts (+ phi (/ theta 2.0))))

;; Signed area of a closed vertex list (shoelace + circular segments).
;; vts = list of (x y bulge), bulge belongs to the segment leaving it.
(defun cchk:pv-area (vts / n i a b blg area theta r seg)
  (setq n (length vts) i 0 area 0.0)
  (repeat n
    (setq a   (nth i vts)
          b   (nth (rem (1+ i) n) vts)
          blg (caddr a))
    (setq area (+ area (* 0.5 (- (* (car a) (cadr b)) (* (car b) (cadr a))))))
    (if (/= blg 0.0)
        (progn
          (setq seg   (cchk:pv-arcdata a b blg)
                theta (abs (car seg))
                r     (cadr seg))
          (setq area (+ area (* (if (> blg 0.0) 1.0 -1.0)
                                0.5 r r (- theta (sin theta)))))))
    (setq i (1+ i)))
  area)

;; Next pad along an arc: starting from arc-parameter CUR (previous
;; pad center PREV), find the parameter where the pad center is
;; exactly PADSIZE away from PREV in Chebyshev distance -- axis-
;; aligned pads of that size then touch edge-to-edge without ever
;; overlapping. Returns (parameter center), or nil when the rest of
;; the arc is too short for another flush pad.
(defun cchk:pv-next-flush (cen r sa sgn cur sweep prev padsize
                           / ds d p hit lo hi mid)
  (setq ds (/ padsize r 8.0))                ; ~1/8 pad per probe step
  (if (> ds (/ sweep 4.0)) (setq ds (/ sweep 4.0)))
  (setq d cur hit nil)
  (while (and (not hit) (< d (- sweep 1e-9))) ; walk until pads separate
    (setq lo d
          d  (min sweep (+ d ds))
          p  (cchk:pv-arcpt cen r (+ sa (* sgn d))))
    (if (>= (cchk:pv-cheb (cal:v- p prev)) padsize)
        (setq hit T)))
  (if hit
      (progn ; tighten the crossing between lo and d by bisection
        (setq hi d)
        (repeat 45
          (setq mid (/ (+ lo hi) 2.0)
                p   (cchk:pv-arcpt cen r (+ sa (* sgn mid))))
          (if (>= (cchk:pv-cheb (cal:v- p prev)) padsize)
              (setq hi mid)
              (setq lo mid)))
        (list hi (cchk:pv-arcpt cen r (+ sa (* sgn hi)))))))

;; Pad centers for one concave arc: the first pad is centered on the
;; MIDDLE of the arc; further pads march outward toward both ends,
;; each exactly one pad-size on center from the last. Marching stops
;; when the leftover end of the arc is too short for another flush
;; pad - the extreme ends of the radius are allowed to stay uncovered.
(defun cchk:pv-arc-pads (cen r sa sgn sweep padsize
                         / mid amid pmid fwd bwd cur prev nxt)
  (setq mid  (/ sweep 2.0)
        amid (+ sa (* sgn mid))
        pmid (cchk:pv-arcpt cen r amid))
  ;; march from the middle toward the arc's end...
  (setq cur 0.0 prev pmid fwd nil)
  (while (setq nxt (cchk:pv-next-flush cen r amid sgn cur (- sweep mid) prev padsize))
    (setq cur (car nxt) prev (cadr nxt) fwd (cons prev fwd)))
  ;; ...and from the middle back toward the arc's start
  (setq cur 0.0 prev pmid bwd nil)
  (while (setq nxt (cchk:pv-next-flush cen r amid (- sgn) cur mid prev padsize))
    (setq cur (car nxt) prev (cadr nxt) bwd (cons prev bwd)))
  (append bwd (list pmid) (reverse fwd)))

;; Direction (unit vector) of travel at the START / END of segment a->b.
(defun cchk:pv-tan-start (a b blg)
  (if (= blg 0.0)
      (cal:unit (cal:v- b a))
      (cchk:pv-dir (cadddr (cchk:pv-arcdata a b blg)))))
(defun cchk:pv-tan-end (a b blg)
  (if (= blg 0.0)
      (cal:unit (cal:v- b a))
      (cchk:pv-dir (last (cchk:pv-arcdata a b blg)))))

;; LWPOLYLINE -> (closed-flag . vts)
(defun cchk:pv-lwverts (ent / ed out grp)
  (setq ed (entget ent))
  (foreach grp ed
    (cond
      ((= (car grp) 10)
       (setq out (cons (list (cadr grp) (caddr grp) 0.0) out)))
      ((= (car grp) 42)
       (if out (setq out (cons (list (caar out) (cadr (car out)) (cdr grp)) (cdr out)))))))
  (cons (= 1 (logand 1 (cdr (assoc 70 ed)))) (reverse out)))

;; heavy 2D POLYLINE -> (closed-flag . vts), nil for 3D/mesh plines
(defun cchk:pv-plverts (ent / ed flags e ved out p)
  (setq ed (entget ent) flags (cdr (assoc 70 ed)))
  (if (zerop (logand 112 flags)) ; skip 3D polylines / meshes / polyfaces
      (progn
        (setq e (entnext ent))
        (while (and e (= "VERTEX" (cdr (assoc 0 (setq ved (entget e))))))
          (if (zerop (logand 16 (cond ((cdr (assoc 70 ved))) (0)))) ; skip spline frame pts
              (progn
                (setq p (cdr (assoc 10 ved)))
                (setq out (cons (list (car p) (cadr p)
                                      (cond ((cdr (assoc 42 ved))) (0.0)))
                                out))))
          (setq e (entnext e)))
        (cons (= 1 (logand 1 flags)) (reverse out)))))

;; vertex list -> segments (p1 p2 bulge), wrapping when closed
(defun cchk:pv-vts->segs (closed vts / n i segs a b)
  (setq n (length vts) i 0)
  (repeat (if closed n (max 0 (1- n)))
    (setq a (nth i vts)
          b (nth (rem (1+ i) n) vts))
    (setq segs (cons (list (cal:2d a) (cal:2d b) (caddr a)) segs))
    (setq i (1+ i)))
  (reverse segs))

;; any supported entity -> list of bulge-aware segments
(defun cchk:pv-ent-segs (ent / ed typ cen r sa ea sweep cv)
  (setq ed (entget ent) typ (cdr (assoc 0 ed)))
  (cond
    ((= typ "LINE")
     (list (list (cal:2d (cdr (assoc 10 ed)))
                 (cal:2d (cdr (assoc 11 ed))) 0.0)))
    ((= typ "ARC")
     (setq cen   (cal:2d (cdr (assoc 10 ed)))
           r     (cdr (assoc 40 ed))
           sa    (cdr (assoc 50 ed))
           ea    (cdr (assoc 51 ed))
           sweep (- ea sa))
     (if (<= sweep 0.0) (setq sweep (+ sweep pi pi)))
     (list (list (cal:v+ cen (cal:v* (cchk:pv-dir sa) r))
                 (cal:v+ cen (cal:v* (cchk:pv-dir ea) r))
                 (/ (sin (/ sweep 4.0)) (cos (/ sweep 4.0)))))) ; tan(sweep/4)
    ((= typ "CIRCLE")
     ;; two flush half-circle arcs (east point -> west point -> east
     ;; point, both CCW) chain into the same closed loop a polyline
     ;; circle would, without any extra vertex-list plumbing
     (setq cen (cal:2d (cdr (assoc 10 ed)))
           r   (cdr (assoc 40 ed)))
     (list (list (cal:v+ cen (list r 0.0)) (cal:v+ cen (list (- r) 0.0)) 1.0)
           (list (cal:v+ cen (list (- r) 0.0)) (cal:v+ cen (list r 0.0)) 1.0)))
    ((= typ "LWPOLYLINE")
     (setq cv (cchk:pv-lwverts ent))
     (cchk:pv-vts->segs (car cv) (cdr cv)))
    ((= typ "POLYLINE")
     (setq cv (cchk:pv-plverts ent))
     (if cv (cchk:pv-vts->segs (car cv) (cdr cv))))))

;; Chains touching segments (ends within *cchk-chain-fuzz*) end-to-end.
;; Returns (loops . open-count); each loop is a vertex list (x y bulge).
(defun cchk:pv-chain (segs / loops nopen chain head tail done found rest s)
  (setq nopen 0)
  ;; drop degenerate slivers
  (setq segs (vl-remove-if
               '(lambda (s) (<= (distance (car s) (cadr s)) *cchk-chain-fuzz*))
               segs))
  (while segs
    (setq chain (list (car segs))
          head  (car (car segs))
          tail  (cadr (car segs))
          segs  (cdr segs)
          done  nil)
    (while (not done)
      (cond
        ;; loop closed back onto its start?
        ((and (> (length chain) 1) (<= (distance tail head) *cchk-chain-fuzz*))
         (setq loops (cons (mapcar '(lambda (s) (list (car (car s)) (cadr (car s)) (caddr s)))
                                   chain)
                           loops)
               done  T))
        (T ;; look for a segment continuing from the tail
         (setq found nil rest nil)
         (foreach s segs
           (if found
               (setq rest (cons s rest))
               (cond
                 ((<= (distance tail (car s)) *cchk-chain-fuzz*)
                  (setq found s))
                 ((<= (distance tail (cadr s)) *cchk-chain-fuzz*) ; reversed
                  (setq found (list (cadr s) (car s) (- (caddr s)))))
                 (T (setq rest (cons s rest))))))
         (if found
             (setq chain (append chain (list found))
                   tail  (cadr found)
                   segs  (reverse rest))
             (setq nopen (1+ nopen) done T)))))) ; dead end: open chain
  (cons (reverse loops) nopen))

;; Concave features of one closed loop: returns pads, each
;; (center rotation kind) with kind = "corner" / "arc". PADSIZE sets
;; the pad-grid pitch used to cover concave arcs.
(defun cchk:pv-features (vts padsize / s n i a b c blg pads din dout turn
                             seg theta r cen sa sgn sweep)
  (setq s (if (< (cchk:pv-area vts) 0.0) -1 1) ; -1 = clockwise
        n (length vts)
        i 0)
  (repeat n
    (setq a   (nth i vts)                     ; segment i : a -> b
          b   (nth (rem (1+ i) n) vts)
          c   (nth (rem (+ i (1- n)) n) vts)  ; previous vertex
          blg (caddr a))
    ;; --- concave vertex (inside corner) at a, between seg i-1 and i ---
    (setq din  (cchk:pv-tan-end (cal:2d c) (cal:2d a) (caddr c))
          dout (cchk:pv-tan-start (cal:2d a) (cal:2d b) blg))
    (if (and din dout)
        (progn
          (setq turn (atan (cal:cross din dout) (cal:dot din dout)))
          (if (< (* s turn) (- *cchk-pad-angtol*)) ; turns away from interior
              (setq pads (cons (list (cal:2d a) (angle '(0.0 0.0) din) "corner")
                               pads)))))
    ;; --- concave arc segment with radius <= *cchk-pad-maxrad* ---
    (if (and (/= blg 0.0)
             (< (* s blg) 0.0)) ; bulges into the interior
        (progn
          (setq seg   (cchk:pv-arcdata (cal:2d a) (cal:2d b) blg)
                theta (car seg)
                r     (cadr seg)
                cen   (caddr seg))
          (if (and (<= r (+ *cchk-pad-maxrad* 1e-6))
                   (> (abs theta) *cchk-pad-angtol*)) ; total bend over the
                                     ; tolerance, else it's a semi-straight line
              (progn
                (setq sa    (angle cen (cal:2d a))
                      sgn   (if (> theta 0.0) 1.0 -1.0)
                      sweep (abs theta))
                (foreach ctr (cchk:pv-arc-pads cen r sa sgn sweep padsize)
                  (setq pads (cons (list ctr 0.0 "arc") pads)))))))
    (setq i (1+ i)))
  (reverse pads))

;; Keep suggested pads from colliding where features crowd together,
;; without ever pulling a pad off a sharp point (PADDLE v1.2). Corner
;; pads commit first, dead-center on their vertex -- they NEVER slide;
;; one that would overlap an earlier corner pad is dropped (in a notch
;; that tight, the neighbour carries the area). Arc pads then dodge
;; around everything committed: one that would overlap slides along
;; one axis to sit flush alongside instead (pads are PADSIZE x
;; PADSIZE, so flush = exactly PADSIZE on center). An arc pad whose
;; center is already inside a committed pad -- or that cannot find a
;; clear flush spot within half a pad of where it wanted to be -- is
;; dropped: its area is covered by the neighbours it kept hitting.
(defun cchk:pv-dodge (pads padsize / out ctr orig tries done hit d ax sgn)
  (foreach pad pads ; sharp points first: exact centers, never slid
    (if (= (caddr pad) "corner")
        (progn
          (setq hit nil)
          (foreach q out
            (if (and (not hit)
                     (< (cchk:pv-cheb (cal:v- (car pad) (car q)))
                        (- padsize 1e-6)))
                (setq hit T)))
          (if (not hit) (setq out (cons pad out))))))
  (foreach pad pads ; arc pads dodge around what's committed
    (if (/= (caddr pad) "corner")
        (progn
          (setq ctr   (car pad)
                orig  ctr
                tries 0
                done  nil)
          (while (not done)
            (setq hit nil)
            (foreach q out
              (if (and (not hit)
                       (< (cchk:pv-cheb (cal:v- ctr (car q)))
                          (- padsize 1e-6)))
                  (setq hit (car q))))
            (cond
              ((not hit) ; clear: commit it here
               (setq out  (cons (list ctr (cadr pad) (caddr pad)) out)
                     done T))
              ((or (< (cchk:pv-cheb (cal:v- ctr hit)) (/ padsize 2.0))
                   (> tries 6)
                   (> (cchk:pv-cheb (cal:v- ctr orig)) (/ padsize 2.0)))
               (setq done T)) ; already covered there, or stuck: drop it
              (T ; slide along the more-separated axis until flush
               (setq d   (cal:v- ctr hit)
                     ax  (if (>= (abs (car d)) (abs (cadr d))) 0 1)
                     sgn (if (< (nth ax d) 0.0) -1.0 1.0))
               (setq ctr (if (= ax 0)
                             (list (+ (car hit) (* sgn padsize)) (cadr ctr))
                             (list (car ctr) (+ (cadr hit) (* sgn padsize)))))
               (setq tries (1+ tries))))))))
  (reverse out))

;; --- cover rules ----------------------------------------------------

(defun cchk:bylayer-p (ent col / ed)
  ;; T when the entity's properties are all ByLayer; COL is its TRUE
  ;; colour (256 = ByLayer) - passed in because during a review the
  ;; entity may be wearing the grey or a flag colour
  (setq ed (entget ent))
  (and (= 256 col)
       (or (null (assoc 6 ed))
           (= "BYLAYER" (strcase (cdr (assoc 6 ed)))))
       (or (null (assoc 370 ed))
           (= -1 (cdr (assoc 370 ed))))))

(defun cchk:pool-ents (ss saved / i e ed out nskip)
  ;; pool-outline candidates: LINE/ARC/LWPOLYLINE/POLYLINE on the pool
  ;; layer with every property ByLayer, from the selection. SAVED (the
  ;; review's colour stash) supplies the true colour of anything
  ;; currently greyed out. Returns (ents . skipped); skipped sit on
  ;; the layer but carry explicit properties.
  (setq i 0 nskip 0)
  (repeat (sslength ss)
    (setq e  (ssname ss i)
          i  (1+ i)
          ed (entget e))
    (if (and ed
             (member (cdr (assoc 0 ed)) '("LINE" "ARC" "LWPOLYLINE" "POLYLINE" "CIRCLE"))
             (= (strcase (cdr (assoc 8 ed))) (strcase *cchk-pool-layer*)))
      (if (cchk:bylayer-p e (cond ((assoc e saved) (cdr (assoc e saved)))
                                  ((cchk:ent-color e))))
        (setq out (cons e out))
        (setq nskip (1+ nskip)))))
  (cons (reverse out) nskip))

(defun cchk:pool-loop (pents / segs e res loops best bestarea a l)
  ;; the pool outline: the largest closed loop chained from the
  ;; candidates' bulge-aware segments. Returns
  ;;   (best-loop open-chain-count other-closed-loop-count)
  ;; best-loop is nil when nothing closes back on itself; the other
  ;; two counts flag an ambiguous outline (a gap, or extra geometry
  ;; on the pool layer) even when a loop was still found.
  (foreach e pents
    (setq segs (append segs (cchk:pv-ent-segs e))))
  (setq res      (cchk:pv-chain segs)
        loops    (car res)
        bestarea 0.0)
  (foreach l loops
    (setq a (abs (cchk:pv-area l)))
    (if (> a bestarea) (setq bestarea a best l)))
  (list best (cdr res) (max 0 (1- (length loops)))))

(defun cchk:parse-nxn (s / lst i n num a res)
  ;; the first "NxN" written in the text ("5x5", "3 X 3") as a list
  ;; (n1 n2); nil when none
  (if s
    (progn
      (setq lst (vl-string->list (cchk:squash s))
            i   0
            n   (length lst))
      (while (and (< i n) (null res))
        (if (and (>= (nth i lst) 48) (<= (nth i lst) 57))
          (progn
            (setq num 0)
            (while (and (< i n) (>= (nth i lst) 48) (<= (nth i lst) 57))
              (setq num (+ (* 10 num) (- (nth i lst) 48))
                    i   (1+ i)))
            (setq a num)
            (if (and (< i n) (= (nth i lst) 88))       ; X
              (progn
                (setq i (1+ i))
                (if (and (< i n) (>= (nth i lst) 48) (<= (nth i lst) 57))
                  (progn
                    (setq num 0)
                    (while (and (< i n) (>= (nth i lst) 48) (<= (nth i lst) 57))
                      (setq num (+ (* 10 num) (- (nth i lst) 48))
                            i   (1+ i)))
                    (setq res (list a num)))))))
          (setq i (1+ i))))))
  res)

(defun cchk:nxn-str (sp)
  (strcat (itoa (car sp)) "x" (itoa (cadr sp))))

(defun cchk:na-p (s)
  ;; T when the text reads NA / N/A instead of a value
  (and s (wcmatch (strcat " " (cchk:norm-text s) " ")
                  "* NA *,* N A *")))

(defun cchk:ent-linetype (ent / ed lt ld)
  ;; the entity's effective linetype name (ByLayer resolved through
  ;; its layer); "CONTINUOUS" when nothing says otherwise
  (setq ed (entget ent)
        lt (cdr (assoc 6 ed)))
  (if (or (null lt) (= "BYLAYER" (strcase lt)))
    (progn
      (setq ld (tblsearch "LAYER" (cdr (assoc 8 ed))))
      (setq lt (if ld (cdr (assoc 6 ld))))))
  (if lt lt "CONTINUOUS"))

(defun cchk:dashed-poly-on (ss lay / i e ed found)
  ;; T when the selection holds a polyline on the given layer drawn
  ;; with a dashed linetype (*cchk-dashed-pat*)
  (setq i 0 lay (strcase lay))
  (repeat (sslength ss)
    (setq e  (ssname ss i)
          i  (1+ i)
          ed (entget e))
    (if (and (not found) ed
             (member (cdr (assoc 0 ed)) '("LWPOLYLINE" "POLYLINE"))
             (= lay (strcase (cdr (assoc 8 ed))))
             (wcmatch (strcase (cchk:ent-linetype e)) *cchk-dashed-pat*))
      (setq found T)))
  found)

(defun cchk:cover-nonpoly (ss lay / i ed n bad)
  ;; (total . non-polylines) over everything in the selection on the
  ;; given layer - the drawn cover must be polylines only
  (setq i 0 n 0 bad 0 lay (strcase lay))
  (repeat (sslength ss)
    (setq ed (entget (ssname ss i))
          i  (1+ i))
    (if (and ed (= lay (strcase (cdr (assoc 8 ed)))))
      (progn
        (setq n (1+ n))
        (if (not (member (cdr (assoc 0 ed)) '("LWPOLYLINE" "POLYLINE")))
          (setq bad (1+ bad))))))
  (cons n bad))

(defun cchk:sel-has-phrase (ss blks phrase / pat found i e ed g b)
  ;; T when the phrase appears in the highlighted area: on a TEXT or
  ;; MTEXT entity, or in a block's name, attributes or definition
  ;; (case, spacing and punctuation ignored). COVERCHECK's own report
  ;; is skipped so a rerun never reads its own words back.
  (setq pat (strcat "*" (cchk:squash phrase) "*")
        i   0)
  (repeat (sslength ss)
    (setq e  (ssname ss i)
          i  (1+ i)
          ed (entget e))
    (if (and (not found) ed
             (/= (strcase (cdr (assoc 8 ed))) (strcase *cchk-report-layer*))
             (member (cdr (assoc 0 ed)) '("TEXT" "MTEXT")))
      (foreach g ed
        (if (and (member (car g) '(1 3))
                 (wcmatch (cchk:squash (cdr g)) pat))
          (setq found T)))))
  (foreach b blks
    (if (and (not found) (cchk:ins-matches b phrase))
      (setq found T)))
  found)

(defun cchk:pad-centers (/ ss2 i e ed nm bb out)
  ;; centers (extents middle) of every pad already in the drawing: an
  ;; INSERT on the pads layer, or one whose (effective) name is a pad
  ;; block from *cchk-pad-blocks* - scoped to the current layout tab
  ;; so a pad sitting in another tab is never counted as covering this one
  (setq ss2 (ssget "_X" (list '(0 . "INSERT") (cons 410 (getvar "CTAB"))))
        i   0)
  (if ss2
    (repeat (sslength ss2)
      (setq e  (ssname ss2 i)
            i  (1+ i)
            ed (entget e))
      (if ed
        (progn
          (setq nm (cchk:squash (cchk:block-name e)))
          (if (or (= (strcase (cdr (assoc 8 ed))) (strcase *cchk-pads-layer*))
                  (vl-some '(lambda (p) (= nm (cchk:squash p))) *cchk-pad-blocks*))
            (progn
              (setq bb (cal:bbox-ent e))
              (if bb
                (setq out (cons (list (* 0.5 (+ (caar bb) (caadr bb)))
                                      (* 0.5 (+ (cadar bb) (cadadr bb))))
                                out)))))))))
  out)

(defun cchk:mark-pad (ctr)
  ;; circle a suggested pad spot on the construction layer, tagged so
  ;; a rerun or COVERCHECKRESCUE clears it
  (if (entmake (list '(0 . "CIRCLE")
                     '(100 . "AcDbEntity")
                     (cons 8 *cchk-constr-layer*)
                     '(100 . "AcDbCircle")
                     (cons 10 (list (car ctr) (cadr ctr) 0.0))
                     (cons 40 (/ *cchk-pad-size* 2.0))))
    (cchk:tag (entlast) "MARKER")))

(defun cchk:cover-audit (ss blks live saved / pres pents lres vts narc nlin v
                          sqft det ovraw ovval ovok ovna spraw spval spna
                          arcy wantov wantsp why dashpoly cstat covered note
                          spanote replblk replp replsum padskip pk lines s f
                          feats padctrs miss poolsum detsum padsum notesum)
  ;; every cover rule, run over the selection. Returns
  ;;   (header-summaries detail-lines)
  ;; as plain report strings - cchk:attn-p decides which turn red.
  ;; Nothing in the drawing is rewritten; disagreements are only
  ;; SUGGESTED against. LIVE marks a real COVERCHECK run: suggested
  ;; pad spots are circled on the construction layer, and with no
  ;; Replacement Disclaimer selected the replacement question is
  ;; asked at the prompt (COVERSCAN never asks).

  ;; the 'Pool Size Shown' note is checked first: besides its own
  ;; verdict (below) it also silences the replacement prompt and the
  ;; NA-overlap dashed-outline demand, both of which assume a drawn
  ;; cover exists to check against
  (setq note    (cchk:sel-has-phrase ss blks *cchk-pool-note*)
        spanote (cchk:sel-has-phrase ss blks *cchk-spa-note*))
  ;; both notes at once is a contradiction, not two separate all-clears
  (if (and note spanote)
    (setq lines (append lines (list
      (strcat "Pool/Spa size: BOTH '" *cchk-pool-note* "' and '" *cchk-spa-note*
              "' are in the selection - ONLY ONE SIZE CAN BE SHOWN")))))

  ;; --- pool outline & area (ByLayer geometry on the pool layer) ----
  (setq pres  (cchk:pool-ents ss saved)
        pents (car pres)
        lres  (if pents (cchk:pool-loop pents))
        vts   (car lres)
        narc  0
        nlin  0)
  (if (> (cdr pres) 0)
    (setq lines
          (append lines
                  (list (strcat "Pool: " (itoa (cdr pres)) " item(s) on layer '"
                                *cchk-pool-layer*
                                "' SKIPPED - properties are not ByLayer")))))
  (if (and lres (or (> (cadr lres) 0) (> (caddr lres) 0)))
    (setq lines (append lines (list
      (strcat "Pool: outline on layer '" *cchk-pool-layer* "' is AMBIGUOUS -"
              (if (> (cadr lres) 0)
                (strcat " " (itoa (cadr lres)) " open chain(s) (check for gaps)")
                "")
              (if (> (caddr lres) 0)
                (strcat (if (> (cadr lres) 0) ";" "") " " (itoa (caddr lres))
                        " other closed loop(s) ignored (largest used)")
                ""))))))
  (if vts
    (progn
      (foreach v vts
        (if (equal 0.0 (caddr v) 1e-12)
          (setq nlin (1+ nlin))
          (setq narc (1+ narc))))
      (setq sqft    (/ (abs (cchk:pv-area vts)) 144.0)
            arcy    (> narc nlin)
            poolsum (strcat (rtos sqft 2 1) " sq ft - outline "
                            (itoa nlin) " straight / " (itoa narc)
                            " arc segment(s), mostly "
                            (if arcy "arcs" "straights")
                            (if (and lres (or (> (cadr lres) 0) (> (caddr lres) 0)))
                              " (AMBIGUOUS - see detail)"
                              "")))
      ;; what the cover SHOULD be for this pool
      (cond
        (arcy
         (setq wantov 18.0
               wantsp '(3 3)
               why    "outline is mostly arcs"))
        ((< sqft *cchk-area-small*)
         (setq wantov 12.0
               wantsp '(5 5)
               why    (strcat "under " (rtos *cchk-area-small* 2 0) " sq ft")))
        ((<= sqft *cchk-area-large*)
         (setq wantov 15.0
               wantsp '(3 3)
               why    (strcat (rtos *cchk-area-small* 2 0) "-"
                              (rtos *cchk-area-large* 2 0) " sq ft")))
        (t
         (setq wantov 18.0
               wantsp '(3 3)
               why    (strcat "over " (rtos *cchk-area-large* 2 0) " sq ft")))))
    (setq poolsum (strcat "NOTHING closed and ByLayer found on layer '"
                          *cchk-pool-layer*
                          "' - area not measured (check for gaps)")))

  ;; --- Cover Details: Overlap & Spacing vs what the pool needs -----
  (setq det (car (vl-remove-if-not
                   '(lambda (b) (cchk:ins-matches b *cchk-details-block*))
                   blks)))
  (if (null det)
    (progn
      (setq detsum (strcat "block MISSING"
                           (if wantov
                             (strcat " - SUGGEST Overlap "
                                     (rtos wantov 2 0) "\", Spacing "
                                     (cchk:nxn-str wantsp) " (" why ")")
                             "")))
      (setq lines (append lines (list (strcat "Cover Details: " detsum)))))
    (progn
      ;; the OVERLAP value: attribute tag first, any text carrying
      ;; the word next
      (setq ovraw (cchk:ins-attrib det "OVERLAP"))
      (if (null ovraw)
        (foreach s (cchk:ins-texts det)
          (if (and (null ovraw) s (wcmatch (cchk:norm-text s) "*OVERLAP*"))
            (setq ovraw s))))
      (setq ovval    (if ovraw (cchk:parse-len ovraw))
            ovna     (cchk:na-p ovraw)
            ovok     (and ovval
                          (vl-some '(lambda (x) (equal x ovval 1e-6))
                                   *cchk-overlap-vals*))
            dashpoly (cchk:dashed-poly-on ss *cchk-pool-layer*))
      ;; the SPACING tag, same hunt
      (setq spraw (cchk:ins-attrib det "SPACING"))
      (if (null spraw)
        (foreach s (cchk:ins-texts det)
          (if (and (null spraw) s (wcmatch (cchk:norm-text s) "*SPACING*"))
            (setq spraw s))))
      (setq spval (cchk:parse-nxn spraw)
            spna  (cchk:na-p spraw))
      (setq lines (append lines (list
        (cond
          (ovna
           (strcat "Cover Details: Overlap is NA"
                   (if dashpoly
                     (strcat " but a DASHED polyline sits on layer '"
                             *cchk-pool-layer* "' - LOOK AT it")
                     (strcat " and layer '" *cchk-pool-layer*
                             "' has no dashed polyline - OK"))))
          ((null ovval)
           (strcat "Cover Details: Overlap is "
                   (if (and ovraw (/= ovraw ""))
                     (strcat "UNREADABLE ('" (cchk:clip ovraw 20) "')")
                     "BLANK")
                   " - "
                   (if wantov
                     (strcat "SUGGEST " (rtos wantov 2 0) "\" (" why ")")
                     "fill it in")))
          ((not ovok)
           (strcat "Cover Details: Overlap reads '" (cchk:clip ovraw 20)
                   "' - not 12\"/15\"/18\""
                   (if wantov
                     (strcat " - SUGGEST " (rtos wantov 2 0) "\" (" why ")")
                     "")))
          ((and wantov (not (equal ovval wantov 1e-6)))
           (strcat "Cover Details: Overlap " (rtos ovval 2 0)
                   "\" - SUGGEST " (rtos wantov 2 0) "\" (" why ")"))
          (wantov
           (strcat "Cover Details: Overlap " (rtos ovval 2 0)
                   "\" - matches (" why ")"))
          (t
           (strcat "Cover Details: Overlap " (rtos ovval 2 0)
                   "\" - no pool outline to check it against"))))))
      ;; any stated overlap demands a dashed cover outline on the pool
      ;; layer - UNLESS the 'Pool Size Shown' note is present, which
      ;; means no drawn cover is expected in the first place
      (if (and ovval (not note))
        (setq lines (append lines (list
          (if dashpoly
            (strcat "Cover Details: overlap set and a dashed polyline sits on layer '"
                    *cchk-pool-layer* "' - OK")
            (strcat "Cover Details: overlap set but NO DASHED polyline on layer '"
                    *cchk-pool-layer*
                    "' - draw the cover outline dashed"))))))
      (setq lines (append lines (list
        (cond
          (spna "Cover Details: Spacing is NA")
          ((null spval)
           (strcat "Cover Details: Spacing is "
                   (if (and spraw (/= spraw ""))
                     (strcat "UNREADABLE ('" (cchk:clip spraw 20) "')")
                     "BLANK")
                   " - "
                   (if wantsp
                     (strcat "SUGGEST " (cchk:nxn-str wantsp) " (" why ")")
                     "fill it in (NxN)")))
          ((/= (car spval) (cadr spval))
           (strcat "Cover Details: Spacing reads '" (cchk:clip spraw 20)
                   "' - not NxN"
                   (if wantsp
                     (strcat " - SUGGEST " (cchk:nxn-str wantsp) " (" why ")")
                     "")))
          ((and wantsp (not (equal spval wantsp)))
           (strcat "Cover Details: Spacing " (cchk:nxn-str spval)
                   " - SUGGEST " (cchk:nxn-str wantsp) " (" why ")"))
          (wantsp
           (strcat "Cover Details: Spacing " (cchk:nxn-str spval)
                   " - matches (" why ")"))
          (t
           (strcat "Cover Details: Spacing " (cchk:nxn-str spval)
                   " - no pool outline to check it against"))))))
      (setq detsum
            (strcat "Overlap "
                    (cond (ovna "NA")
                          (ovval (strcat (rtos ovval 2 0) "\""))
                          (t "BLANK"))
                    (if (and ovval (not ovok)) " (not 12/15/18)" "")
                    (if (and wantov (not ovna)
                             (or (null ovval)
                                 (not (equal ovval wantov 1e-6))))
                      (strcat " - SUGGEST " (rtos wantov 2 0) "\"")
                      "")
                    (if (and ovval (not dashpoly) (not note)) " - NO DASHED outline" "")
                    (if (and ovna dashpoly) " - dashed outline present, LOOK AT it" "")
                    "; Spacing "
                    (cond (spna "NA")
                          (spval (cchk:nxn-str spval))
                          (t "BLANK"))
                    (if (and wantsp (not spna)
                             (or (null spval)
                                 (not (equal spval wantsp))))
                      (strcat " - SUGGEST " (cchk:nxn-str wantsp))
                      "")))))

  ;; --- the cover layer: polylines only + 'Pool Size Shown' note ----
  ;; (note itself was already read at the top of the function)
  (setq cstat   (cchk:cover-nonpoly ss *cchk-cover-layer*)
        covered (> (car cstat) 0))
  (if (and covered (> (cdr cstat) 0))
    (setq lines (append lines (list
      (strcat "Cover: " (itoa (cdr cstat)) " of " (itoa (car cstat))
              " item(s) on layer '" *cchk-cover-layer*
              "' are NOT A POLYLINE - redraw the cover as a polyline")))))
  (setq notesum
        (cond
          ((and covered note)
           (strcat "cover drawn on layer '" *cchk-cover-layer*
                   "' AND the '" *cchk-pool-note*
                   "' note is in - SUGGEST taking the note off"))
          (covered
           (strcat "cover drawn on layer '" *cchk-cover-layer*
                   "', no '" *cchk-pool-note* "' note - OK"))
          (note
           (strcat "no cover on layer '" *cchk-cover-layer*
                   "', '" *cchk-pool-note* "' note is in - OK"))
          (t
           (strcat "no cover on layer '" *cchk-cover-layer*
                   "' and the '" *cchk-pool-note*
                   "' note is nowhere in the selection - SUGGEST adding it"))))
  (if (and covered (> (cdr cstat) 0))
    (setq notesum (strcat notesum "; " (itoa (cdr cstat))
                          " item(s) NOT A POLYLINE")))
  (if (and note spanote)
    (setq notesum (strcat notesum "; ONLY ONE SIZE CAN BE SHOWN ('"
                          *cchk-pool-note* "' & '" *cchk-spa-note*
                          "' both present)")))

  ;; --- Replacement Disclaimer --------------------------------------
  (setq replblk (car (vl-remove-if-not
                       '(lambda (b) (cchk:ins-matches b *cchk-repl-block*))
                       blks)))
  (cond
    (replblk
     (setq replp   T
           replsum (strcat "'" *cchk-repl-block*
                           "' block present - replacement drawing")))
    (note
     ;; a full pool size drawing is never a replacement - do not ask
     (setq replsum (strcat "not asked - '" *cchk-pool-note*
                           "' note is present (full pool size shown)")))
    (live
     (if (cal:ask-yn (strcat "\nNo '" *cchk-repl-block*
                              "' block is selected - is this drawing a replacement?")
                     "No")
       (progn
         (setq replp T)
         (setq pk (entsel (strcat "\nPick the '" *cchk-repl-block*
                                  "' block <it is not placed>: ")))
         (cond
           ((and pk
                 (= "INSERT" (cdr (assoc 0 (entget (car pk)))))
                 (cchk:ins-matches (car pk) *cchk-repl-block*))
            (cchk:zoom-ent (car pk))
            (setq replsum (strcat "replacement; '" *cchk-repl-block*
                                  "' found where you pointed (outside the selection)")))
           (pk
            (setq replsum (strcat "replacement, but what you picked is not it - '"
                                  *cchk-repl-block* "' block MISSING, add it")))
           (t
            (setq replsum (strcat "replacement but the '" *cchk-repl-block*
                                  "' block is MISSING - add it")))))
       (setq replsum (strcat "not a replacement - '" *cchk-repl-block*
                             "' not needed"))))
    (t
     (setq replsum (strcat "no '" *cchk-repl-block*
                           "' in the selection - run COVERCHECK to confirm"))))
  (setq lines (append lines (list (strcat "Replacement: " replsum))))

  ;; --- pads along the pool outline (PADDLE logic, 36" pads) --------
  ;; a replacement, an NA overlap or a drawn cover all mean the pads
  ;; are not sized from the pool outline - PADDLE is not used there
  (setq padskip
        (cond
          (replp   "this is a replacement")
          (ovna    "the Overlap is NA")
          (covered (strcat "a cover is drawn on layer '"
                           *cchk-cover-layer* "'"))))
  (if (and vts (not padskip))
    (progn
      (setq feats   (if (> (length vts) 1)
                      (cchk:pv-dodge (cchk:pv-features vts *cchk-pad-size*)
                                     *cchk-pad-size*))
            padctrs (cchk:pad-centers)
            miss    nil)
      (foreach f feats
        (if (not (vl-some
                   '(lambda (p) (<= (cchk:pv-cheb (cal:v- p (car f)))
                                    *cchk-pad-near*))
                   padctrs))
          (setq miss (cons f miss))))
      (setq miss (reverse miss))
      (setq padsum
            (cond
              ((null feats) "outline has no concave features - none needed")
              ((null miss)  (strcat (itoa (length feats))
                                    " spot(s) checked - every one has a pad"))
              (t (strcat (itoa (length miss)) " of " (itoa (length feats))
                         " 36\" spot(s) have no pad - SUGGEST adding"
                         (if live " (circled)" "")))))
      (setq lines (append lines (list (strcat "Pads: " padsum))))
      (foreach f miss
        (if live (cchk:mark-pad (car f)))
        (setq lines (append lines (list
          (strcat "Pad SUGGESTED at " (cchk:ptstr (car f))
                  (if (= (caddr f) "corner")
                    " (inside corner)"
                    " (along a concave arc)")))))))
    (progn
      (setq padsum (if padskip
                     (strcat "not suggested - " padskip)
                     "pool outline not found - not checked"))
      (setq lines (append lines (list (strcat "Pads: " padsum))))))

  (list (list (strcat "Pool: " poolsum)
              (strcat "Cover Details: " detsum)
              (strcat "Cover: " notesum)
              (strcat "Replacement: " replsum)
              (strcat "Pads: " padsum))
        lines))

;; --- command -------------------------------------------------------

(defun c:COVERCHECK ( / *error* oldecho vc vs undo-open ss i e et
                      cands dims arcs plns segs blks olaps e1 e2 pr
                      saved keep res n total lines
                      ndok ndflag ndmoved naok namoved nasnap
                      nomerged noflag noleft
                      rowtol sty l pair hdr cres
                      laylist locked relock lay
                      dlines skiprest
                      minx miny maxx maxy bb m dhdr right dimlay units datev carried cmv)

  (defun *error* (msg)
    ;; put the greys back (flagged/moved items keep their colour),
    ;; re-lock what we unlocked, clear markers, close the undo group
    (foreach pair saved
      (if (and (not (member (car pair) keep)) (entget (car pair)))
        (cchk:set-color (car pair) (cdr pair))))
    (foreach l relock (cchk:set-layer-lock l T))
    (redraw)
    (if undo-open
      (progn (setvar "CMDECHO" 0) (command "_.UNDO" "_End")))
    (if oldecho (setvar "CMDECHO" oldecho))
    (if (and msg (not (wcmatch (strcase msg) "*BREAK*,*CANCEL*,*QUIT*,*EXIT*")))
      (princ (strcat "\nCOVERCHECK error: " msg)))
    (princ))

  (prompt "\nHighlight the drawing to COVERCHECK: ")
  (setq ss (ssget))
  (cond
    ((null ss)
     (prompt "\nNothing selected - COVERCHECK cancelled."))
    (t
     (setq cands nil dims nil arcs nil blks nil segs nil
           saved nil keep nil lines nil i 0
           ndok 0 ndflag 0 ndmoved 0 naok 0 namoved 0 nasnap 0
           nomerged 0 noflag 0 noleft 0)
     (repeat (sslength ss)
       (setq e  (ssname ss i)
             i  (1+ i)
             et (cdr (assoc 0 (entget e))))
       (if (= et "DIMENSION") (setq dims (cons e dims)))
       (if (= et "ARC") (setq arcs (cons e arcs)))
       (if (member et '("LINE" "LWPOLYLINE" "POLYLINE"))
         (setq plns (cons e plns)))
       (if (= et "INSERT") (setq blks (cons e blks)))
       (if (member et *cchk-curve-types*) (setq cands (cons e cands))))
     (setq dims  (reverse dims)
           arcs  (reverse arcs)
           plns  (reverse plns)
           blks  (reverse blks)
           cands (reverse cands)
           ;; detection runs on segments, so a shape drawn as one
           ;; polyline counts like the same shape drawn as lines
           segs  (cchk:collect-segs plns))
     (cond
       ((and (null dims) (null arcs) (< (length segs) 2) (null blks))
        (prompt "\nSelection holds no dimensions, arcs, lines, or blocks to check - nothing to do."))
       (t
        (setq oldecho (getvar "CMDECHO"))
        (setvar "CMDECHO" 0)
        (setq vc (getvar "VIEWCTR")
              vs (getvar "VIEWSIZE"))
        (command "_.UNDO" "_Begin")
        (setq undo-open T)
        (cal:ensure-layer *cchk-constr-layer* *cchk-constr-color*)
        (cal:ensure-layer *cchk-report-layer* *cchk-report-color*)

        ;; a locked layer swallows every fix and recolour silently -
        ;; surface that up front and offer to unlock for the run
        (setq laylist nil relock nil i 0)
        (repeat (sslength ss)
          (setq lay (cdr (assoc 8 (entget (ssname ss i))))
                i   (1+ i))
          (if (and lay (not (member lay laylist)))
            (setq laylist (cons lay laylist))))
        (setq locked (vl-remove-if-not 'cchk:layer-locked-p laylist))
        (if locked
          (if (cal:ask-yn
                (strcat "\n" (itoa (length locked))
                        " locked layer(s) in the selection ("
                        (cchk:join locked ", ")
                        ") - COVERCHECK cannot recolour or fix anything on them. Unlock for this run?")
                "Yes")
            (progn
              (foreach l locked (cchk:set-layer-lock l nil))
              (setq relock locked)
              (princ "\n  Unlocked; they will be re-locked when the run ends."))
            (princ "\n  Locked layers stay locked - items on them are reported but left untouched.")))

        ;; a rerun replaces the previous run's report and markers
        (cchk:clear-old)

        ;; extents of the selection (report goes to the right of them)
        (setq i 0)
        (repeat (sslength ss)
          (setq e  (ssname ss i)
                i  (1+ i)
                bb (cal:bbox-ent e))
          (if bb
            (setq minx (if minx (min minx (caar bb)) (caar bb))
                  miny (if miny (min miny (cadar bb)) (cadar bb))
                  maxx (if maxx (max maxx (caadr bb)) (caadr bb))
                  maxy (if maxy (max maxy (cadadr bb)) (cadadr bb)))))

        ;; march order for the dimensions: style groups first
        ;; (*cchk-style-order*), then row by row, left to right
        (setq rowtol (if (and miny maxy (> (- maxy miny) 1e-8))
                       (* 0.05 (- maxy miny))
                       1.0))
        (setq dims (cchk:sort-dims dims rowtol))

        ;; grey out the whole selection so each item can take the
        ;; stage, stashing every original colour in xdata first so
        ;; COVERCHECKRESCUE can recover them even after a crash
        (setq i 0)
        (repeat (sslength ss)
          (setq e (ssname ss i)
                i (1+ i))
          (if (entget e)
            (progn
              (setq saved (cons (cons e (cchk:ent-color e)) saved))
              (cchk:stash-color e (cchk:ent-color e))
              (cchk:set-color e *cchk-grey-color*))))

        ;; --- dimensions, one at a time -----------------------------
        (if dims
          (princ (strcat "\n--- Reviewing " (itoa (length dims))
                         " dimension(s): Enter = correct, N = flag to fix, "
                         "B = back one, S = skip the rest ---")))
        ;; index-based so Back can step to the previous dimension and
        ;; Skip can leave the rest unreviewed without losing the report
        (setq n 0 total (length dims) dlines nil skiprest nil)
        (while (and (< n total) (not skiprest))
          (setq e   (nth n dims)
                res nil)
          (cchk:set-color e (cdr (assoc e saved)))       ; step into the light
          (setq res (cchk:review-dim e cands (1+ n) total))
          ;; points already moved count however the prompt was answered
          (setq ndmoved (+ ndmoved (cadddr res)))
          (cond
            ((eq (cadr res) 'skip)
             (cchk:set-color e *cchk-grey-color*)
             (setq skiprest T)
             (princ (strcat "\n  Skipping the remaining "
                            (itoa (- total n)) " dimension(s).")))
            ((eq (cadr res) 'back)
             ;; undo what the previous item recorded, then redo it
             (cchk:set-color e *cchk-grey-color*)
             (if (> n 0)
               (progn
                 (setq n  (1- n)
                       e1 (nth n dims))
                 (if (car dlines)                        ; roll back its tally
                   (progn
                     (if (cadr (car dlines))
                       (setq ndok (1- ndok))
                       (setq ndflag (1- ndflag)))
                     ;; A MOVED POINT STAYS MOVED.  Back re-asks the
                     ;; question; it does not put the point back, and
                     ;; its construction line is still standing.  So
                     ;; the move is CARRIED to the re-review, not
                     ;; un-counted -- subtracting it made the report
                     ;; claim "points adjusted: 0" over a drawing
                     ;; whose points really had been adjusted, and
                     ;; the rebuilt line lost its "moved" note with
                     ;; it (the second pass finds them attached and
                     ;; has nothing to report).
                     (if (> (caddr (car dlines)) 0)
                       (setq carried (cons (cons e1 (caddr (car dlines)))
                                           (vl-remove (assoc e1 carried)
                                                      carried))))
                     (setq dlines (cdr dlines))))
                 (setq keep (vl-remove e1 keep))
                 (cchk:set-color e1 *cchk-grey-color*)
                 (princ "\n  Stepping back one dimension."))
               (princ "\n  Already at the first dimension."))
             (setq n (1- n)))                            ; loop's 1+ re-enters it
            (t
             (if (cadr res)
               (progn (setq ndok (1+ ndok))
                      (cchk:set-color e *cchk-grey-color*))
               (progn (setq ndflag (1+ ndflag))
                      (setq keep (cons e keep))))
             (setq sty (cchk:dim-style e))
             ;; moves this dim collected on an earlier pass, before a
             ;; Back sent us round again -- they are real and belong
             ;; in both the line and the tally
             (setq cmv (cond ((cdr (assoc e carried))) (0)))
             (setq dlines (cons (list (strcat "Dim " (car res)
                                              (if (= sty "") "" (strcat " [" sty "]"))
                                              (if (nth 4 res)
                                                (strcat " = " (nth 4 res))
                                                "")
                                              ": " (caddr res)
                                              (if (> cmv 0)
                                                (strcat " - " (itoa cmv)
                                                        " point(s) moved before"
                                                        " you stepped back")
                                                ""))
                                      (cadr res)
                                      (+ (cadddr res) cmv))
                                dlines))))
          (setq n (1+ n)))
        (if skiprest
          (setq lines (cons (strcat "Dimensions: " (itoa (- total (length dlines)))
                                    " left UNREVIEWED (skipped by user)")
                            lines)))
        (foreach pair (reverse dlines)
          (setq lines (cons (car pair) lines)))

        ;; --- arcs, one endpoint at a time --------------------------
        (if arcs
          (princ (strcat "\n--- Reviewing " (itoa (length arcs))
                         " arc(s): checking endpoint attachment ---")))
        (setq n 0 total (length arcs))
        (foreach e arcs
          (setq n (1+ n))
          (cchk:set-color e (cdr (assoc e saved)))
          (setq res (cchk:review-arc e cands n total))
          (setq nasnap (+ nasnap (cadddr res)))
          (if (cadr res)
            (progn (setq naok (1+ naok))
                   (cchk:set-color e *cchk-grey-color*))
            (progn (setq namoved (1+ namoved))
                   (setq keep (cons e keep))))           ; moved: stays magenta
          (setq lines (cons (strcat "Arc " (car res) ": " (caddr res)) lines)))

        ;; --- overlapping lines, one pair at a time ------------------
        (setq olaps (cchk:find-overlaps segs))
        (if olaps
          (princ (strcat "\n--- Reviewing " (itoa (length olaps))
                         " overlapping line pair(s): Enter = merge, F = flag, L = leave ---")))
        (setq n 0 total (length olaps))
        (foreach pr olaps
          (setq n  (1+ n)
                e1 (cchk:seg-ent (car pr))
                e2 (cchk:seg-ent (cadr pr)))
          (cchk:stage e1 saved keep)
          (cchk:stage e2 saved keep)
          (setq res (cchk:review-olap (car pr) (cadr pr) n total))
          (cond
            ((null res)                       ; absorbed by an earlier merge
             (cchk:unstage e1 keep)
             (cchk:unstage e2 keep))
            ((eq (caddr res) 'left)
             (setq noleft (1+ noleft))
             (cchk:unstage e1 keep)
             (cchk:unstage e2 keep)
             (setq lines (cons (strcat "Lines " (car res) ": " (cadr res)) lines)))
            (t
             (if (eq (caddr res) 'merged)
               (setq nomerged (1+ nomerged))
               (setq noflag (1+ noflag)))
             (setq keep (append (cdddr res) keep))
             (setq lines (cons (strcat "Lines " (car res) ": " (cadr res)) lines)))))

        ;; --- restore colours (flagged/moved keep theirs) ------------
        ;; restored entities drop their rescue stash; flagged/moved
        ;; ones keep it so COVERCHECKRESCUE can clear the marks later
        (foreach pair saved
          (if (and (not (member (car pair) keep)) (entget (car pair)))
            (progn
              (cchk:set-color (car pair) (cdr pair))
              (cchk:unstash (car pair)))))
        (foreach l relock (cchk:set-layer-lock l T))
        (setq relock nil)

        ;; --- cover checks: pool area, Cover Details, note, pads -----
        (princ "\n--- Cover checks: pool outline & area, Cover Details, pads ---")
        (setq cres (cchk:cover-audit ss blks T saved))
        (foreach l (cadr cres)
          (princ (strcat "\n  " l))
          (setq lines (cons l lines)))

        ;; --- report on the right side, to scale with the drawing ----
        ;; the cover checks lead on the main sheet; the DIMCHECK-style
        ;; findings go in the DIMENSION AUDIT column beside it
        (setq dhdr
          (list
            (cons (strcat "Dimensions checked: " (itoa (length dims))
                          " (correct: " (itoa ndok)
                          ", flagged to fix: " (itoa ndflag)
                          ", points adjusted: " (itoa ndmoved) ")")
                  (> ndflag 0))
            (cons (strcat "Arcs checked: " (itoa (length arcs))
                          " (OK: " (itoa naok)
                          ", with endpoints moved: " (itoa namoved)
                          ", endpoints moved in total: " (itoa nasnap) ")")
                  (> namoved 0))
            (cons (strcat "Overlapping line pairs: " (itoa (length olaps))
                          (if olaps
                            (strcat " (merged: " (itoa nomerged)
                                    ", flagged: " (itoa noflag)
                                    ", left as drawn: " (itoa noleft) ")")
                            " - none found"))
                  (> noflag 0))))
        (setq dimlay (cchk:dimlayer-verdict dims)
              units  (cchk:audit-units ss)
              datev  (cchk:audit-date ss))
        (foreach l (caddr units)
          (princ (strcat "\n  " l))
          (setq lines (cons l lines)))
        (setq hdr (cons (cons (strcat "Dimension layer: " (car dimlay))
                              (cdr dimlay))
                        (cons (cons (strcat "Feet & inches: " (car units))
                                    (cadr units))
                              (cons (cons (strcat "Tech Title date: "
                                                  (car datev))
                                          (cdr datev))
                                    (mapcar '(lambda (s)
                                               (cons s (cchk:attn-p s)))
                                            (car cres))))))
        (setq right (cchk:write-report "COVERCHECK REPORT" nil hdr dhdr
                                       (reverse lines) nil
                                       minx miny maxx maxy))

        ;; --- show the drawing plus the report -----------------------
        (if minx
          (progn
            (setq m (* 0.05 (max (- maxx minx) (- maxy miny) 1.0)))
            (command "_.ZOOM" "_Window"
                     (trans (list (- minx m) (- miny m) 0.0) 0 1)
                     (trans (list (+ right m) (+ maxy m) 0.0) 0 1)))
          (command "_.ZOOM" "_Center" vc vs))

        (command "_.UNDO" "_End")
        (setq undo-open nil)
        (setvar "CMDECHO" oldecho)
        (princ (strcat "\n\n--- COVERCHECK complete ---"
                       "\nDimensions: " (itoa (length dims)) " checked, "
                       (itoa ndok) " correct, "
                       (itoa ndflag) " flagged to fix (red)"
                       (if (> ndmoved 0)
                         (strcat ", " (itoa ndmoved) " point(s) adjusted")
                         "")
                       "\nArcs: " (itoa (length arcs)) " checked, "
                       (itoa namoved) " with endpoint(s) moved ("
                       (itoa nasnap) " endpoint(s), magenta)"
                       "\nOverlapping lines: " (itoa (length olaps)) " pair(s) found"
                       (if olaps
                         (strcat ", " (itoa nomerged) " merged, "
                                 (itoa noflag) " flagged (cyan), "
                                 (itoa noleft) " left as drawn")
                         "")))
        (foreach l (car cres) (princ (strcat "\n" l)))
        (princ (strcat "\nReport placed on the right side of the drawing (layer "
                       *cchk-report-layer* ")."
                       (if (> ndmoved 0)
                         (strcat "\nConstruction lines through moved dimensions' original points are on layer "
                                 *cchk-constr-layer* ".")
                         "")
                       "\nOne UNDO reverts everything COVERCHECK changed (including the report)."))))))
  (princ))

;; --- COVERSCAN / LITECOVERSCAN: the read-only twins -------------------
;;  Run every audit, ask nothing, and change nothing in the drawing
;;  except writing the report. Use them as a quick pre-flight, or when
;;  you want the findings without touching a released sheet.
;;  LITECOVERSCAN skips the DIMCHECK-style pass entirely - no
;;  dimension, arc or overlap audit and no DIMENSION AUDIT column -
;;  for a drawing DIMCHECK already went over.

(defun c:COVERSCAN () (cchk:scan nil))

(defun c:LITECOVERSCAN () (cchk:scan T))

(defun cchk:scan (lite / *error* oldecho name ss i e et ed cands dims arcs
                       plns segs blks lines olaps pr bb bad
                       nd ndbad na nabad hdr dhdr l cres dimlay units datev
                       minx miny maxx maxy p13 p14 near s)

  (setq name (if lite "LITECOVERSCAN" "COVERSCAN"))
  (defun *error* (msg)
    (if oldecho (setvar "CMDECHO" oldecho))
    (if (and msg (not (wcmatch (strcase msg) "*BREAK*,*CANCEL*,*QUIT*,*EXIT*")))
      (princ (strcat "\n" name " error: " msg)))
    (princ))

  (prompt (strcat "\nHighlight the drawing to " name
                  " (Enter = whole drawing): "))
  (setq ss (ssget))
  (if (null ss) (setq ss (ssget "_X" (list (cons 410 (getvar "CTAB"))))))
  (cond
    ((null ss) (prompt "\nNothing to scan."))
    (t
     (setq oldecho (getvar "CMDECHO"))
     (setvar "CMDECHO" 0)
     ;; a rerun's leftover report/marker entities (e.g. suggested-pad
     ;; circles) must not pollute this scan's own attachment checks -
     ;; clear them before anything is collected, not after
     (cal:ensure-layer *cchk-report-layer* *cchk-report-color*)
     (cchk:clear-old)
     (setq i 0 nd 0 ndbad 0 na 0 nabad 0)
     (repeat (sslength ss)
       (setq e  (ssname ss i)
             i  (1+ i)
             et (cdr (assoc 0 (entget e))))
       (if (= et "DIMENSION") (setq dims (cons e dims)))
       (if (= et "ARC") (setq arcs (cons e arcs)))
       (if (member et '("LINE" "LWPOLYLINE" "POLYLINE")) (setq plns (cons e plns)))
       (if (= et "INSERT") (setq blks (cons e blks)))
       (if (member et *cchk-curve-types*) (setq cands (cons e cands)))
       (setq bb (cal:bbox-ent e))
       (if bb
         (setq minx (if minx (min minx (caar bb)) (caar bb))
               miny (if miny (min miny (cadar bb)) (cadar bb))
               maxx (if maxx (max maxx (caadr bb)) (caadr bb))
               maxy (if maxy (max maxy (cadadr bb)) (cadadr bb)))))
     (setq dims (reverse dims) arcs (reverse arcs)
           plns (reverse plns) blks (reverse blks) cands (reverse cands)
           segs (if lite nil (cchk:collect-segs plns)))

     ;; --- dimensions: report stray definition points, move nothing
     ;;     (a lite scan leaves the DIMCHECK-style pass out entirely)
     (foreach e (if lite
                  nil
                  (cchk:sort-dims dims (if (and miny maxy)
                                         (* 0.05 (- maxy miny)) 1.0)))
       (setq ed  (entget e)
             nd  (1+ nd)
             p13 (cdr (assoc 13 ed))
             p14 (cdr (assoc 14 ed))
             bad nil)
       (if (member (logand 7 (cdr (assoc 70 ed))) '(0 1))
         (foreach s (list (cons "point 1" p13) (cons "point 2" p14))
           (if (cdr s)
             (progn
               (setq near (cchk:nearest-curve (cdr s) nil cands))
               (if (and near (> (caddr near) *cchk-tol*))
                 (setq bad (append bad (list (strcat (car s) " off by "
                                                     (rtos (caddr near) 2 4))))))))))
       (if bad (setq ndbad (1+ ndbad)))
       (setq lines (cons (strcat "Dim " (cdr (assoc 5 ed))
                                 (if (= (cchk:dim-style e) "") ""
                                   (strcat " [" (cchk:dim-style e) "]"))
                                 (if (cchk:dim-meas e)
                                   (strcat " = " (cchk:dim-meas e)) "")
                                 ": "
                                 (if bad
                                   (strcat "NOT attached - " (cchk:join bad ", "))
                                   "OK")
                                 (if (cchk:dim-assoc-p e) " (associative)" ""))
                         lines)))

     ;; --- arcs: report unattached endpoints, move nothing
     (foreach e (if lite nil arcs)
       (setq na  (1+ na)
             bad nil)
       (if (cchk:planar-arc-p (entget e))
         (foreach s '(("start" . start) ("end" . end))
           (if (cchk:arc-end-target e (cdr s) cands)
             (setq bad (append bad (list (car s)))))))
       (if bad (setq nabad (1+ nabad)))
       (setq lines (cons (strcat "Arc " (cdr (assoc 5 (entget e))) ": "
                                 (if bad
                                   (strcat (cchk:join bad " & ")
                                           " NOT attached to an object end")
                                   "endpoints OK"))
                         lines)))

     ;; --- overlaps
     (setq olaps (if lite nil (cchk:find-overlaps segs)))
     (foreach pr olaps
       (setq lines (cons (strcat "Lines "
                                 (cdr (assoc 5 (entget (cchk:seg-ent (car pr)))))
                                 "+"
                                 (cdr (assoc 5 (entget (cchk:seg-ent (cadr pr)))))
                                 ": OVERLAP of "
                                 (rtos (caddr (cchk:overlap-info (car pr) (cadr pr))))
                                 " - flagged")
                         lines)))

     ;; --- cover checks (read-only - no pad markers are drawn) -------
     (princ "\n--- Cover checks: pool outline & area, Cover Details, pads ---")
     (setq cres (cchk:cover-audit ss blks nil nil))
     (foreach l (cadr cres)
       (princ (strcat "\n  " l))
       (setq lines (cons l lines)))

     ;; --- report (the only thing the scan writes) -------------------
     (setq dhdr (if lite
                  nil
                  (list
                    (cons (strcat "Dimensions scanned: " (itoa nd) " ("
                                  (itoa ndbad)
                                  " with a stray definition point)")
                          (> ndbad 0))
                    (cons (strcat "Arcs scanned: " (itoa na) " ("
                                  (itoa nabad) " with an unattached end)")
                          (> nabad 0))
                    (cons (strcat "Overlapping line pairs: "
                                  (itoa (length olaps)))
                          (> (length olaps) 0)))))
     (setq dimlay (cchk:dimlayer-verdict dims)
           units  (cchk:audit-units ss)
           datev  (cchk:audit-date ss))
     (foreach l (caddr units)
       (princ (strcat "\n  " l))
       (setq lines (cons l lines)))
     (setq hdr (cons (cons (strcat "Dimension layer: " (car dimlay))
                           (cdr dimlay))
                     (cons (cons (strcat "Feet & inches: " (car units))
                                 (cadr units))
                           (cons (cons (strcat "Tech Title date: "
                                               (car datev))
                                       (cdr datev))
                                 (mapcar '(lambda (s)
                                            (cons s (cchk:attn-p s)))
                                         (car cres))))))
     (cchk:write-report (strcat name " REPORT")
                        (strcat "Read-only scan - nothing in the drawing"
                                " was changed.  "
                                (if lite
                                  (strcat "Lite: dimensions, arcs and"
                                          " overlaps were not audited -"
                                          " run DIMCHECK or COVERSCAN"
                                          " for those.  ")
                                  ""))
                        hdr dhdr (reverse lines) lite
                        minx miny maxx maxy)
     (setvar "CMDECHO" oldecho)
     (princ (strcat "\n--- " name " complete (read-only) ---"
                    (if lite
                      "\nLite: dimensions, arcs and overlaps were not audited."
                      (strcat "\nDimensions: " (itoa nd) " scanned, "
                              (itoa ndbad) " with a stray point"
                              "\nArcs: " (itoa na) " scanned, "
                              (itoa nabad) " with an unattached end"
                              "\nOverlapping line pairs: "
                              (itoa (length olaps))))))
     (foreach l (car cres) (princ (strcat "\n" l)))
     (princ (strcat "\nReport written on layer " *cchk-report-layer*
                    "; nothing else was changed."))))
  (princ))


;; --- TUTORIALCOVERCHECK: a guided, hands-on introduction ------------
;; TUTORIALCOVERCHECK prints the full list of everything COVERCHECK /
;; COVERSCAN check, then - if you say yes - builds a small demo scene
;; in this drawing (tagged so TUTORIALCOVERCHECKCLEAN can remove it
;; again) so you can window-select it and run COVERCHECK for real and
;; watch every step happen exactly as it would on a real sheet: an
;; off-object dimension point, a detached arc end, a pair of
;; overlapping lines, a concave pool corner that needs a pad, and a
;; Cover Details block whose Overlap/Spacing were set wrong on purpose
;; so you see a real SUGGEST line. The Replacement Disclaimer block is
;; deliberately left out of the demo, so the live Yes/No + point-at-it
;; prompt fires for real too.

(defun cchk:tut-checklist ()
  (princ "\n\n=== What COVERCHECK / COVERSCAN check ===")
  (princ (strcat "\n(this file: " *cchk-version* ")"))
  (princ "\n\nDIMENSIONS - each linear/aligned dimension's two definition")
  (princ "\n  points are checked against nearby geometry; an off-object point")
  (princ "\n  is offered Move (snap it), Keep (leave it), or Pick (place it")
  (princ "\n  yourself). You then confirm the dimension itself is correct;")
  (princ "\n  No recolours it red.")
  (princ "\n\nARCS - each arc's two endpoints get the same Move/Keep/Pick")
  (princ "\n  audit against nearby geometry; a moved endpoint recolours the")
  (princ "\n  arc magenta.")
  (princ "\n\nOVERLAPPING LINES - collinear LINEs that run on top of each")
  (princ "\n  other are found and offered Merge (into one line, cyan), Flag")
  (princ "\n  (cyan, fix by hand), or Leave (intentional).")
  (princ (strcat "\n\nPOOL OUTLINE & AREA - everything on layer '" *cchk-pool-layer*
                 "' with fully"))
  (princ "\n  ByLayer properties (a closed polyline, a circle, or the same shape")
  (princ "\n  exploded into lines/arcs) is chained into the pool's outline; its")
  (princ "\n  area (sq ft) and straight/arc segment mix are reported. An")
  (princ "\n  outline with gaps or extra closed loops is flagged AMBIGUOUS.")
  (princ (strcat "\n\nCOVER DETAILS - the '" *cchk-details-block*
                 "' block's OVERLAP"))
  (princ "\n  (12\"/15\"/18\") and SPACING (NxN) values are checked against what")
  (princ "\n  the pool's shape and size call for; a disagreement, blank, or")
  (princ "\n  unreadable value is SUGGESTED against - never rewritten.")
  (princ (strcat "\n\nCOVER LAYER = POLYLINES - anything on layer '"
                 *cchk-cover-layer* "' that"))
  (princ "\n  isn't a polyline is called out.")
  (princ "\n\nOVERLAP NA <-> DASHED OUTLINE - an NA overlap means no")
  (princ (strcat "\n  dashed polyline may sit on layer '" *cchk-pool-layer*
                 "'; any stated"))
  (princ "\n  overlap demands one - unless a \"Pool Size Shown\" note is")
  (princ "\n  present, meaning no drawn cover is expected at all.")
  (princ (strcat "\n\n\"" *cchk-pool-note* "\" / \"" *cchk-spa-note* "\" - with"))
  (princ (strcat "\n  nothing on layer '" *cchk-cover-layer*
                 "', the pool note must be"))
  (princ "\n  somewhere in the selection; with a cover drawn, it must NOT be.")
  (princ "\n  Finding both the pool note AND the spa note together is an")
  (princ "\n  error - only one size can be shown.")
  (princ (strcat "\n\nREPLACEMENT DISCLAIMER - the '" *cchk-repl-block*
                 "' block should"))
  (princ "\n  be selected; if it isn't (and no pool-size note explains why")
  (princ "\n  not), COVERCHECK asks whether this is a replacement and, if")
  (princ "\n  so, asks you to point at the block elsewhere in the drawing.")
  (princ "\n\nPADS - the pool outline is run through PADDLE's concave-")
  (princ (strcat "\n  feature hunt at " (rtos *cchk-pad-size* 2 0)
                 "\": every inside corner or tight"))
  (princ "\n  concave arc with no pad already nearby is SUGGESTED and")
  (princ "\n  circled - unless this is a replacement, the Overlap is NA, or")
  (princ "\n  a cover is drawn, in which case pads are not sized from the")
  (princ "\n  outline at all.")
  (princ "\n\nEverything lands in one COVERCHECK REPORT (or COVERSCAN REPORT")
  (princ "\nfor a read-only pass) placed beside the drawing, with anything")
  (princ "\nneeding a second look shown in red.")
  (princ))

;; --- demo-scene builders (all tagged "TUTORIAL" for cleanup) --------

(defun cchk:tut-label (pt height str)
  (if (entmake (list '(0 . "TEXT") '(100 . "AcDbEntity")
                     (cons 8 *cchk-tut-layer*)
                     '(100 . "AcDbText")
                     (cons 10 pt) (cons 40 height) (cons 1 str)))
    (cchk:tag (entlast) "TUTORIAL")))

(defun cchk:tut-line (p1 p2 layer)
  (if (entmake (list '(0 . "LINE") '(100 . "AcDbEntity") (cons 8 layer)
                     '(100 . "AcDbLine") (cons 10 p1) (cons 11 p2)))
    (cchk:tag (entlast) "TUTORIAL")))

(defun cchk:tut-arc (cen r sa ea layer)
  (if (entmake (list '(0 . "ARC") '(100 . "AcDbEntity") (cons 8 layer)
                     '(100 . "AcDbCircle") (cons 10 cen) (cons 40 r)
                     (cons 50 sa) (cons 51 ea)))
    (cchk:tag (entlast) "TUTORIAL")))

(defun cchk:tut-poly (verts layer / dxf v)
  ;; VERTS a list of (x y) pairs; always closed
  (setq dxf (list '(0 . "LWPOLYLINE") '(100 . "AcDbEntity") (cons 8 layer)
                  '(100 . "AcDbPolyline") (cons 90 (length verts)) '(70 . 1)))
  (foreach v verts (setq dxf (append dxf (list (list 10 (car v) (cadr v))))))
  (if (entmake dxf) (cchk:tag (entlast) "TUTORIAL")))

;; the demo "Cover Details" block: a minimal block with OVERLAP and
;; SPACING attributes, built only when the drawing has no block by
;; that name yet (never redefines an existing real one)
(defun cchk:tut-details-block (name / h)
  (setq h 6.0)
  (entmake (list '(0 . "BLOCK") (cons 2 name) '(10 0.0 0.0 0.0) '(70 . 0)))
  (entmake (list '(0 . "ATTDEF") '(100 . "AcDbEntity") (cons 8 "0")
                 '(100 . "AcDbText") (cons 10 (list 0.0 0.0 0.0)) (cons 40 h)
                 (cons 1 "12\"") '(100 . "AcDbAttribute")
                 (cons 2 "OVERLAP") (cons 3 "Overlap: ") (cons 70 0)))
  (entmake (list '(0 . "ATTDEF") '(100 . "AcDbEntity") (cons 8 "0")
                 '(100 . "AcDbText") (cons 10 (list 0.0 (- h) 0.0)) (cons 40 h)
                 (cons 1 "5x5") '(100 . "AcDbAttribute")
                 (cons 2 "SPACING") (cons 3 "Spacing: ") (cons 70 0)))
  (entmake '((0 . "ENDBLK")))
  (tblsearch "BLOCK" name))

;; inserts a Cover Details demo instance with OVVAL/SPVAL as its
;; attribute answers; returns the new INSERT, or nil if it couldn't
;; be built (a stuck/odd command sequence is not silently ignored)
(defun cchk:tut-insert-details (pt ovval spval
                                 / oldattdia oldattreq oldfiledia pre new)
  (if (not (tblsearch "BLOCK" *cchk-details-block*))
    (cchk:tut-details-block *cchk-details-block*))
  (setq oldattdia  (getvar "ATTDIA")
        oldattreq  (getvar "ATTREQ")
        oldfiledia (getvar "FILEDIA"))
  (setvar "ATTDIA" 0) (setvar "ATTREQ" 1) (setvar "FILEDIA" 0)
  (setq pre (entlast))
  (vl-catch-all-apply
    '(lambda ()
       (command "_.-INSERT" *cchk-details-block* pt "1" "1" "0" ovval spval "")))
  (setvar "ATTDIA" oldattdia) (setvar "ATTREQ" oldattreq) (setvar "FILEDIA" oldfiledia)
  (setq new (if pre (entnext pre) (entnext)))
  (if (and new (entget new) (= "INSERT" (cdr (assoc 0 (entget new)))))
    (progn (cchk:tag new "TUTORIAL") new)))

;; the whole demo scene, anchored at BP (WCS, z=0). Each piece is
;; independent - one failing (e.g. no DASHED linetype available)
;; never stops the rest from being built.
(defun cchk:tut-build (bp / bx by oldfiledia oldosmode pre newdim detpt ins)
  (setq bx (car bp) by (cadr bp))
  (cal:ensure-layer *cchk-pool-layer* 7)
  (cal:ensure-layer *cchk-tut-layer* 5)

  ;; pool outline: an L-shape, ByLayer, exactly one concave (inside)
  ;; corner, area well under 1,200 sq ft (wants 12" overlap, 5x5)
  (cchk:tut-poly
    (list (list bx by) (list (+ bx 180.0) by)
          (list (+ bx 180.0) (+ by 72.0)) (list (+ bx 108.0) (+ by 72.0))
          (list (+ bx 108.0) (+ by 120.0)) (list bx (+ by 120.0)))
    *cchk-pool-layer*)
  (princ "\n  Built: pool outline (L-shape, one inside corner) on layer '")
  (princ *cchk-pool-layer*) (princ "'.")

  ;; a dashed cover outline on the same layer, so the NA/dashed check
  ;; has something to find (skips cleanly if DASHED can't be loaded)
  (setq oldfiledia (getvar "FILEDIA"))
  (setvar "FILEDIA" 0)
  (vl-catch-all-apply '(lambda () (command "_.-LINETYPE" "_Load" "DASHED" "acad.lin" "")))
  (setvar "FILEDIA" oldfiledia)
  (if (tblsearch "LTYPE" "DASHED")
    (progn
      (entmake (list '(0 . "LWPOLYLINE") '(100 . "AcDbEntity")
                     (cons 8 *cchk-pool-layer*) (cons 6 "DASHED")
                     '(100 . "AcDbPolyline") '(90 . 4) '(70 . 1)
                     (list 10 (+ bx 6.0) (+ by 6.0))
                     (list 10 (+ bx 174.0) (+ by 6.0))
                     (list 10 (+ bx 174.0) (+ by 66.0))
                     (list 10 (+ bx 6.0) (+ by 66.0))))
      (cchk:tag (entlast) "TUTORIAL")
      (princ "\n  Built: dashed cover outline on the pool layer."))
    (princ "\n  Skipped: could not load the DASHED linetype - the dashed-outline check has nothing to find in this demo."))

  ;; Cover Details block, Overlap/Spacing set WRONG on purpose (this
  ;; pool wants 12"/5x5; the block says 15"/3x3) so the report shows
  ;; a real SUGGEST line instead of a bland pass
  (setq detpt (list (+ bx 210.0) (+ by 60.0) 0.0))
  (if (tblsearch "BLOCK" *cchk-details-block*)
    (princ (strcat "\n  Skipped: a '" *cchk-details-block*
                   "' block already exists in this drawing - not redefining it."))
    (progn
      (setq ins (cchk:tut-insert-details detpt "15\"" "3x3"))
      (if ins
        (princ "\n  Built: 'Cover Details' block (Overlap/Spacing set wrong on purpose).")
        (princ "\n  Skipped: could not insert the 'Cover Details' demo block (-INSERT did not complete as expected)."))))

  ;; an off-object dimension point: point 1 sits 4" below the pool's
  ;; true bottom-left corner instead of on it
  (setq oldosmode (getvar "OSMODE"))
  (setvar "OSMODE" 0)
  (setq pre (entlast))
  (vl-catch-all-apply
    '(lambda ()
       (command "_.DIMLINEAR"
                (list bx (- by 4.0) 0.0)
                (list (+ bx 180.0) by 0.0)
                (list (+ bx 90.0) (- by 40.0) 0.0))))
  (setvar "OSMODE" oldosmode)
  (setq newdim (if pre (entnext pre) (entnext)))
  (if (and newdim (entget newdim) (= "DIMENSION" (cdr (assoc 0 (entget newdim)))))
    (progn (cchk:tag newdim "TUTORIAL")
           (princ "\n  Built: dimension with one point 4\" off the pool edge."))
    (princ "\n  Skipped: could not create the demo dimension (DIMLINEAR did not complete as expected)."))

  ;; a detached arc end: the arc's start point sits 3" from the
  ;; nearest line end instead of touching it
  (cchk:tut-arc (list (+ bx 220.0) (+ by 150.0) 0.0) 20.0 0.0 pi *cchk-tut-layer*)
  (cchk:tut-line (list (+ bx 240.0) (+ by 147.0)) (list (+ bx 280.0) (+ by 147.0)) *cchk-tut-layer*)
  (princ "\n  Built: arc with a detached end, 3\" from the nearest line.")

  ;; two overlapping lines
  (cchk:tut-line (list bx (+ by 250.0)) (list (+ bx 100.0) (+ by 250.0)) *cchk-tut-layer*)
  (cchk:tut-line (list (+ bx 60.0) (+ by 250.0)) (list (+ bx 160.0) (+ by 250.0)) *cchk-tut-layer*)
  (princ "\n  Built: two overlapping lines.")

  ;; callouts
  (cchk:tut-label (list bx (+ by 290.0) 0.0) 6.0
    "COVERCHECK TUTORIAL DEMO - window-select everything here, then type COVERCHECK (or COVERSCAN to preview).")
  (cchk:tut-label (list (+ bx 100.0) (+ by 78.0) 0.0) 4.0 "(1) inside corner -> pad SUGGESTED")
  (cchk:tut-label (list (+ bx 20.0) (- by 55.0) 0.0) 4.0 "(2) dimension point 4\" off the edge")
  (cchk:tut-label (list (+ bx 195.0) (+ by 168.0) 0.0) 4.0 "(3) arc end detached 3\"")
  (cchk:tut-label (list bx (+ by 258.0) 0.0) 4.0 "(4) overlapping lines")
  (cchk:tut-label (list (+ bx 195.0) (+ by 78.0) 0.0) 4.0 "(5) Cover Details set wrong on purpose")
  T)

(defun c:TUTORIALCOVERCHECK ( / *error* oldecho undo-open bp)
  (defun *error* (msg)
    (if undo-open (progn (setvar "CMDECHO" 0) (command "_.UNDO" "_End")))
    (if oldecho (setvar "CMDECHO" oldecho))
    (if (and msg (not (wcmatch (strcase msg) "*BREAK*,*CANCEL*,*QUIT*,*EXIT*")))
      (princ (strcat "\nTUTORIALCOVERCHECK error: " msg)))
    (princ))

  (cchk:tut-checklist)

  (if (cal:ask-yn "\nBuild a small demo scene in this drawing so you can watch it live?" "Yes")
    (progn
      (setq bp (getpoint "\nPick a base point for the demo, clear of your real geometry <0,0>: "))
      (if (null bp) (setq bp (list 0.0 0.0 0.0)))
      (setq oldecho (getvar "CMDECHO"))
      (setvar "CMDECHO" 0)
      (command "_.UNDO" "_Begin")
      (setq undo-open T)
      (princ "\n--- Building the demo scene ---")
      (cchk:tut-build bp)
      (command "_.UNDO" "_End")
      (setq undo-open nil)
      (setvar "CMDECHO" oldecho)
      (command "_.ZOOM" "_Window"
               (trans (list (- (car bp) 20.0) (- (cadr bp) 60.0) 0.0) 0 1)
               (trans (list (+ (car bp) 300.0) (+ (cadr bp) 310.0) 0.0) 0 1))
      (princ "\n\nDemo scene built. Window-select all of it and type COVERCHECK")
      (princ "\n(or COVERSCAN to preview read-only first) to watch every check")
      (princ "\nrun on real geometry, one step at a time.")
      (princ "\nWhen you're done, type TUTORIALCOVERCHECKCLEAN to erase the demo -")
      (princ "\nit only removes what the tutorial built (tagged), plus whatever")
      (princ "\nreport and markers COVERCHECK/COVERSCAN left behind on it.")))
  (princ))

(defun c:TUTORIALCOVERCHECKCLEAN ( / ss i e xd n)
  ;; erases everything TUTORIALCOVERCHECK built (tagged "TUTORIAL"),
  ;; then clears any COVERCHECK/COVERSCAN report and markers left on
  ;; it too, so a demo run leaves nothing behind
  (setq ss (ssget "_X" '((-3 ("COVERCHECK")))) n 0 i 0)
  (if ss
    (repeat (sslength ss)
      (setq e  (ssname ss i)
            i  (1+ i)
            xd (cchk:xd e))
      (if (= (cdr (assoc 1000 xd)) "TUTORIAL")
        (progn (entdel e) (setq n (1+ n))))))
  (cchk:clear-old)
  (if (> n 0)
    (princ (strcat "\nTUTORIALCOVERCHECKCLEAN: removed " (itoa n)
                   " demo item(s), plus any report/markers left on them."))
    (princ "\nTUTORIALCOVERCHECKCLEAN: nothing tagged TUTORIAL was found."))
  (princ))

(defun c:COVERCHECKVER ()
  (princ (strcat "\nThis file's COVERCHECK / COVERSCAN: " *cchk-version*))
  (princ "\n(covercheck.lsp and its dated covercheck_MMDDYY_REV##.lsp twin should always match this.)")
  (princ))

;; the pre-standard name, kept as an alias - STANDARDS section 5 names
;; the version reporter TOOLNAMEVER, and muscle memory keeps the old one
(defun c:COVERCHECKVERSION () (c:COVERCHECKVER))

(princ (strcat "\ncovercheck.lsp loaded (" *cchk-version* ") - COVERCHECK reviews dims, arcs & the cover rules,"))
(princ "\n  COVERSCAN reports everything read-only, COVERCHECKRESCUE undoes COVERCHECK's marks.")
(princ "\n  TUTORIALCOVERCHECK walks a new user through it; COVERCHECKVER prints this file's version.")
(princ)


;;; ======================================================================
;;; >>> CUSTBLOCK.lsp
;;; ======================================================================

;;; ======================================================================
;;; CUSTBLOCK.lsp  --  draw a custom block in pictorial view from its
;;;                    length, width and height, dimensioned
;;; ----------------------------------------------------------------------
;;; For AutoCAD 2018 and later (plain AutoLISP, no external libraries).
;;;
;;; Commands:  CUSTBLOCK      ask L/W/H and draw the block
;;;            CUSTBLOCKVER   print the loaded version
;;;
;;; SHARED BUILD: requires CALOFIN-LIB.lsp (load via CALOFIN-LOADER.lsp).
;;; Generic helpers live there under cal: - see STANDARDS.md.
;;;
;;;  Three questions and a base point, and the block is on the sheet:
;;;
;;;    1. Block length   -- the long axis, drawn receding back-right
;;;    2. Block width    -- across the front face
;;;    3. Block height   -- up the front face
;;;    4. Insertion base point (Enter = 0,0) -- the FRONT BOTTOM LEFT
;;;       corner of the block
;;;
;;;  What is drawn (the 84 x 36 x 4 block of the sample sheet, if those
;;;  are the three answers):
;;;
;;;      * nine lines on layer "COVER" -- the front face, the top face
;;;        and the right-hand face of the box.  The three hidden edges
;;;        (the bottom-left receding edge, the bottom and the left edge
;;;        of the back face) are NOT drawn, which is what makes it read
;;;        as a solid block rather than a wire cage.
;;;      * the length receding at 45 degrees, at TRUE length -- it is a
;;;        pictorial, not an isometric projection, so the dimension on
;;;        that edge reads the number that was typed.
;;;      * three dimensions on layer "DIMENSION" in the "STANDARD
;;;        INCHES" style: the length aligned along the top-left
;;;        receding edge, the height up the left of the front face, the
;;;        width along under it.  Text centred, dimension lines pushed
;;;        cbk:*dimoff* clear of the block.
;;;
;;;  The whole run is one undo group: a single U takes the block and
;;;  its dimensions away together.
;;;
;;;  Usage
;;;    Command: CUSTBLOCK
;;;    Command: CUSTBLOCKVER     prints the version
;;;
;;;  Tunables (setq them after loading if a drawing needs different
;;;  names, e.g. in a startup file):
;;;    cbk:*layer*     layer the block lines go on   ("COVER")
;;;    cbk:*laycolor*  colour that layer is created with, when the
;;;                    drawing has no such layer yet (7)
;;;    cbk:*dimlayer*  layer the dimensions go on    ("DIMENSION")
;;;    cbk:*dimcolor*  colour IT is created with     (141)
;;;    cbk:*style*     dimension style to use        ("STANDARD INCHES")
;;;    cbk:*dimoff*    how far the dimension lines stand off the block,
;;;                    drawing units (12.0 = a foot in an inch drawing)
;;;
;;;  Notes
;;;    * Back (or Undo, or B) at any question after the first re-asks
;;;      the one before it.  Nothing is drawn until all four answers
;;;      are in, so backing out costs nothing.
;;;    * Length, width and height are all required and all must be
;;;      positive -- a zero-thickness block has no pictorial to draw.
;;;      Either type the number or pick the distance in the drawing;
;;;      your own object snaps stay live for that, and for the base
;;;      point.
;;;    * The layers are created when the drawing lacks them, and
;;;      thawed / unlocked / switched back on when they are there but
;;;      not usable -- a run onto a frozen layer would otherwise look
;;;      like the command did nothing.
;;;      A missing "STANDARD INCHES" style is NOT invented: the dims
;;;      are drawn in whatever style is current and the routine says
;;;      so, so a drawing started from the wrong template is obvious
;;;      instead of silently producing wrong-looking dims.
;;;    * The dimension style, current layer, CMDECHO and OSMODE in
;;;      force before the command are restored afterwards, on a clean
;;;      finish, an error, or Esc.
;;; ======================================================================

(setq *custblock-version* "v1.0")  ; announced on load; release_lisp.py
                                   ; reads this banner and stamps the
                                   ; dated twin in releases/ from it

(setq cbk:*layer*    "COVER")           ; the block itself
(setq cbk:*laycolor* 7)
(setq cbk:*dimlayer* "DIMENSION")       ; its dimensions
(setq cbk:*dimcolor* 141)
(setq cbk:*style*    "STANDARD INCHES")
(setq cbk:*dimoff*   12.0)              ; dim line stand-off, units

;;; -------------------- helpers -----------------------------------------

;; Where the block goes -- its front bottom left corner.  Picked with
;; the user's own object snaps still live, and backed out of like any
;; other question; nothing has been drawn at that point.  Enter takes
;; the origin.  Returns a 3-D point (the elevation is carried, so a UCS
;; with one is honoured) or CAL-BACK.
(defun cbk:askbase (back / v)
  (if back (initget "Back Undo"))
  ;; bracket before the default, the one prompt shape of STANDARDS.md
  ;; section 1 -- the wording itself is section 3's Placement question
  (setq v (getpoint (strcat "\nInsertion base point"
                            (if back " [Back]" "") " <0,0>: ")))
  (cond ((and (= (type v) 'STR) (member v '("Back" "Undo"))) 'CAL-BACK)
        ((null v) (list 0.0 0.0 0.0))
        (t (list (car v) (cadr v) (if (caddr v) (caddr v) 0.0)))))

;; A point of the block: x across the front, y up it, both measured
;; from the base point.  Every corner below is built through here, so
;; the whole block moves with one answer -- and every one of them is in
;; the CURRENT UCS, which is where the base point arrived from, so the
;; block lies flat in the coordinate system the drafter is working in.
(defun cbk:pt (base x y)
  (list (+ (car base) x) (+ (cadr base) y) (caddr base)))

;; One block edge.  entmakex rather than the LINE command: no command
;; echo, no chance of a running object snap catching an endpoint, and
;; the layer is stated outright instead of depending on CLAYER.  entmake
;; wants WORLD coordinates, so the two UCS points are translated on the
;; way in -- skip that and the block lands somewhere else entirely under
;; a rotated or shifted UCS.
(defun cbk:line (p1 p2)
  (entmakex (list '(0 . "LINE") '(100 . "AcDbEntity")
                  (cons 8 cbk:*layer*) '(100 . "AcDbLine")
                  (cons 10 (trans p1 1 0)) (cons 11 (trans p2 1 0)))))

;; restore a dimension style by name when the drawing has it;
;; returns T when the style was set
(defun cbk:setstyle (name)
  (if (and name (tblsearch "DIMSTYLE" name))
    (progn (command "_.-DIMSTYLE" "_Restore" name) t)))

;; DIMSTYLE is read-only to setvar, so it goes back through a command --
;; and only when the style really did move: a run that never found
;; "STANDARD INCHES" should not leave a pointless -DIMSTYLE Restore in
;; the drawing's command history.  command-s, so the same call is legal
;; from inside the error handler.
(defun cbk:restyle (odim)
  (if (and odim (tblsearch "DIMSTYLE" odim)
           (not (equal odim (getvar "DIMSTYLE"))))
    (vl-catch-all-apply 'command-s
                        (list "_.-DIMSTYLE" "_Restore" odim))))

;; a copy of an entget list with every entry for group CODE dropped
(defun cbk:strip (code lst / out)
  (foreach g lst (if (/= code (car g)) (setq out (cons g out))))
  (reverse out))

;; force a freshly drawn dimension onto the layer and style CUSTBLOCK
;; promises, ByLayer -- DIMLAYER, a style-owned layer or a leftover
;; per-entity override would otherwise have the last word
(defun cbk:fixdim (en havestyle / ed)
  (if (and en (setq ed (entget en))
           (= "DIMENSION" (cdr (assoc 0 ed))))
    (progn
      (setq ed (if (assoc 8 ed)
                 (subst (cons 8 cbk:*dimlayer*) (assoc 8 ed) ed)
                 (append ed (list (cons 8 cbk:*dimlayer*)))))
      (if havestyle
        (setq ed (if (assoc 3 ed)
                   (subst (cons 3 cbk:*style*) (assoc 3 ed) ed)
                   (append ed (list (cons 3 cbk:*style*))))))
      (foreach code '(62 6 370) (setq ed (cbk:strip code ed)))
      (entmod ed)
      (entupd en)
      t)))

;; Draw one dimension and hand it its layer and style.  kind is 'ALIGNED
;; for a dim that reads along its own axis (the receding length edge),
;; 'HORIZ or 'VERT for a linear one held to the horizontal or the
;; vertical -- forced, rather than left to AutoCAD to infer from where
;; the dimension line was put, so a stand-off the user has retuned
;; cannot flip a width dim into a height one.  (Spelled out, not 'H and
;; 'V: AutoLISP symbols are case-blind, so a bare 'V is the same symbol
;; as a local named v.)
(defun cbk:dim (kind p1 p2 loc havestyle / pre new)
  ;; the points go in as they were built, in the current UCS, which is
  ;; what a command reads; _non so a running object snap cannot pull an
  ;; extension line origin onto nearby geometry
  (setq pre (entlast))
  (if (eq kind 'ALIGNED)
    (command "_.DIMALIGNED" "_non" p1 "_non" p2 "_non" loc)
    (command "_.DIMLINEAR" "_non" p1 "_non" p2
             (if (eq kind 'VERT) "_V" "_H") "_non" loc))
  (setq new (entlast))
  (if (and new (not (eq new pre)))
    (progn (cbk:fixdim new havestyle) new)))

;; how the numbers read back in the closing report -- rtos in the
;; drawing's own units, so a 4'-0" block says 4'-0" on an architectural
;; sheet and 48 on a decimal one
(defun cbk:num (x) (rtos x))

;;; -------------------- the command -------------------------------------

(defun c:CUSTBLOCK ( / *error* olderr odim
                       step len wid hgt base v d
                       pa pb pc pd qb qc qd
                       havestyle undo-open off made )

  ;; -- restore drawing state on error / Esc.  The user's settings come
  ;;    back FIRST so nothing below can skip them; a dimension command
  ;;    may still be open, so AutoCAD is talked to through command-s --
  ;;    and the undo group is closed, or the next U would swallow the
  ;;    user's own work
  (setq olderr *error*)
  (defun *error* (m)
    (cal:sysrestore)
    (cbk:restyle odim)
    (if undo-open
      (vl-catch-all-apply 'command-s (list "_.UNDO" "_End")))
    (setq *error* olderr)
    (if (and m (not (wcmatch (strcase m)
                             "*BREAK*,*CANCEL*,*QUIT*,*EXIT*")))
      (princ (strcat "\nCUSTBLOCK error: " m)))
    (princ))

  (cal:syssave '("OSMODE" "CMDECHO" "CLAYER"))
  (setq odim (getvar "DIMSTYLE"))

  ;; -- 1. the four answers.  Back re-asks the question before; the
  ;;       first question never offers it, and nothing is drawn until
  ;;       all four are in, so a run can be walked backwards for free
  (setq step 1)
  (while (< step 5)
    (cond
      ((= step 1)
         (setq len  (cal:askdist 'REQ "Block length" nil nil)
               step 2))
      ((= step 2)
         (setq v (cal:askdist 'REQ "Block width" nil T))
         (if (eq v 'CAL-BACK)
           (progn (princ "\nStepping back one dimension.")
                  (setq step 1))
           (setq wid v step 3)))
      ((= step 3)
         (setq v (cal:askdist 'REQ "Block height" nil T))
         (if (eq v 'CAL-BACK)
           (progn (princ "\nStepping back one dimension.")
                  (setq step 2))
           (setq hgt v step 4)))
      ((= step 4)
         (setq v (cbk:askbase T))
         (if (eq v 'CAL-BACK)
           (progn (princ "\nStepping back one dimension.")
                  (setq step 3))
           (setq base v step 5)))))

  ;; -- 2. the eight corners.  The block is a pictorial: the back face
  ;;       is the front face slid up-right at 45 degrees, and it is slid
  ;;       by the TRUE length over root 2 on each axis, so the receding
  ;;       edge measures the length that was typed
  (setq d  (/ len (sqrt 2.0))
        pa (cbk:pt base 0.0 0.0)              ; front face, anticlockwise
        pb (cbk:pt base wid 0.0)              ; from the base point
        pc (cbk:pt base wid hgt)
        pd (cbk:pt base 0.0 hgt)
        qb (cbk:pt base (+ wid d) d)          ; back face, three of the
        qc (cbk:pt base (+ wid d) (+ hgt d))  ; four -- its bottom left
        qd (cbk:pt base d (+ hgt d)))         ; corner is never reached

  ;; -- 3. draw it, all of it inside one undo group
  (setvar "CMDECHO" 0)
  (setvar "OSMODE"  0)
  (command "_.UNDO" "_Begin")
  (setq undo-open t)

  (cal:ensure-layer cbk:*layer* cbk:*laycolor*)
  ;; the front face, then the two faces the viewpoint shows.  The back
  ;; bottom left corner is a corner of the block, but all three edges
  ;; that meet there are hidden behind it -- so it is not even computed
  ;; above, and no line below reaches it.  Drawing those three is what
  ;; would turn a solid into a wire cage
  (cbk:line pd pc)                            ; front face
  (cbk:line pc pb)
  (cbk:line pb pa)
  (cbk:line pa pd)
  (cbk:line pd qd)                            ; top face, back edge and
  (cbk:line qd qc)                            ; the two receding edges
  (cbk:line pc qc)
  (cbk:line qc qb)                            ; right face, back edge
  (cbk:line pb qb)                            ; and its receding edge

  ;; -- 4. the three dimensions, in their own layer and style
  (setvar "CLAYER" (cal:ensure-layer cbk:*dimlayer* cbk:*dimcolor*))
  (setq havestyle (cbk:setstyle cbk:*style*))
  (if (not havestyle)
    (princ (strcat "\n** This drawing has no \"" cbk:*style*
                   "\" dimension style -- dims drawn in \""
                   (getvar "DIMSTYLE")
                   "\" instead.  Create the style (or start from the"
                   " standard template) and re-run.")))

  (setq off  cbk:*dimoff*
        made 0)
  ;; the length, aligned along the top-left receding edge and pushed
  ;; out on the far side of it, away from the top face
  (if (cbk:dim 'ALIGNED pd qd
               (cbk:pt base (- (/ d 2.0) (/ off (sqrt 2.0)))
                            (+ hgt (/ d 2.0) (/ off (sqrt 2.0))))
               havestyle)
    (setq made (1+ made)))
  ;; the height, up the left of the front face
  (if (cbk:dim 'VERT pa pd (cbk:pt base (- off) (/ hgt 2.0)) havestyle)
    (setq made (1+ made)))
  ;; the width, along under it
  (if (cbk:dim 'HORIZ pb pa (cbk:pt base (/ wid 2.0) (- off)) havestyle)
    (setq made (1+ made)))

  ;; -- 5. put the drawing back the way it was
  (cbk:restyle odim)
  (command "_.UNDO" "_End")
  (setq undo-open nil)
  (cal:sysrestore)
  (setq *error* olderr)

  (princ (strcat "\nCUSTBLOCK: " (cbk:num len) " x " (cbk:num wid)
                 " x " (cbk:num hgt) " block drawn on layer "
                 cbk:*layer* " -- 9 lines and " (itoa made)
                 " dimension" (if (= made 1) "" "s") " on layer "
                 cbk:*dimlayer*
                 (if havestyle
                   (strcat " in style " cbk:*style* ".")
                   " (current style).")))
  (princ))

(defun c:CUSTBLOCKVER ()
  (princ (strcat "\nCUSTBLOCK " *custblock-version*))
  (princ))

(princ (strcat "\nCUSTBLOCK " *custblock-version*
               " loaded -- type CUSTBLOCK to draw a block from its"
               " length, width and height (layer \"" cbk:*layer*
               "\", dims \"" cbk:*style* "\")."))
(princ)


;;; ======================================================================
;;; >>> dimcheck.lsp
;;; ======================================================================

;;; ------------------------------------------------------------------
;;;  dimcheck.lsp — DIMCHECK: dims, arcs & overlaps QA review
;;;
;;;  The lean pass — dimension placement, arc-end attachment, and
;;;  overlapping lines, with nothing else touched. For the full
;;;  liner-finish review (this plus steps/side views, wall height,
;;;  the liner pattern, and the title block border), load
;;;  linfincheck.lsp instead and run LINFINCHECK; it shares this
;;;  file's Move/Keep/Pick review and report machinery. Type DIMCHECK,
;;;  then:
;;;
;;;  1. You are asked to highlight the drawing (any selection).
;;;     Everything selected is greyed out so only the item under
;;;     review stands out.
;;;
;;;  2. Dimensions are reviewed ONE AT A TIME, in a fixed marching
;;;     order: grouped by dimension style — "STANDARD", then "SIDE
;;;     STANDARD", then "STANDARD INCHES", then "CROSS DIMENSIONS",
;;;     then whatever styles are left (tune *dchk-style-order*) —
;;;     and inside each group left to right, top to bottom (row by
;;;     row, like reading). Each dimension is zoomed to, shown in
;;;     its own colour and highlighted while the rest stays grey.
;;;     For linear/aligned dimensions the two definition points are
;;;     audited first: a point that does not sit on any object is
;;;     shown where DIMCHECK thinks it belongs, with BOTH spots
;;;     marked on screen and spelled out so there is no doubt which
;;;     is which —
;;;         a RED X   where you drew it,
;;;         a GREEN + where we would move it, joined by a line.
;;;     You then choose, one point at a time:
;;;         Enter / M  ->  MOVE it onto the nearest object (green +)
;;;         K          ->  KEEP it exactly where you drew it (red X);
;;;                        the point is put back and nothing changes
;;;         P          ->  PICK the spot yourself
;;;     A construction line (XLINE) is drawn through the dimension's
;;;     original points on layer DIMCHECK-CONSTRUCTION so you can see
;;;     where it used to measure — only when a point actually moved.
;;;     Then the overall question for every dimension:
;;;         "Is this dimension correct?"
;;;         Enter / Y  ->  correct, the dimension is left alone
;;;         N          ->  the dimension is recoloured RED so it is
;;;                        easy to find and fix afterwards
;;;         B          ->  back one dimension, redo it
;;;         S          ->  skip the rest, still write the report
;;;
;;;  3. Arcs are reviewed the same way, one endpoint at a time, with
;;;     the same Move / Keep / Pick choice. An endpoint not attached
;;;     to the end of another object is snapped there and both spots
;;;     are marked; Keep puts the arc back exactly as you drew it
;;;     (its original shape is restored, not re-fitted), Pick re-fits
;;;     it through your spot. Arcs whose endpoints actually changed
;;;     are recoloured MAGENTA — an arc you kept is left alone.
;;;
;;;  4. OVERLAPPING LINES are hunted down: two straight LINE entities
;;;     (or polyline edges) that are collinear and run on top of each
;;;     other (a leftover from drawing over an existing line to
;;;     continue it and never cleaning it up). Each overlapping pair
;;;     is zoomed to and highlighted, the overlapping stretch is
;;;     marked with crosses, and you choose:
;;;         Enter / M  ->  MERGE the two into one line spanning both
;;;                        (only when they are two whole LINEs on one
;;;                        layer; the merged line turns CYAN)
;;;         F          ->  FLAG both CYAN to fix by hand
;;;         L          ->  LEAVE them as drawn (intentional)
;;;     Lines that merely touch end-to-end are fine and not reported.
;;;
;;;  5. A DIMCHECK REPORT (MTEXT) is placed to the RIGHT of the
;;;     drawing on layer DIMCHECK-REPORT listing every dimension —
;;;     with its measured distance (in the drawing's units; angular
;;;     dims show their angle) — every arc, and every overlapping
;;;     line pair (with its overlap length), plus totals. The report
;;;     text is sized from the drawing's extents so it sits to scale
;;;     next to it. Any line describing something questionable (a
;;;     flagged/moved item, a skipped check) is coloured RED in the
;;;     report; everything that checked out stays the report's normal
;;;     colour and is drawn at *dchk-green-scale* (3/4) of the red
;;;     text's height, so the problems are the big lines on the sheet.
;;;
;;;  All original colours are restored when the review ends — except
;;;  the red "fix me" dimensions, magenta moved arcs and cyan
;;;  merged/flagged lines, which stay marked on purpose. Everything
;;;  (including the report) runs inside one UNDO group, so a single U
;;;  reverts the whole review.
;;;
;;;  SAFETY NETS
;;;  - Locked layers in the selection are announced up front with an
;;;    offer to unlock for the run (re-locked afterwards, even on
;;;    error); left locked, their items are reported but untouched.
;;;  - Object-associative dimensions are warned about before their
;;;    points are moved — an associative point may re-anchor on its
;;;    own — and their report line says so in red.
;;;  - Rerunning DIMCHECK replaces the previous report and marker
;;;    lines instead of stacking a second copy on top.
;;;  - Original colours are stashed in xdata before greying. If a
;;;    crash or kill ever leaves the drawing grey, DIMCHECKRESCUE
;;;    restores every stashed colour and clears DIMCHECK's report
;;;    and markers (flag colours included — it is the full reset).
;;;  - Loading both dimcheck.lsp and linfincheck.lsp in the same
;;;    session is safe: distinct dchk:/lfc: function prefixes,
;;;    *dchk-/*lfc- globals, layer names and xdata tags mean neither
;;;    tool's rescue command touches the other's markers.
;;; ------------------------------------------------------------------
;;; SHARED BUILD: requires CALOFIN-LIB.lsp (load via CALOFIN-LOADER.lsp).
;;; Generic helpers live there under cal: - see STANDARDS.md.

(vl-load-com)

;; ---- configuration -------------------------------------------------
(setq *dchk-version* "v1.4")        ; announced on load; release_lisp.py
                                    ; reads this banner and stamps the
                                    ; dated twin in releases/ from it

(defun c:DIMCHECKVER ()
  (princ (strcat "\nDIMCHECK " *dchk-version*))
  (princ))

;; --- tunables ------------------------------------------------------
(setq *dchk-tol*          1.0e-4)  ; max gap (drawing units) that still counts as attached
(setq *dchk-grey-color*   8)       ; grey used to fade out everything not under review
(setq *dchk-flag-color*   1)       ; red: dimensions you answered "No" to
(setq *dchk-arc-color*    6)       ; magenta: arcs whose endpoints were moved
(setq *dchk-olap-color*   4)       ; cyan: merged or flagged overlapping lines
(setq *dchk-olap-fuzz*    1.0e-4)  ; max sideways offset that still counts as "same line"
(setq *dchk-constr-layer* "DIMCHECK-CONSTRUCTION")
(setq *dchk-constr-color* 2)       ; yellow
(setq *dchk-green-scale*  0.75)    ; report: all-clear text height, as a fraction of the red text
(setq *dchk-orig-color*   1)       ; red X: where you drew the point
(setq *dchk-sugg-color*   3)       ; green +: where DIMCHECK would move it
(setq *dchk-report-layer* "DIMCHECK-REPORT")
(setq *dchk-report-color* 3)       ; green
(setq *dchk-zoom-margin*  0.75)    ; empty space around the zoomed item (fraction of its size)
(setq *dchk-report-chars* 45.0)    ; report column width, in text heights
(setq *dchk-ask-all-arc-ends* nil) ; T = confirm EVERY arc endpoint, even already-attached ones

;; dimension styles are reviewed in this order; styles not listed
;; come afterwards ("whatever else is left"), still left-to-right
(setq *dchk-style-order*
      '("STANDARD" "SIDE STANDARD" "STANDARD INCHES" "CROSS DIMENSIONS"))

;; entity types dimension points and arc ends may attach to
(setq *dchk-curve-types*
      '("LINE" "ARC" "CIRCLE" "ELLIPSE" "LWPOLYLINE" "POLYLINE" "SPLINE"))

;; --- safety: xdata tags, colour stash, layer locks -----------------

(defun dchk:regapp ()
  (if (not (tblsearch "APPID" "DIMCHECK"))
    (regapp "DIMCHECK")))

(defun dchk:xd (ent / g)
  ;; DIMCHECK's xdata groups on ent, nil when none
  (setq g (assoc -3 (entget ent '("DIMCHECK"))))
  (if g (cdadr g)))

(defun dchk:tag (ent kind / ed)
  ;; stamp a DIMCHECK-created entity (report, marker line) so a rerun
  ;; or DIMCHECKRESCUE can find and clear it
  (dchk:regapp)
  (setq ed (entget ent '("DIMCHECK")))
  (if (and ed (not (assoc -3 ed)))
    (entmod (append ed (list (list -3 (list "DIMCHECK" (cons 1000 kind))))))))

(defun dchk:stash-color (ent col / ed)
  ;; remember the entity's own colour in xdata so DIMCHECKRESCUE can
  ;; put it back even after a crash; an existing stash (from an
  ;; interrupted run - the TRUE original) is never overwritten
  (dchk:regapp)
  (setq ed (entget ent '("DIMCHECK")))
  (if (and ed (not (assoc -3 ed)))
    (entmod (append ed (list (list -3 (list "DIMCHECK"
                                            '(1000 . "COLOR")
                                            (cons 1071 col))))))))

(defun dchk:unstash (ent / ed)
  ;; drop DIMCHECK's xdata once the run has restored things itself
  (setq ed (entget ent '("DIMCHECK")))
  (if (and ed (assoc -3 ed))
    (entmod (subst (list -3 (list "DIMCHECK")) (assoc -3 ed) ed))))

(defun dchk:clear-old (/ ss2 i e xd n)
  ;; erase the report and marker lines left by an earlier DIMCHECK
  ;; run, so a rerun replaces them instead of stacking on top
  (setq ss2 (ssget "_X" '((-3 ("DIMCHECK")))) n 0 i 0)
  (if ss2
    (repeat (sslength ss2)
      (setq e  (ssname ss2 i)
            i  (1+ i)
            xd (dchk:xd e))
      (if (member (cdr (assoc 1000 xd)) '("REPORT" "XLINE"))
        (progn (entdel e) (setq n (1+ n))))))
  (if (> n 0)
    (princ (strcat "\n(Removed " (itoa n)
                   " report/marker item(s) from an earlier DIMCHECK run.)"))))

(defun dchk:layer-locked-p (name / ld)
  (setq ld (tblsearch "LAYER" name))
  (and ld (= 4 (logand 4 (cdr (assoc 70 ld))))))

(defun dchk:set-layer-lock (name lock / ed old new)
  ;; set or clear a layer's locked flag; T when it actually changed
  (setq ed  (entget (tblobjname "LAYER" name))
        old (cdr (assoc 70 ed))
        new (if lock (logior old 4) (logand old (~ 4))))
  (if (/= old new)
    (progn (entmod (subst (cons 70 new) (assoc 70 ed) ed)) T)))

(defun dchk:dim-assoc-p (ent / found g)
  ;; T when the dimension carries persistent reactors - the mark of
  ;; an object-associative dim, whose definition points may re-anchor
  ;; on their own after being moved
  (foreach g (entget ent)
    (if (and (= 102 (car g)) (= "{ACAD_REACTORS" (cdr g)))
      (setq found T)))
  found)

(defun c:DIMCHECKRESCUE ( / ss i e xd n)
  ;; the way out after a crash or interrupted run: puts back every
  ;; colour DIMCHECK stashed (flag colours included) and removes its
  ;; report and marker lines
  (setq ss (ssget "_X" '((-3 ("DIMCHECK")))) n 0 i 0)
  (if ss
    (repeat (sslength ss)
      (setq e  (ssname ss i)
            i  (1+ i)
            xd (dchk:xd e))
      (cond
        ((member (cdr (assoc 1000 xd)) '("REPORT" "XLINE"))
         (entdel e)
         (setq n (1+ n)))
        ((assoc 1071 xd)
         (dchk:set-color e (cdr (assoc 1071 xd)))
         (dchk:unstash e)
         (setq n (1+ n))))))
  (if (> n 0)
    (princ (strcat "\nDIMCHECKRESCUE: restored or removed " (itoa n) " item(s)."))
    (princ "\nDIMCHECKRESCUE: nothing to restore - no DIMCHECK markers in the drawing."))
  (princ))

;; --- small helpers -------------------------------------------------

(defun dchk:ent-color (ent / c)
  ;; the entity's explicit colour, 256 (ByLayer) when it has none
  (setq c (cdr (assoc 62 (entget ent))))
  (if c c 256))

(defun dchk:set-color (ent color / ed old)
  (setq ed  (entget ent)
        old (assoc 62 ed))
  (entmod (if old
            (subst (cons 62 color) old ed)
            (append ed (list (cons 62 color)))))
  (entupd ent))

(defun dchk:make-xline (p1 p2 / len)
  ;; infinite construction line through p1-p2 on the check layer,
  ;; tagged so reruns and DIMCHECKRESCUE can clear it
  (setq len (distance p1 p2))
  (if (and (> len 1e-8)
           (entmake (list '(0 . "XLINE")
                          '(100 . "AcDbEntity")
                          (cons 8 *dchk-constr-layer*)
                          '(100 . "AcDbXline")
                          (cons 10 p1)
                          (cons 11 (mapcar '(lambda (x) (/ x len))
                                           (mapcar '- p2 p1))))))
    (dchk:tag (entlast) "XLINE")))

(defun dchk:closest-on (ent pt / res)
  ;; closest point on ent to pt; nil when ent is not curve-like
  (setq res (vl-catch-all-apply 'vlax-curve-getClosestPointTo (list ent pt)))
  (if (vl-catch-all-error-p res) nil res))

(defun dchk:nearest-curve (pt exclude cands / best bestd cp d e)
  ;; (ent closest-point distance) for the candidate closest to pt
  (foreach e cands
    (if (and (not (eq e exclude)) (setq cp (dchk:closest-on e pt)))
      (progn
        (setq d (distance pt cp))
        (if (or (null bestd) (< d bestd))
          (setq bestd d
                best  (list e cp d))))))
  best)

(defun dchk:curve-ends (ent / cl sp ep)
  ;; the curve's two endpoints; nil when closed (or not a curve)
  (setq cl (vl-catch-all-apply 'vlax-curve-isClosed (list ent)))
  (if (or (vl-catch-all-error-p cl) cl)
    nil
    (progn
      (setq sp (vl-catch-all-apply 'vlax-curve-getStartPoint (list ent))
            ep (vl-catch-all-apply 'vlax-curve-getEndPoint (list ent)))
      (if (or (vl-catch-all-error-p sp) (vl-catch-all-error-p ep))
        nil
        (list sp ep)))))

(defun dchk:closest-of (pt pts / best bestd d q)
  (foreach q pts
    (setq d (distance pt q))
    (if (or (null bestd) (< d bestd)) (setq bestd d best q)))
  best)

(defun dchk:nearest-end (pt exclude cands / best bestd d e q)
  ;; closest endpoint over every open candidate curve
  (foreach e cands
    (if (not (eq e exclude))
      (foreach q (dchk:curve-ends e)
        (setq d (distance pt q))
        (if (or (null bestd) (< d bestd)) (setq bestd d best q)))))
  best)

(defun dchk:ptstr (p)
  (strcat "(" (rtos (car p) 2 4) ", " (rtos (cadr p) 2 4) ")"))

(defun dchk:zoom-ent (ent / bb p1 p2 m)
  ;; zoom the current view onto ent with some breathing room
  (setq bb (cal:bbox-ent ent))
  (if bb
    (progn
      (setq p1 (car bb)
            p2 (cadr bb)
            m  (* *dchk-zoom-margin*
                  (max (- (car p2) (car p1)) (- (cadr p2) (cadr p1)) 1e-6)))
      (command "_.ZOOM" "_Window"
               (trans (list (- (car p1) m) (- (cadr p1) m) 0.0) 0 1)
               (trans (list (+ (car p2) m) (+ (cadr p2) m) 0.0) 0 1)))))

(defun dchk:zoom-2ents (e1 e2 / b1 b2 p1 p2 m)
  ;; zoom onto the combined box of two entities
  (setq b1 (cal:bbox-ent e1)
        b2 (cal:bbox-ent e2))
  (cond
    ((and b1 b2)
     (setq p1 (list (min (caar b1) (caar b2))
                    (min (cadar b1) (cadar b2)))
           p2 (list (max (caadr b1) (caadr b2))
                    (max (cadadr b1) (cadadr b2)))
           m  (* *dchk-zoom-margin*
                 (max (- (car p2) (car p1)) (- (cadr p2) (cadr p1)) 1e-6)))
     (command "_.ZOOM" "_Window"
              (trans (list (- (car p1) m) (- (cadr p1) m) 0.0) 0 1)
              (trans (list (+ (car p2) m) (+ (cadr p2) m) 0.0) 0 1)))
    (b1 (dchk:zoom-ent e1))
    (b2 (dchk:zoom-ent e2))))

(defun dchk:stage (ent saved keep)
  ;; bring an entity back to its own colour for review — unless it
  ;; already wears a DIMCHECK marker colour it must not lose
  (if (and (entget ent) (not (member ent keep)))
    (dchk:set-color ent (cdr (assoc ent saved)))))

(defun dchk:unstage (ent keep)
  ;; send a reviewed entity back into the grey background
  (if (and (entget ent) (not (member ent keep)))
    (dchk:set-color ent *dchk-grey-color*)))

(defun dchk:mark-x (pt col / p s)
  ;; diagonal cross - marks WHERE YOU DREW IT
  (setq p (trans pt 0 1)
        s (* 0.02 (getvar "VIEWSIZE")))
  (grdraw (list (- (car p) s) (- (cadr p) s)) (list (+ (car p) s) (+ (cadr p) s)) col 1)
  (grdraw (list (- (car p) s) (+ (cadr p) s)) (list (+ (car p) s) (- (cadr p) s)) col 1))

(defun dchk:mark-plus (pt col / p s)
  ;; upright cross - marks WHERE DIMCHECK WOULD PUT IT
  (setq p (trans pt 0 1)
        s (* 0.02 (getvar "VIEWSIZE")))
  (grdraw (list (- (car p) s) (cadr p)) (list (+ (car p) s) (cadr p)) col 1)
  (grdraw (list (car p) (- (cadr p) s)) (list (car p) (+ (cadr p) s)) col 1))

(defun dchk:mark-point (pt)
  ;; both strokes, for a point that is simply being pointed out
  (dchk:mark-x pt 2)
  (dchk:mark-plus pt 2))

(defun dchk:confirm-move (label orig sugg / ans newp)
  ;; The point has been put where DIMCHECK thinks it belongs, but BOTH
  ;; spots are marked and spelled out so there is no doubt which is
  ;; which: a red X where you drew it, a green + where we would move
  ;; it, joined by a line. Returns
  ;;   'move - take our suggestion
  ;;   'keep - put it back exactly where you drew it
  ;;   <point> - a spot you picked yourself (current UCS)
  (dchk:mark-x    orig *dchk-orig-color*)
  (dchk:mark-plus sugg *dchk-sugg-color*)
  (if (> (distance orig sugg) 1e-8)
    (grdraw (trans orig 0 1) (trans sugg 0 1) *dchk-sugg-color* 1))
  (princ (strcat "\n  " label " - which spot is right?"
                 "\n    Keep = where you drew it   " (dchk:ptstr orig)
                 "  (red X)"
                 "\n    Move = onto nearest object " (dchk:ptstr sugg)
                 "  (green +), " (rtos (distance orig sugg) 2 4) " away"
                 "\n    Pick = somewhere else you point at"))
  (initget "Move Keep Pick")
  (setq ans (getkword
              "\n  [Move/Keep/Pick] <Move>: "))
  (cond
    ((or (null ans) (= ans "Move")) 'move)
    ((= ans "Keep") 'keep)
    (t (setq newp (getpoint (strcat "\n  Pick the spot for " label
                                    " <Move to the green +>: ")))
       (if newp newp 'move))))

(defun dchk:mtext (ins height width text layer / e)
  ;; entmake an MTEXT, splitting text into 250-char DXF chunks
  (if (setq e (cal:mtext ins height width text layer))
    (dchk:tag e "REPORT")))

(defun dchk:join (lst sep / out s)
  ;; "A" + "B" + ... joined with sep
  (foreach s lst
    (setq out (if out (strcat out sep s) s)))
  out)

(defun dchk:attn-p (s)
  ;; T when a report line describes something questionable or that
  ;; needs looking over / fixing, so the report renders it in red
  (wcmatch (strcase s)
    "*FLAGGED*,*SKIPPED*,*MAGENTA*,*ASSOCIATIVE*,*NOT ATTACHED*,*OVERLAP*"))

(defun dchk:red (s)
  ;; wrap an MTEXT run so it renders in the flag colour, reverting
  ;; to the surrounding colour after (braces scope the change)
  (strcat "{\\C" (itoa *dchk-flag-color*) ";" s "}"))

(defun dchk:small (s)
  ;; all-clear text renders at *dchk-green-scale* of the height the
  ;; red attention text gets, so problems stand out on the sheet
  (strcat "{\\H" (rtos *dchk-green-scale* 2 4) "x;" s "}"))

;; --- geometry ------------------------------------------------------

(defun dchk:planar-arc-p (ed / n)
  ;; only arcs drawn in the world XY plane are handled
  (setq n (cdr (assoc 210 ed)))
  (or (null n)
      (and (< (abs (car n)) 1e-9)
           (< (abs (cadr n)) 1e-9)
           (> (caddr n) 0.0))))

(defun dchk:rebuild-arc (ent which fixed mid target / c r a1 a2 am tmp ed pair)
  ;; re-fit the arc through its fixed end, its old midpoint and the
  ;; target point; returns T on success
  (if (and (> (distance target fixed) 1e-8)
           (setq c (cal:circumcenter fixed mid target)))
    (progn
      (setq r  (distance c target)
            a1 (angle c (if (eq which 'start) target fixed))
            a2 (angle c (if (eq which 'start) fixed target))
            am (angle c mid))
      ;; ARC entities always sweep counter-clockwise from start to
      ;; end; keep the sweep that contains the old midpoint
      (if (> (cal:angnorm (- am a1)) (cal:angnorm (- a2 a1)))
        (setq tmp a1
              a1  a2
              a2  tmp))
      (setq ed (entget ent))
      (foreach pair (list (cons 10 c) (cons 40 r) (cons 50 a1) (cons 51 a2))
        (setq ed (subst pair (assoc (car pair) ed) ed)))
      (if (entmod ed)
        (progn (entupd ent) T)))))

(defun dchk:move-arc-end (ent which target / mid other)
  ;; re-fit the arc so the chosen endpoint lands on target (WCS)
  (setq mid   (vlax-curve-getPointAtDist
                ent
                (/ (vlax-curve-getDistAtParam ent (vlax-curve-getEndParam ent)) 2.0))
        other (if (eq which 'start)
                (vlax-curve-getEndPoint ent)
                (vlax-curve-getStartPoint ent)))
  (dchk:rebuild-arc ent which other mid target))

;; --- overlap detection ----------------------------------------------

(defun dchk:overlap-info (la lb / a1 a2 b1 b2 u lena s1 s2 tmp lo hi)
  ;; when segments la and lb are collinear (within *dchk-olap-fuzz*)
  ;; and run on top of each other for more than *dchk-tol*, returns
  ;;   (ov-start ov-end ov-length union-start union-end)
  ;; nil when they do not overlap (touching end-to-end is fine)
  (setq a1 (dchk:seg-p1 la)
        a2 (dchk:seg-p2 la)
        b1 (dchk:seg-p1 lb)
        b2 (dchk:seg-p2 lb)
        u  (cal:unitn (mapcar '- a2 a1)))
  (if (and u
           (<= (cal:pt-line-dist b1 a1 u) *dchk-olap-fuzz*)
           (<= (cal:pt-line-dist b2 a1 u) *dchk-olap-fuzz*))
    (progn
      (setq lena (distance a1 a2)
            s1   (cal:proj-param b1 a1 u)
            s2   (cal:proj-param b2 a1 u))
      (if (> s1 s2) (setq tmp s1 s1 s2 s2 tmp))
      (setq lo (max 0.0 s1)
            hi (min lena s2))
      (if (> (- hi lo) *dchk-tol*)
        (list (cal:axis-pt a1 u lo)
              (cal:axis-pt a1 u hi)
              (- hi lo)
              (cal:axis-pt a1 u (min 0.0 s1))
              (cal:axis-pt a1 u (max lena s2)))))))

(defun dchk:merge-lines (la lb info / ed)
  ;; stretch la's LINE over the union of both, delete lb's LINE
  (setq ed (entget (dchk:seg-ent la))
        ed (subst (cons 10 (nth 3 info)) (assoc 10 ed) ed)
        ed (subst (cons 11 (nth 4 info)) (assoc 11 ed) ed))
  (entmod ed)
  (entupd (dchk:seg-ent la))
  (entdel (dchk:seg-ent lb)))

(defun dchk:whole-line-p (s / ed)
  ;; T when the segment IS its owner entity - only whole LINEs can be
  ;; merged; a polyline edge has to be fixed by hand
  (setq ed (entget (dchk:seg-ent s)))
  (= "LINE" (cdr (assoc 0 ed))))

;; --- segments: lines AND polyline edges ----------------------------
;; Detection works on "segs" - (start end owner-entity) records - so a
;; run of overlapping geometry drawn as ONE polyline counts exactly
;; like the same shape drawn as separate LINEs.

(defun dchk:seg-p1 (s) (car s))

(defun dchk:seg-p2 (s) (cadr s))

(defun dchk:seg-ent (s) (caddr s))

(defun dchk:ocs->wcs (p nz)
  (if (and nz (not (equal nz '(0.0 0.0 1.0) 1e-9))) (trans p nz 0) p))

(defun dchk:lwpoly-segs (ent / ed nz elev vs bl cls n i segs g)
  ;; straight edges of an LWPOLYLINE; bulged (arc) edges are skipped
  (setq ed   (entget ent)
        nz   (cdr (assoc 210 ed))
        elev (cdr (assoc 38 ed))
        cls  (= 1 (logand 1 (cdr (assoc 70 ed))))
        vs   nil
        bl   nil)
  (if (null elev) (setq elev 0.0))
  (foreach g ed
    (cond
      ((= 10 (car g))
       (setq vs (cons (dchk:ocs->wcs (list (car (cdr g)) (cadr (cdr g)) elev) nz) vs)
             bl (cons 0.0 bl)))
      ((= 42 (car g))
       (if bl (setq bl (cons (cdr g) (cdr bl)))))))
  (setq vs (reverse vs)
        bl (reverse bl)
        n  (length vs)
        i  0)
  (while (< i (1- n))
    (if (equal 0.0 (nth i bl) 1e-12)
      (setq segs (cons (list (nth i vs) (nth (1+ i) vs) ent) segs)))
    (setq i (1+ i)))
  (if (and cls (> n 2) (equal 0.0 (nth (1- n) bl) 1e-12))
    (setq segs (cons (list (nth (1- n) vs) (car vs) ent) segs)))
  segs)

(defun dchk:heavy-poly-segs (ent / e ed vs bl cls n i segs)
  ;; straight edges of an old-style POLYLINE (VERTEX entities)
  (setq cls (= 1 (logand 1 (cdr (assoc 70 (entget ent)))))
        e   (entnext ent)
        vs  nil
        bl  nil)
  (while (and e (= "VERTEX" (cdr (assoc 0 (setq ed (entget e))))))
    (if (zerop (logand 16 (cdr (assoc 70 ed))))    ; skip spline frame points
      (setq vs (cons (cdr (assoc 10 ed)) vs)
            bl (cons (if (assoc 42 ed) (cdr (assoc 42 ed)) 0.0) bl)))
    (setq e (entnext e)))
  (setq vs (reverse vs)
        bl (reverse bl)
        n  (length vs)
        i  0)
  (while (< i (1- n))
    (if (equal 0.0 (nth i bl) 1e-12)
      (setq segs (cons (list (nth i vs) (nth (1+ i) vs) ent) segs)))
    (setq i (1+ i)))
  (if (and cls (> n 2) (equal 0.0 (nth (1- n) bl) 1e-12))
    (setq segs (cons (list (nth (1- n) vs) (car vs) ent) segs)))
  segs)

(defun dchk:ent-segs (ent / ed et)
  ;; every straight segment an entity contributes, in WCS
  (setq ed (entget ent)
        et (cdr (assoc 0 ed)))
  (cond
    ((= et "LINE")       (list (list (cdr (assoc 10 ed)) (cdr (assoc 11 ed)) ent)))
    ((= et "LWPOLYLINE") (dchk:lwpoly-segs ent))
    ((= et "POLYLINE")   (dchk:heavy-poly-segs ent))))

(defun dchk:collect-segs (ents / segs e s)
  ;; all straight segments of a list of entities, longer than the
  ;; attachment tolerance (zero-length stubs help nothing)
  (foreach e ents
    (if (entget e)
      (foreach s (dchk:ent-segs e)
        (if (> (distance (car s) (cadr s)) *dchk-tol*)
          (setq segs (cons s segs))))))
  (reverse segs))

(defun dchk:seg-dir-ang (s / a)
  ;; segment direction folded into [0, pi)
  (setq a (angle (dchk:seg-p1 s) (dchk:seg-p2 s)))
  (if (>= a pi) (- a pi) a))

(defun dchk:sort-recs (recs / out r pre rest)
  ;; stable insertion sort by (car rec); keeps equal elements
  (setq out nil)
  (foreach r recs
    (setq pre  nil
          rest out)
    (while (and rest (>= (car r) (caar rest)))
      (setq pre  (cons (car rest) pre)
            rest (cdr rest)))
    (setq out (append (reverse pre) (list r) rest)))
  out)

(defun dchk:find-overlaps (segs / atol fams a placed fam recs e p1 p2 dx dy
                                off s1 s2 tmp rest r q pairs seen key)
  ;; every overlapping segment pair, without comparing all pairs:
  ;; segments are bucketed by direction, then swept in offset order so
  ;; only genuinely collinear neighbours are ever tested. Segments of
  ;; the same entity are skipped (a polyline meeting itself is not a
  ;; duplicate), as are pairs already found through another segment.
  (setq atol  (* 0.5 (/ pi 180.0))              ; 0.5 deg is ample at this fuzz
        fams  nil
        pairs nil
        seen  nil)
  (foreach e segs
    (setq a      (dchk:seg-dir-ang e)
          placed nil)
    (foreach fam fams
      (if (and (not placed)
               (or (<= (cal:ang-diff a (car fam)) atol)))
        (setq fams   (subst (cons (car fam) (cons e (cdr fam))) fam fams)
              placed T)))
    (if (not placed) (setq fams (cons (list a e) fams))))
  (foreach fam fams
    (if (cdr (cdr fam))                          ; two or more to compare
      (progn
        (setq a  (car fam)
              dx (cos a)
              dy (sin a)
              recs nil)
        (foreach e (cdr fam)
          (setq p1  (dchk:seg-p1 e)
                p2  (dchk:seg-p2 e)
                off (- (* (cadr p1) dx) (* (car p1) dy))
                s1  (+ (* (car p1) dx) (* (cadr p1) dy))
                s2  (+ (* (car p2) dx) (* (cadr p2) dy)))
          (if (> s1 s2) (setq tmp s1 s1 s2 s2 tmp))
          (setq recs (cons (list off s1 s2 e) recs)))
        (setq recs (dchk:sort-recs recs))
        ;; sorted by offset: only sweep forward while still collinear
        (while recs
          (setq r    (car recs)
                rest (cdr recs))
          (while (and rest
                      (<= (- (car (car rest)) (car r)) *dchk-olap-fuzz*))
            (setq q (car rest))
            (if (and (not (eq (dchk:seg-ent (cadddr r))
                              (dchk:seg-ent (cadddr q))))
                     ;; spans must actually meet before the exact test
                     (> (min (caddr r) (caddr q)) (max (cadr r) (cadr q)))
                     (dchk:overlap-info (cadddr r) (cadddr q)))
              (progn
                (setq key (list (dchk:seg-ent (cadddr r))
                                (dchk:seg-ent (cadddr q))))
                (if (not (member key seen))
                  (setq seen  (cons key (cons (reverse key) seen))
                        pairs (cons (list (cadddr r) (cadddr q)) pairs)))))
            (setq rest (cdr rest)))
          (setq recs (cdr recs))))))
  (reverse pairs))

;; --- dimension review ----------------------------------------------

(defun dchk:dim-style (ent / s)
  ;; the dimension's style name, "" when it has none
  (setq s (cdr (assoc 3 (entget ent))))
  (if s s ""))

(defun dchk:style-rank (style / i r s)
  ;; position of the style in *dchk-style-order* (exact name match,
  ;; case-blind); unlisted styles land after every listed one
  (setq style (strcase style)
        i     0
        r     nil)
  (foreach s *dchk-style-order*
    (if (and (null r) (= (strcase s) style)) (setq r i))
    (setq i (1+ i)))
  (if r r (length *dchk-style-order*)))

(defun dchk:ent-center (ent / bb)
  ;; (x y) centre of the entity's box; falls back to its group-10 point
  (setq bb (cal:bbox-ent ent))
  (if bb
    (list (* 0.5 (+ (caar bb) (caadr bb)))
          (* 0.5 (+ (cadar bb) (cadadr bb))))
    (progn
      (setq bb (cdr (assoc 10 (entget ent))))
      (if bb (list (car bb) (cadr bb)) (list 0.0 0.0)))))

(defun dchk:dim-order-p (r1 r2 rowtol)
  ;; strict "r1 reviews before r2" for recs (rank cx cy ent):
  ;; style rank first, then row (higher = earlier), then left first
  (cond
    ((< (car r1) (car r2)) T)
    ((> (car r1) (car r2)) nil)
    ((> (- (caddr r1) (caddr r2)) rowtol) T)   ; r1 sits a row above
    ((> (- (caddr r2) (caddr r1)) rowtol) nil) ; r2 sits a row above
    (t (< (cadr r1) (cadr r2)))))

(defun dchk:sort-dims (dims rowtol / recs cen r out pre rest e)
  ;; stable insertion sort into review order
  (setq recs nil)
  (foreach e dims
    (setq cen  (dchk:ent-center e)
          recs (cons (list (dchk:style-rank (dchk:dim-style e))
                           (car cen) (cadr cen) e)
                     recs)))
  (setq recs (reverse recs)
        out  nil)
  (foreach r recs
    (setq pre  nil
          rest out)
    (while (and rest (not (dchk:dim-order-p r (car rest) rowtol)))
      (setq pre  (cons (car rest) pre)
            rest (cdr rest)))
    (setq out (append (reverse pre) (list r) rest)))
  (mapcar '(lambda (r) (nth 3 r)) out))

(defun dchk:dim-meas (ent / ed dtype p13 p14 ang v meas)
  ;; the dimension's current measurement as display text, formatted
  ;; with the drawing's unit settings (LUNITS/AUNITS); nil if unknown.
  ;; Linear/aligned dims are recomputed from their definition points
  ;; so the value reflects any point that was just moved.
  (setq ed    (entget ent)
        dtype (logand 7 (cdr (assoc 70 ed)))
        meas  (cdr (assoc 42 ed)))            ; stored actual measurement
  (cond
    ((= dtype 1)                              ; aligned: point-to-point
     (setq p13 (cdr (assoc 13 ed))
           p14 (cdr (assoc 14 ed)))
     (if (and p13 p14) (rtos (distance p13 p14))))
    ((= dtype 0)                              ; rotated/linear: project the
     (setq p13 (cdr (assoc 13 ed))            ; points onto the dim direction
           p14 (cdr (assoc 14 ed))
           ang (cdr (assoc 50 ed)))
     (if (and p13 p14)
       (progn
         (if (null ang) (setq ang 0.0))
         (setq v (mapcar '- p14 p13))
         (rtos (abs (+ (* (car v) (cos ang))
                       (* (cadr v) (sin ang))))))))
    ((member dtype '(2 5))                    ; angular: show the angle
     (if (and meas (>= meas 0.0)) (angtos meas)))
    (t                                        ; radius/diameter/ordinate
     (if (and meas (>= meas 0.0)) (rtos meas)))))

(defun dchk:audit-dim-point (ent gcode label cands / ed pt near sugg ans final how)
  ;; audits one definition point: an off-object point is put where it
  ;; looks like it belongs, then you choose - Move (take it), Keep
  ;; (put it back exactly where you drew it) or Pick your own spot.
  ;; Returns (original final how) when the point was looked at, where
  ;; how is 'auto / 'user / 'kept; nil when the point was already fine.
  (setq ed (entget ent)
        pt (cdr (assoc gcode ed)))
  (if pt
    (progn
      (setq near (dchk:nearest-curve pt nil cands))
      (if (and near (> (caddr near) *dchk-tol*))
        (progn
          (setq sugg (cadr near))
          ;; show the suggestion in place, but keep the original spot
          ;; marked so both are on screen while the question is asked
          (entmod (subst (cons gcode sugg) (assoc gcode ed) ed))
          (entupd ent)
          (princ (strcat "\n  " label " is not on any object - nearest one is "
                         (rtos (caddr near) 2 4) " away."))
          (setq ans (dchk:confirm-move label pt sugg))
          (cond
            ((eq ans 'move)
             (setq final sugg
                   how   'auto)
             (princ (strcat "\n  " label " MOVED onto the nearest object, "
                            (dchk:ptstr final) ".")))
            ((eq ans 'keep)
             (setq ed    (entget ent)
                   final pt
                   how   'kept)
             (entmod (subst (cons gcode pt) (assoc gcode ed) ed))
             (entupd ent)
             (princ (strcat "\n  " label " KEPT where you drew it, "
                            (dchk:ptstr final) " - nothing changed.")))
            (t
             (setq final (trans ans 1 0)
                   how   'user
                   ed    (entget ent))
             (entmod (subst (cons gcode final) (assoc gcode ed) ed))
             (entupd ent)
             (princ (strcat "\n  " label " moved to the spot you picked, "
                            (dchk:ptstr final) "."))))
          (redraw)
          (list pt final how))))))

(defun dchk:review-dim (ent cands num total / ed dtype h sty p13 p14 r1 r2
                                              looked moved kept ok note meas assocnote)
  ;; interactive review of one dimension.
  ;; Returns (handle ok-flag report-note moved-point-count measurement).
  (setq ed    (entget ent)
        h     (cdr (assoc 5 ed))
        sty   (dchk:dim-style ent)
        dtype (logand 7 (cdr (assoc 70 ed))))
  (dchk:zoom-ent ent)
  (redraw ent 3)
  (princ (strcat "\n\nDimension " (itoa num) " of " (itoa total)
                 " (handle " h
                 (if (= sty "") "" (strcat ", style " sty))
                 ")"))
  (if (member dtype '(0 1))                   ; rotated/linear or aligned
    (progn
      (if (dchk:dim-assoc-p ent)
        (princ "\n  Note: this dimension is object-associative - a moved point may re-anchor on its own."))
      (setq p13 (cdr (assoc 13 ed))           ; the two dimmed points
            p14 (cdr (assoc 14 ed))
            r1  (dchk:audit-dim-point ent 13 "dimension point 1" cands)
            r2  (dchk:audit-dim-point ent 14 "dimension point 2" cands))))
  (setq looked (append (if r1 (list r1)) (if r2 (list r2)))
        moved  (vl-remove-if '(lambda (x) (eq (caddr x) 'kept)) looked)
        kept   (vl-remove-if-not '(lambda (x) (eq (caddr x) 'kept)) looked))
  ;; only when something actually moved is there an old position worth
  ;; drawing a construction line through
  (if moved (dchk:make-xline p13 p14))        ; through the ORIGINAL points
  (if (and moved (dchk:dim-assoc-p ent))
    (setq assocnote " (ASSOCIATIVE - verify the moved point holds)"))
  (setq meas (dchk:dim-meas ent))             ; after any point moves
  (if meas (princ (strcat "\n  Measures " meas ".")))
  (redraw ent 3)
  (setq ok (cal:ask-yn-nav "\n  Is this dimension correct?"))
  (redraw ent 4)
  (redraw)
  (if (member ok '(back skip))
    (list h ok nil (length moved) meas)       ; navigation: caller handles it
    (progn
      (setq ok (eq ok 'yes))
      (setq note (strcat
                   (if ok "OK" "FLAGGED to fix (red)")
                   (if moved
                     (strcat " - " (itoa (length moved))
                             " point(s) moved onto the nearest object")
                     "")
                   (if kept
                     (strcat " - " (itoa (length kept))
                             " point(s) kept where you drew them")
                     "")
                   (if assocnote assocnote "")))
      (if (not ok) (dchk:set-color ent *dchk-flag-color*))
      (list h ok note (length moved) meas))))

;; --- arc review ----------------------------------------------------

(defun dchk:arc-end-target (ent which cands / p other near ends target)
  ;; where the attachment audit says this endpoint should go;
  ;; nil when the endpoint is already fine (or nothing to attach to)
  (setq p     (if (eq which 'start)
                (vlax-curve-getStartPoint ent)
                (vlax-curve-getEndPoint ent))
        other (if (eq which 'start)
                (vlax-curve-getEndPoint ent)
                (vlax-curve-getStartPoint ent))
        near  (dchk:nearest-curve p ent cands))
  (cond
    ((null near) nil)                         ; nothing to attach to at all
    ((<= (caddr near) *dchk-tol*)             ; endpoint sits on an object...
     (setq ends (dchk:curve-ends (car near)))
     ;; never snap onto the arc's own other endpoint
     (setq ends (vl-remove-if '(lambda (q) (< (distance q other) 1e-8)) ends))
     (cond
       ((null ends) nil)                      ; closed curve: no ends to demand
       ((vl-some '(lambda (q) (<= (distance p q) *dchk-tol*)) ends)
        nil)                                  ; ...and at one of its ends: OK
       (t (dchk:closest-of p ends))))         ; ...but mid-object: closest end
    (t                                        ; floating: closest end anywhere,
     (setq target (dchk:nearest-end p ent cands))
     (if (or (null target) (< (distance target other) 1e-8))
       (cadr near)                            ; else closest point on closest object
       target))))

(defun dchk:arc-state (ent / ed)
  ;; the groups that define an arc's shape, for an exact put-it-back
  (setq ed (entget ent))
  (list (assoc 10 ed) (assoc 40 ed) (assoc 50 ed) (assoc 51 ed)))

(defun dchk:arc-restore (ent st / ed g)
  ;; restore a saved shape exactly, rather than re-fitting back to it
  (setq ed (entget ent))
  (foreach g st (setq ed (subst g (assoc (car g) ed) ed)))
  (entmod ed)
  (entupd ent))

(defun dchk:review-arc-end (ent which label cands / p target st ans final how)
  ;; audits one arc endpoint: a detached end is snapped where it looks
  ;; like it belongs, then you choose - Move (take it), Keep (put the
  ;; arc back exactly as drawn) or Pick your own spot.
  ;; Returns (original final how) when the end was looked at, where how
  ;; is 'auto / 'user / 'kept; nil when the end was already fine.
  (setq p      (if (eq which 'start)
                 (vlax-curve-getStartPoint ent)
                 (vlax-curve-getEndPoint ent))
        target (dchk:arc-end-target ent which cands)
        st     (dchk:arc-state ent))
  (cond
    (target
     (if (dchk:move-arc-end ent which target)
       (progn
         (princ (strcat "\n  " label " is not attached to an object end - nearest is "
                        (rtos (distance p target) 2 4) " away."))
         (setq ans (dchk:confirm-move label p target))
         (cond
           ((eq ans 'move)
            (setq final target
                  how   'auto)
            (princ (strcat "\n  " label " SNAPPED to the object end, "
                           (dchk:ptstr final) ".")))
           ((eq ans 'keep)
            (dchk:arc-restore ent st)
            (setq final p
                  how   'kept)
            (princ (strcat "\n  " label " KEPT where you drew it, "
                           (dchk:ptstr final) " - the arc is unchanged.")))
           (t
            (setq ans (trans ans 1 0))
            (if (dchk:move-arc-end ent which ans)
              (progn
                (setq final ans
                      how   'user)
                (princ (strcat "\n  " label " moved to the spot you picked, "
                               (dchk:ptstr final) ".")))
              (progn
                (setq final target
                      how   'auto)
                (princ "\n  Could not re-fit the arc through that spot (collinear?); left it on the object end.")))))
         (redraw)
         (list p final how))
       (progn
         (princ (strcat "\n  " label " should attach at " (dchk:ptstr target)
                        " but the arc could not be re-fitted (points collinear?)."))
         nil)))
    (*dchk-ask-all-arc-ends*                  ; optional: confirm attached ends too
     (setq ans (dchk:confirm-move label p p))
     (redraw)
     (if (member ans '(move keep))
       nil
       (progn
         (setq ans (trans ans 1 0))
         (if (dchk:move-arc-end ent which ans)
           (list p ans 'user)
           (progn
             (princ "\n  Could not re-fit the arc through that spot (collinear?); unchanged.")
             nil)))))
    (t nil)))

(defun dchk:review-arc (ent cands num total / ed h planar r1 r2 looked moved kept note)
  ;; interactive review of one arc's endpoints.
  ;; Returns (handle untouched-flag report-note moved-point-count).
  (setq ed     (entget ent)
        h      (cdr (assoc 5 ed))
        planar (dchk:planar-arc-p ed))
  (dchk:zoom-ent ent)
  (redraw ent 3)
  (princ (strcat "\n\nArc " (itoa num) " of " (itoa total)
                 " (handle " h ")"))
  (if planar
    (setq r1 (dchk:review-arc-end ent 'start "arc start point" cands)
          r2 (dchk:review-arc-end ent 'end   "arc end point"   cands))
    (princ "\n  Arc is not in the world XY plane - endpoint audit skipped."))
  (redraw ent 4)
  (redraw)
  (setq looked (append (if r1 (list r1)) (if r2 (list r2)))
        moved  (vl-remove-if '(lambda (x) (eq (caddr x) 'kept)) looked)
        kept   (vl-remove-if-not '(lambda (x) (eq (caddr x) 'kept)) looked))
  (if moved (dchk:set-color ent *dchk-arc-color*))
  (setq note (cond
               ((not planar) "not in world XY plane - skipped")
               ((and moved kept)
                (strcat (itoa (length moved)) " endpoint(s) moved (magenta), "
                        (itoa (length kept)) " kept where you drew them"))
               (moved (strcat (itoa (length moved))
                              " endpoint(s) moved (magenta)"))
               (kept (strcat (itoa (length kept))
                             " endpoint(s) kept where you drew them"))
               (t "endpoints OK")))
  (list h (null moved) note (length moved)))

;; --- overlapping line review ---------------------------------------

(defun dchk:review-olap (la lb num total / info ea eb h1 h2 lay1 lay2 label
                                           ans mergeable kinds)
  ;; interactive review of one overlapping segment pair.
  ;; Returns nil when the pair no longer overlaps (an earlier merge
  ;; absorbed it); otherwise (label report-note action ents...) where
  ;; action is merged / flagged / left and ents keep their cyan.
  (setq ea (dchk:seg-ent la)
        eb (dchk:seg-ent lb))
  (if (and (entget ea) (entget eb) (setq info (dchk:overlap-info la lb)))
    (progn
      (setq h1        (cdr (assoc 5 (entget ea)))
            h2        (cdr (assoc 5 (entget eb)))
            lay1      (cdr (assoc 8 (entget ea)))
            lay2      (cdr (assoc 8 (entget eb)))
            mergeable (and (dchk:whole-line-p la)
                           (dchk:whole-line-p lb)
                           (= (strcase lay1) (strcase lay2)))
            kinds     (if (and (dchk:whole-line-p la) (dchk:whole-line-p lb))
                        "lines"
                        "segments")
            label     (strcat h1 "+" h2 " (overlap " (rtos (caddr info)) ")"))
      (dchk:zoom-2ents ea eb)
      (redraw ea 3)
      (redraw eb 3)
      (dchk:mark-point (car info))
      (dchk:mark-point (cadr info))
      (princ (strcat "\n\nOverlap " (itoa num) " of " (itoa total)
                     ": " kinds " " h1 " + " h2
                     " run on top of each other for " (rtos (caddr info)) "."))
      (if mergeable
        (progn
          (initget "Merge Flag Leave")
          (setq ans (getkword
                      "\n  Merge into one line, Flag to fix, or Leave as is? [Merge/Flag/Leave] <Merge>: "))
          (if (null ans) (setq ans "Merge")))
        (progn
          (princ (if (= (strcase lay1) (strcase lay2))
                   "\n  (Polyline edge - cannot be merged automatically.)"
                   (strcat "\n  (Different layers: " lay1 " / " lay2
                           " - cannot be merged automatically.)")))
          (initget "Flag Leave")
          (setq ans (getkword
                      "\n  Flag to fix, or Leave as is? [Flag/Leave] <Flag>: "))
          (if (null ans) (setq ans "Flag"))))
      (redraw ea 4)
      (redraw eb 4)
      (redraw)
      (cond
        ((= ans "Merge")
         (dchk:merge-lines la lb info)
         (dchk:set-color ea *dchk-olap-color*)
         (princ "\n  Merged into one line (cyan).")
         (list label "merged into one line (cyan)" 'merged ea))
        ((= ans "Flag")
         (dchk:set-color ea *dchk-olap-color*)
         (dchk:set-color eb *dchk-olap-color*)
         (princ "\n  Flagged to fix (cyan).")
         (list label
               (if (dchk:whole-line-p la)
                 (if (= (strcase lay1) (strcase lay2))
                   "flagged to fix (cyan)"
                   "different layers - flagged to fix (cyan)")
                 "polyline edge - flagged to fix (cyan)")
               'flagged ea eb))
        (t
         (princ "\n  Left as drawn.")
         (list label "left as drawn" 'left))))))

(defun c:DIMCHECK ( / *error* oldecho vc vs undo-open ss i e et
                      cands dims arcs lns plns segs olaps rest e1 e2 pr
                      saved keep res n total lines ans
                      ndok ndflag ndmoved naok namoved nasnap
                      nomerged noflag noleft
                      rowtol sty pair dlines skiprest
                      laylist locked relock lay
                      minx miny maxx maxy bb h m ins txt nlin ref hdr l carried cmv)
  (defun *error* (msg)
    ;; put the greys back (flagged/moved items keep their colour),
    ;; re-lock what we unlocked, clear markers, close the undo group
    (foreach pair saved
      (if (and (not (member (car pair) keep)) (entget (car pair)))
        (dchk:set-color (car pair) (cdr pair))))
    (foreach l relock (dchk:set-layer-lock l T))
    (redraw)
    (if undo-open
      (progn (setvar "CMDECHO" 0) (command "_.UNDO" "_End")))
    (if oldecho (setvar "CMDECHO" oldecho))
    (if (and msg (not (wcmatch (strcase msg) "*BREAK*,*CANCEL*,*QUIT*,*EXIT*")))
      (princ (strcat "\nDIMCHECK error: " msg)))
    (princ))

  (prompt "\nHighlight the drawing to DIMCHECK: ")
  (setq ss (ssget))
  (cond
    ((null ss)
     (prompt "\nNothing selected - DIMCHECK cancelled."))
    (t
     (setq cands nil dims nil arcs nil lns nil segs nil
           saved nil keep nil lines nil i 0
           ndok 0 ndflag 0 ndmoved 0 naok 0 namoved 0 nasnap 0
           nomerged 0 noflag 0 noleft 0)
     (repeat (sslength ss)
       (setq e  (ssname ss i)
             i  (1+ i)
             et (cdr (assoc 0 (entget e))))
       (if (= et "DIMENSION") (setq dims (cons e dims)))
       (if (= et "ARC") (setq arcs (cons e arcs)))
       (if (= et "LINE") (setq lns (cons e lns)))
       (if (member et '("LINE" "LWPOLYLINE" "POLYLINE"))
         (setq plns (cons e plns)))
       (if (member et *dchk-curve-types*) (setq cands (cons e cands))))
     (setq dims  (reverse dims)
           arcs  (reverse arcs)
           lns   (reverse lns)
           plns  (reverse plns)
           cands (reverse cands)
           ;; overlap detection runs on segments, so a run of lines
           ;; drawn as one polyline counts like separate lines
           segs  (dchk:collect-segs plns))
     (cond
       ((and (null dims) (null arcs) (< (length segs) 2))
        (prompt "\nSelection holds no dimensions, arcs, or lines to check - nothing to do."))
       (t
        (setq oldecho (getvar "CMDECHO"))
        (setvar "CMDECHO" 0)
        (setq vc (getvar "VIEWCTR")
              vs (getvar "VIEWSIZE"))
        (command "_.UNDO" "_Begin")
        (setq undo-open T)
        (cal:ensure-layer *dchk-constr-layer* *dchk-constr-color*)
        (cal:ensure-layer *dchk-report-layer* *dchk-report-color*)

        ;; a locked layer swallows every fix and recolour silently -
        ;; surface that up front and offer to unlock for the run
        (setq laylist nil relock nil i 0)
        (repeat (sslength ss)
          (setq lay (cdr (assoc 8 (entget (ssname ss i))))
                i   (1+ i))
          (if (and lay (not (member lay laylist)))
            (setq laylist (cons lay laylist))))
        (setq locked (vl-remove-if-not 'dchk:layer-locked-p laylist))
        (if locked
          (if (cal:ask-yn
                (strcat "\n" (itoa (length locked))
                        " locked layer(s) in the selection ("
                        (dchk:join locked ", ")
                        ") - DIMCHECK cannot recolour or fix anything on them. Unlock for this run?")
                "Yes")
            (progn
              (foreach l locked (dchk:set-layer-lock l nil))
              (setq relock locked)
              (princ "\n  Unlocked; they will be re-locked when the run ends."))
            (princ "\n  Locked layers stay locked - items on them are reported but left untouched.")))

        ;; a rerun replaces the previous run's report and markers
        (dchk:clear-old)

        ;; extents of the selection (report goes to the right of them)
        (setq i 0)
        (repeat (sslength ss)
          (setq e  (ssname ss i)
                i  (1+ i)
                bb (cal:bbox-ent e))
          (if bb
            (setq minx (if minx (min minx (caar bb)) (caar bb))
                  miny (if miny (min miny (cadar bb)) (cadar bb))
                  maxx (if maxx (max maxx (caadr bb)) (caadr bb))
                  maxy (if maxy (max maxy (cadadr bb)) (cadadr bb)))))

        ;; march order for the dimensions: style groups first
        ;; (*dchk-style-order*), then row by row, left to right
        (setq rowtol (if (and miny maxy (> (- maxy miny) 1e-8))
                       (* 0.05 (- maxy miny))
                       1.0))
        (setq dims (dchk:sort-dims dims rowtol))

        ;; grey out the whole selection so each item can take the
        ;; stage, stashing every original colour in xdata first so
        ;; DIMCHECKRESCUE can recover them even after a crash
        (setq i 0)
        (repeat (sslength ss)
          (setq e (ssname ss i)
                i (1+ i))
          (if (entget e)
            (progn
              (setq saved (cons (cons e (dchk:ent-color e)) saved))
              (dchk:stash-color e (dchk:ent-color e))
              (dchk:set-color e *dchk-grey-color*))))

        ;; --- dimensions, one at a time -----------------------------
        (if dims
          (princ (strcat "\n--- Reviewing " (itoa (length dims))
                         " dimension(s): Enter = correct, N = flag to fix, "
                         "B = back one, S = skip the rest ---")))
        ;; index-based so Back can step to the previous dimension and
        ;; Skip can leave the rest unreviewed without losing the report
        (setq n 0 total (length dims) dlines nil skiprest nil)
        (while (and (< n total) (not skiprest))
          (setq e   (nth n dims)
                res nil)
          (dchk:set-color e (cdr (assoc e saved)))       ; step into the light
          (setq res (dchk:review-dim e cands (1+ n) total))
          ;; points already moved count however the prompt was answered
          (setq ndmoved (+ ndmoved (cadddr res)))
          (cond
            ((eq (cadr res) 'skip)
             (dchk:set-color e *dchk-grey-color*)
             (setq skiprest T)
             (princ (strcat "\n  Skipping the remaining "
                            (itoa (- total n)) " dimension(s).")))
            ((eq (cadr res) 'back)
             ;; undo what the previous item recorded, then redo it
             (dchk:set-color e *dchk-grey-color*)
             (if (> n 0)
               (progn
                 (setq n  (1- n)
                       e1 (nth n dims))
                 (if (car dlines)                        ; roll back its tally
                   (progn
                     (if (cadr (car dlines))
                       (setq ndok (1- ndok))
                       (setq ndflag (1- ndflag)))
                     ;; A MOVED POINT STAYS MOVED.  Back re-asks the
                     ;; question; it does not put the point back, and
                     ;; its construction line is still standing.  So
                     ;; the move is CARRIED to the re-review, not
                     ;; un-counted -- subtracting it made the report
                     ;; claim "points adjusted: 0" over a drawing
                     ;; whose points really had been adjusted, and
                     ;; the rebuilt line lost its "moved" note with
                     ;; it (the second pass finds them attached and
                     ;; has nothing to report).
                     (if (> (caddr (car dlines)) 0)
                       (setq carried (cons (cons e1 (caddr (car dlines)))
                                           (vl-remove (assoc e1 carried)
                                                      carried))))
                     (setq dlines (cdr dlines))))
                 (setq keep (vl-remove e1 keep))
                 (dchk:set-color e1 *dchk-grey-color*)
                 (princ "\n  Stepping back one dimension."))
               (princ "\n  Already at the first dimension."))
             (setq n (1- n)))                            ; loop's 1+ re-enters it
            (t
             (if (cadr res)
               (progn (setq ndok (1+ ndok))
                      (dchk:set-color e *dchk-grey-color*))
               (progn (setq ndflag (1+ ndflag))
                      (setq keep (cons e keep))))
             (setq sty (dchk:dim-style e))
             ;; moves this dim collected on an earlier pass, before a
             ;; Back sent us round again -- they are real and belong
             ;; in both the line and the tally
             (setq cmv (cond ((cdr (assoc e carried))) (0)))
             (setq dlines (cons (list (strcat "Dim " (car res)
                                              (if (= sty "") "" (strcat " [" sty "]"))
                                              (if (nth 4 res)
                                                (strcat " = " (nth 4 res))
                                                "")
                                              ": " (caddr res)
                                              (if (> cmv 0)
                                                (strcat " - " (itoa cmv)
                                                        " point(s) moved before"
                                                        " you stepped back")
                                                ""))
                                      (cadr res)
                                      (+ (cadddr res) cmv))
                                dlines))))
          (setq n (1+ n)))
        (if skiprest
          (setq lines (cons (strcat "Dimensions: " (itoa (- total (length dlines)))
                                    " left UNREVIEWED (skipped by user)")
                            lines)))
        (foreach pair (reverse dlines)
          (setq lines (cons (car pair) lines)))

        ;; --- arcs, one endpoint at a time --------------------------
        (if arcs
          (princ (strcat "\n--- Reviewing " (itoa (length arcs))
                         " arc(s): checking endpoint attachment ---")))
        (setq n 0 total (length arcs))
        (foreach e arcs
          (setq n (1+ n))
          (dchk:set-color e (cdr (assoc e saved)))
          (setq res (dchk:review-arc e cands n total))
          (setq nasnap (+ nasnap (cadddr res)))
          (if (cadr res)
            (progn (setq naok (1+ naok))
                   (dchk:set-color e *dchk-grey-color*))
            (progn (setq namoved (1+ namoved))
                   (setq keep (cons e keep))))           ; moved: stays magenta
          (setq lines (cons (strcat "Arc " (car res) ": " (caddr res)) lines)))

        ;; --- overlapping lines, one pair at a time ------------------
        (setq olaps (dchk:find-overlaps segs))
        (if olaps
          (princ (strcat "\n--- Reviewing " (itoa (length olaps))
                         " overlapping line pair(s): Enter = merge, F = flag, L = leave ---")))
        (setq n 0 total (length olaps))
        (foreach pr olaps
          (setq n  (1+ n)
                e1 (dchk:seg-ent (car pr))
                e2 (dchk:seg-ent (cadr pr)))
          (dchk:stage e1 saved keep)
          (dchk:stage e2 saved keep)
          (setq res (dchk:review-olap (car pr) (cadr pr) n total))
          (cond
            ((null res)                       ; absorbed by an earlier merge
             (dchk:unstage e1 keep)
             (dchk:unstage e2 keep))
            ((eq (caddr res) 'left)
             (setq noleft (1+ noleft))
             (dchk:unstage e1 keep)
             (dchk:unstage e2 keep)
             (setq lines (cons (strcat "Lines " (car res) ": " (cadr res)) lines)))
            (t
             (if (eq (caddr res) 'merged)
               (setq nomerged (1+ nomerged))
               (setq noflag (1+ noflag)))
             (setq keep (append (cdddr res) keep))
             (setq lines (cons (strcat "Lines " (car res) ": " (cadr res)) lines)))))
        ;; --- restore colours (flagged/moved keep theirs) ------------
        ;; restored entities drop their rescue stash; flagged/moved
        ;; ones keep it so DIMCHECKRESCUE can clear the marks later
        (foreach pair saved
          (if (and (not (member (car pair) keep)) (entget (car pair)))
            (progn
              (dchk:set-color (car pair) (cdr pair))
              (dchk:unstash (car pair)))))
        (foreach l relock (dchk:set-layer-lock l T))
        (setq relock nil)

        ;; --- report on the right side, to scale with the drawing ----
        ;; text height picked from the drawing's extents so the whole
        ;; report roughly matches the drawing's height (MTEXT line
        ;; spacing is ~1.66 x text height), clamped so a short report
        ;; is not gigantic nor a long one unreadably small
        ;; all-clear lines are shorter, so weight them when sizing
        (setq nlin 3.0)                          ; title, legend, separator
        (foreach l lines
          (setq nlin (+ nlin (if (dchk:attn-p l) 1.0 *dchk-green-scale*))))
        (setq nlin (+ nlin (* 3.0 *dchk-green-scale*)))   ; the header dashboard
        (if (and minx (> (max (- maxy miny) (- maxx minx)) 1e-8))
          (progn
            (setq ref (max (- maxy miny) (* 0.25 (- maxx minx)))
                  h   (/ ref (* 1.66 nlin)))
            (if (> h (/ ref 30.0))  (setq h (/ ref 30.0)))
            (if (< h (/ ref 200.0)) (setq h (/ ref 200.0))))
          (progn
            (setq h (* (getvar "DIMTXT") (getvar "DIMSCALE")))
            (if (or (null h) (<= h 0.0)) (setq h 2.5))))
        (setq ins (if minx
                    (list (+ maxx (* 0.05 (max (- maxx minx) 1.0))) maxy 0.0)
                    (list 0.0 0.0 0.0)))
        ;; header dashboard: each line carries a "needs attention" flag
        ;; so a category with anything to look over turns red
        (setq hdr
          (list
            (cons (strcat "Dimensions checked: " (itoa (length dims))
                          " (correct: " (itoa ndok)
                          ", flagged to fix: " (itoa ndflag)
                          ", points adjusted: " (itoa ndmoved) ")")
                  (> ndflag 0))
            (cons (strcat "Arcs checked: " (itoa (length arcs))
                          " (OK: " (itoa naok)
                          ", with endpoints moved: " (itoa namoved)
                          ", endpoints moved in total: " (itoa nasnap) ")")
                  (> namoved 0))
            (cons (strcat "Overlapping line pairs: " (itoa (length olaps))
                          (if olaps
                            (strcat " (merged: " (itoa nomerged)
                                    ", flagged: " (itoa noflag)
                                    ", left as drawn: " (itoa noleft) ")")
                            " - none found"))
                  (> noflag 0))))
        (setq txt (strcat "DIMCHECK REPORT - " (cal:datestr)
                          "  [DIMCHECK " *dchk-version* "]"
                          "\\P"
                          (dchk:small
                            (strcat "Items needing attention are shown in "
                                    (dchk:red "red") ", larger than the rest."))))
        (foreach pr hdr
          (setq txt (strcat txt "\\P"
                            (if (cdr pr)
                              (dchk:red (car pr))
                              (dchk:small (car pr))))))
        (setq txt (strcat txt "\\P"
                          (dchk:small "----------------------------------------")))
        (foreach l (reverse lines)
          (setq txt (strcat txt "\\P"
                            (if (dchk:attn-p l) (dchk:red l) (dchk:small l)))))
        (dchk:mtext ins h (* *dchk-report-chars* h) txt *dchk-report-layer*)

        ;; --- show the drawing plus the report -----------------------
        (if minx
          (progn
            (setq m (* 0.05 (max (- maxx minx) (- maxy miny) 1.0)))
            (command "_.ZOOM" "_Window"
                     (trans (list (- minx m) (- miny m) 0.0) 0 1)
                     (trans (list (+ (car ins) (* *dchk-report-chars* h) m)
                                  (+ maxy m) 0.0)
                            0 1)))
          (command "_.ZOOM" "_Center" vc vs))

        (command "_.UNDO" "_End")
        (setq undo-open nil)
        (setvar "CMDECHO" oldecho)
        (princ (strcat "\n\n--- DIMCHECK complete ---"
                       "\nDimensions: " (itoa (length dims)) " checked, "
                       (itoa ndok) " correct, "
                       (itoa ndflag) " flagged to fix (red)"
                       (if (> ndmoved 0)
                         (strcat ", " (itoa ndmoved) " point(s) adjusted")
                         "")
                       "\nArcs: " (itoa (length arcs)) " checked, "
                       (itoa namoved) " with endpoint(s) moved ("
                       (itoa nasnap) " endpoint(s), magenta)"
                       "\nOverlapping lines: " (itoa (length olaps)) " pair(s) found"
                       (if olaps
                         (strcat ", " (itoa nomerged) " merged, "
                                 (itoa noflag) " flagged (cyan), "
                                 (itoa noleft) " left as drawn")
                         "")
                       "\nReport placed on the right side of the drawing (layer "
                       *dchk-report-layer* ")."
                       (if (> ndmoved 0)
                         (strcat "\nConstruction lines through moved dimensions' original points are on layer "
                                 *dchk-constr-layer* ".")
                         "")
                       "\nOne UNDO reverts everything DIMCHECK changed (including the report)."))))))
  (princ))

;; --- DIMSCAN: the read-only twin -----------------------------------
;;  Runs every audit, asks nothing, and changes nothing in the drawing
;;  except writing the report. Use it as a quick pre-flight, or when
;;  you want the findings without touching a released sheet.

(defun c:DIMSCAN ( / *error* oldecho ss i e et ed cands dims arcs plns segs
                     lines olaps pr
                     nd ndbad na nabad h m ins txt nlin ref hdr l
                     minx miny maxx maxy bb p13 p14 near s bad w)
  (defun *error* (msg)
    (if oldecho (setvar "CMDECHO" oldecho))
    (if (and msg (not (wcmatch (strcase msg) "*BREAK*,*CANCEL*,*QUIT*,*EXIT*")))
      (princ (strcat "\nDIMSCAN error: " msg)))
    (princ))

  (prompt "\nHighlight the drawing to DIMSCAN (Enter = whole drawing): ")
  (setq ss (ssget))
  (if (null ss) (setq ss (ssget "_X")))
  (cond
    ((null ss) (prompt "\nNothing to scan."))
    (t
     (setq oldecho (getvar "CMDECHO"))
     (setvar "CMDECHO" 0)
     (setq i 0 nd 0 ndbad 0 na 0 nabad 0)
     (repeat (sslength ss)
       (setq e  (ssname ss i)
             i  (1+ i)
             et (cdr (assoc 0 (entget e))))
       (if (= et "DIMENSION") (setq dims (cons e dims)))
       (if (= et "ARC") (setq arcs (cons e arcs)))
       (if (member et '("LINE" "LWPOLYLINE" "POLYLINE")) (setq plns (cons e plns)))
       (if (member et *dchk-curve-types*) (setq cands (cons e cands)))
       (setq bb (cal:bbox-ent e))
       (if bb
         (setq minx (if minx (min minx (caar bb)) (caar bb))
               miny (if miny (min miny (cadar bb)) (cadar bb))
               maxx (if maxx (max maxx (caadr bb)) (caadr bb))
               maxy (if maxy (max maxy (cadadr bb)) (cadadr bb)))))
     (setq dims (reverse dims) arcs (reverse arcs)
           plns (reverse plns) cands (reverse cands)
           segs (dchk:collect-segs plns))

     ;; --- dimensions: report stray definition points, move nothing
     (foreach e (dchk:sort-dims dims (if (and miny maxy) (* 0.05 (- maxy miny)) 1.0))
       (setq ed  (entget e)
             nd  (1+ nd)
             p13 (cdr (assoc 13 ed))
             p14 (cdr (assoc 14 ed))
             bad nil)
       (if (member (logand 7 (cdr (assoc 70 ed))) '(0 1))
         (foreach s (list (cons "point 1" p13) (cons "point 2" p14))
           (if (cdr s)
             (progn
               (setq near (dchk:nearest-curve (cdr s) nil cands))
               (if (and near (> (caddr near) *dchk-tol*))
                 (setq bad (append bad (list (strcat (car s) " off by "
                                                     (rtos (caddr near) 2 4))))))))))
       (if bad (setq ndbad (1+ ndbad)))
       (setq lines (cons (strcat "Dim " (cdr (assoc 5 ed))
                                 (if (= (dchk:dim-style e) "") ""
                                   (strcat " [" (dchk:dim-style e) "]"))
                                 (if (dchk:dim-meas e)
                                   (strcat " = " (dchk:dim-meas e)) "")
                                 ": "
                                 (if bad
                                   (strcat "NOT attached - " (dchk:join bad ", "))
                                   "OK")
                                 (if (dchk:dim-assoc-p e) " (associative)" ""))
                         lines)))

     ;; --- arcs: report unattached endpoints, move nothing
     (foreach e arcs
       (setq na  (1+ na)
             bad nil)
       (if (dchk:planar-arc-p (entget e))
         (foreach s '(("start" . start) ("end" . end))
           (if (dchk:arc-end-target e (cdr s) cands)
             (setq bad (append bad (list (car s)))))))
       (if bad (setq nabad (1+ nabad)))
       (setq lines (cons (strcat "Arc " (cdr (assoc 5 (entget e))) ": "
                                 (if bad
                                   (strcat (dchk:join bad " & ")
                                           " NOT attached to an object end")
                                   "endpoints OK"))
                         lines)))

     ;; --- overlaps
     (setq olaps (dchk:find-overlaps segs))
     (foreach pr olaps
       (setq lines (cons (strcat "Lines "
                                 (cdr (assoc 5 (entget (dchk:seg-ent (car pr)))))
                                 "+"
                                 (cdr (assoc 5 (entget (dchk:seg-ent (cadr pr)))))
                                 ": OVERLAP of "
                                 (rtos (caddr (dchk:overlap-info (car pr) (cadr pr))))
                                 " - flagged")
                         lines)))

     ;; --- report (the only thing DIMSCAN writes) ------------------
     (cal:ensure-layer *dchk-report-layer* *dchk-report-color*)
     (dchk:clear-old)
     (setq hdr (list
                 (cons (strcat "Dimensions scanned: " (itoa nd) " ("
                               (itoa ndbad) " with a stray definition point)")
                       (> ndbad 0))
                 (cons (strcat "Arcs scanned: " (itoa na) " ("
                               (itoa nabad) " with an unattached end)")
                       (> nabad 0))
                 (cons (strcat "Overlapping line pairs: " (itoa (length olaps)))
                       (> (length olaps) 0))))
     (setq nlin 3.0)
     (foreach l lines
       (setq nlin (+ nlin (if (dchk:attn-p l) 1.0 *dchk-green-scale*))))
     (setq nlin (+ nlin (* 3.0 *dchk-green-scale*)))
     (if (and minx (> (max (- maxy miny) (- maxx minx)) 1e-8))
       (progn
         (setq ref (max (- maxy miny) (* 0.25 (- maxx minx)))
               h   (/ ref (* 1.66 nlin)))
         (if (> h (/ ref 30.0))  (setq h (/ ref 30.0)))
         (if (< h (/ ref 200.0)) (setq h (/ ref 200.0))))
       (setq h 2.5))
     (setq ins (if minx
                 (list (+ maxx (* 0.05 (max (- maxx minx) 1.0))) maxy 0.0)
                 (list 0.0 0.0 0.0)))
     (setq txt (strcat "DIMSCAN REPORT - " (cal:datestr)
                       "  [DIMCHECK " *dchk-version* "]"
                       "\\P"
                       (dchk:small (strcat "Read-only scan - nothing in the drawing was changed. "
                                           "Items needing attention are shown in "
                                           (dchk:red "red") "."))))
     (foreach pr hdr
       (setq txt (strcat txt "\\P" (if (cdr pr) (dchk:red (car pr))
                                     (dchk:small (car pr))))))
     (setq txt (strcat txt "\\P" (dchk:small "----------------------------------------")))
     (foreach l (reverse lines)
       (setq txt (strcat txt "\\P" (if (dchk:attn-p l) (dchk:red l) (dchk:small l)))))
     (dchk:mtext ins h (* *dchk-report-chars* h) txt *dchk-report-layer*)
     (setvar "CMDECHO" oldecho)
     (princ (strcat "\n--- DIMSCAN complete (read-only) ---"
                    "\nDimensions: " (itoa nd) " scanned, " (itoa ndbad) " with a stray point"
                    "\nArcs: " (itoa na) " scanned, " (itoa nabad) " with an unattached end"
                    "\nOverlapping line pairs: " (itoa (length olaps))
                    "\nReport written on layer " *dchk-report-layer*
                    "; nothing else was changed."))))
  (princ))

;; --- TUTORIALDIMCHECK: learn it two ways ---------------------------
;;  List  - every check spelled out, at the command line and (if you
;;          want) dropped into the drawing as a reference sheet.
;;  Demo  - draws a small practice drawing with faults planted in it,
;;          walks you through each one showing what DIMCHECK sees and
;;          what the colours mean, then scans it so you see a report.
;;  Both  - the list, then the demo.
;;  Everything the demo draws is in one UNDO group and can be erased
;;  when you are done, so it never touches your real work.
(defun dchk:tut-checklist ()
  (list
    "WHAT DIMCHECK CHECKS"
    ""
    "1. DIMENSIONS - one at a time"
    (strcat "   Order: style groups " (dchk:join *dchk-style-order* " > ")
            " > anything else,")
    "     then left to right, top to bottom inside each group."
    "   Every other object greys out; the one under review is zoomed to."
    "   A definition point not touching any object: you choose"
    "     Move (green +, onto the nearest object) / Keep (red X, exactly"
    "     where you drew it) / Pick your own spot."
    "   Then 'Is this dimension correct?'  Enter = yes,  N = flag it RED,"
    "     B = back one dimension,  S = skip the rest."
    "   The measured distance is shown, and object-associative dims are"
    "     called out (a moved point can re-anchor itself)."
    ""
    "2. ARCS - one endpoint at a time"
    "   Each end must sit at the END of another object; a loose one gets"
    "     the same Move / Keep / Pick choice. Keep restores the arc"
    "     exactly. Arcs that changed turn MAGENTA."
    ""
    "3. OVERLAPPING LINES"
    "   Collinear geometry running on top of itself, in LINEs and in"
    "     polyline edges. Touching end-to-end is fine and is not"
    "     reported. Per pair: Merge into one / Flag CYAN / Leave."
    "     Merge is offered only for two whole LINEs on one layer."
    ""
    "4. THE REPORT"
    "   An MTEXT sheet to the right of the drawing, sized to scale with"
    (strcat "     it. Problems in RED at full size; all-clear in green at "
            (rtos (* 100.0 *dchk-green-scale*) 2 0) "%.")
    ""
    "COMMANDS"
    "   DIMCHECK         the full interactive review (fixes things)"
    "   DIMSCAN          the same audits, read-only - changes nothing"
    "   DIMCHECKRESCUE   put back every colour, remove the markers"
    "   DIMCHECKVER      which build is loaded"
    "   TUTORIALDIMCHECK this tutorial"
    ""
    "GOOD HABITS"
    "   Run DIMSCAN first if you want to look before anything is"
    "     touched. One U undoes an entire DIMCHECK run. Need steps,"
    "     wall height, the liner pattern or the title block border"
    "     checked too? Load linfincheck.lsp and run LINFINCHECK -"
    "     it shares this tool's review and report machinery."))

(defun dchk:tut-pause (msg)
  (princ (strcat "\n  " msg))
  (getstring "\n  --- press Enter to continue ---")
  (princ))

(defun dchk:tut-line (p1 p2 lay)
  (entmake (list '(0 . "LINE") '(100 . "AcDbEntity") (cons 8 lay)
                 '(100 . "AcDbLine") (cons 10 p1) (cons 11 p2)))
  (entlast))

(defun dchk:tut-dim (p1 p2 dimpt rot / old res)
  ;; a linear dimension, made with the command so it is valid in any
  ;; release; osnap is muted so the picks land exactly where told
  (setq old (getvar "OSMODE"))
  (setvar "OSMODE" 0)
  (if (zerop rot)
    (command "_.DIMLINEAR" p1 p2 "_H" dimpt)
    (command "_.DIMLINEAR" p1 p2 "_V" dimpt))
  (setvar "OSMODE" old)
  (entlast))

(defun dchk:tut-demo (/ org ox oy made e ss2 i)
  (princ "\n\n--- DEMO: a practice drawing with faults planted in it ---")
  (setq org (getpoint "\n  Pick an empty spot for the practice drawing: "))
  (if (null org)
    (princ "\n  Cancelled - nothing drawn.")
    (progn
      (setq org (trans org 1 0)
            ox  (car org)
            oy  (cadr org)
            made nil)

      ;; --- fault 1: two lines overlapping ------------------------
      (setq made (cons (dchk:tut-line (list ox oy 0.0)
                                      (list (+ ox 100.0) oy 0.0) "0") made))
      (setq made (cons (dchk:tut-line (list (+ ox 60.0) oy 0.0)
                                      (list (+ ox 180.0) oy 0.0) "0") made))
      (command "_.ZOOM" "_Object" (car made) "")
      (command "_.ZOOM" "_0.4x")
      (dchk:tut-pause
        (strcat "FAULT 1 - overlapping lines.\n  Two lines run on top of each other from "
                "60 to 100: someone drew over\n  an existing line to carry on and never cleaned it up. "
                "DIMCHECK\n  shows the overlap marked at both ends and offers Merge / Flag /\n"
                "  Leave. Lines that merely TOUCH end to end are fine and are\n  never reported."))

      ;; --- fault 2: a dim whose point misses the line -------------
      (setq made (cons (dchk:tut-line (list ox (+ oy 80.0) 0.0)
                                      (list (+ ox 120.0) (+ oy 80.0) 0.0) "0") made))
      (setq e (dchk:tut-dim (list ox (+ oy 80.0) 0.0)
                            (list (+ ox 120.0) (+ oy 88.0) 0.0)   ; 8 units OFF the line
                            (list (+ ox 60.0) (+ oy 110.0) 0.0) 0))
      (if e (setq made (cons e made)))
      (command "_.ZOOM" "_Window"
               (trans (list (- ox 20.0) (+ oy 50.0) 0.0) 0 1)
               (trans (list (+ ox 150.0) (+ oy 130.0) 0.0) 0 1))
      (dchk:tut-pause
        (strcat "FAULT 2 - a dimension point off the geometry.\n"
                "  The right-hand point of this dimension sits 8 units above the\n"
                "  line, so it is not measuring the line at all. DIMCHECK marks\n"
                "  BOTH spots - a RED X where you drew it, a GREEN + where it\n"
                "  belongs - and lets you Move it, Keep it exactly as drawn, or\n"
                "  Pick a spot yourself. Answer N to the 'is this correct?'\n"
                "  question and the whole dimension turns RED to fix later."))

      ;; --- fault 3: an arc floating free --------------------------
      (entmake (list '(0 . "ARC") '(100 . "AcDbEntity") '(8 . "0")
                     '(100 . "AcDbCircle")
                     (cons 10 (list (+ ox 220.0) (+ oy 40.0) 0.0))
                     (cons 40 30.0) '(100 . "AcDbArc")
                     (cons 50 0.0) (cons 51 pi)))
      (setq made (cons (entlast) made))
      (command "_.ZOOM" "_Window"
               (trans (list (+ ox 175.0) (- oy 10.0) 0.0) 0 1)
               (trans (list (+ ox 265.0) (+ oy 90.0) 0.0) 0 1))
      (dchk:tut-pause
        (strcat "FAULT 3 - an arc that attaches to nothing.\n"
                "  Both ends of this arc float free. DIMCHECK wants every arc end\n"
                "  to land on the END of another object, so it offers to snap\n"
                "  each one - again with Move / Keep / Pick. An arc whose ends\n"
                "  actually moved turns MAGENTA so you can spot it afterwards."))

      ;; --- and now the report ------------------------------------
      (setq ss2 (ssadd))
      (foreach e made (if (entget e) (ssadd e ss2)))
      (command "_.ZOOM" "_Window"
               (trans (list (- ox 40.0) (- oy 40.0) 0.0) 0 1)
               (trans (list (+ ox 300.0) (+ oy 230.0) 0.0) 0 1))
      (princ (strcat "\n  " (itoa (sslength ss2))
                     " practice objects drawn. What DIMCHECK would say about"
                     "\n  them is easiest to see as a report."))
      (if (cal:ask-yn "\n  Write a read-only DIMSCAN report for the practice drawing?" "Yes")
        (progn
          (princ "\n  Running DIMSCAN - it changes nothing, it only reports.")
          (princ "\n  (In the report, RED lines at full size are the problems;")
          (princ "\n   green lines at three-quarter size are the all-clears.)")
          (dchk:tut-pause
            (strcat "DIMSCAN will ask you to highlight - window the practice\n"
                    "  drawing (or press Enter for the whole drawing). The report\n"
                    "  lands to the right of whatever you highlight."))
          (c:DIMSCAN)))
      (if (cal:ask-yn "\n  Erase the practice drawing now?" "Yes")
        (progn
          (setq i 0)
          (repeat (sslength ss2)
            (if (entget (ssname ss2 i)) (entdel (ssname ss2 i)))
            (setq i (1+ i)))
          (setq ss2 (ssget "_X" (list (cons 8 *dchk-report-layer*))))
          (if ss2
            (progn
              (setq i 0)
              (repeat (sslength ss2) (entdel (ssname ss2 i)) (setq i (1+ i)))))
          (princ "\n  Practice drawing erased."))
        (princ "\n  Left in place - one U removes the whole tutorial."))
      (princ))))

(defun c:TUTORIALDIMCHECK ( / *error* oldecho undo-open ans l ins h)
  (defun *error* (msg)
    (if undo-open (progn (setvar "CMDECHO" 0) (command "_.UNDO" "_End")))
    (if oldecho (setvar "CMDECHO" oldecho))
    (if (and msg (not (wcmatch (strcase msg) "*BREAK*,*CANCEL*,*QUIT*,*EXIT*")))
      (princ (strcat "\nTUTORIALDIMCHECK error: " msg)))
    (princ))

  (princ (strcat "\n=================================================="
                 "\n  DIMCHECK tutorial   [" *dchk-version* "]"
                 "\n=================================================="))
  ;; the tutorial selector of STANDARDS section 3; the old List stays
  ;; accepted typed in full, hidden
  (initget "Checks Demo Both LIST")
  (setq ans (getkword
              "\n  Read the Checks, Demo them on a practice drawing, or Both? [Checks/Demo/Both] <Both>: "))
  (if (null ans) (setq ans "Both"))
  (if (= ans "LIST") (setq ans "Checks"))
  (setq oldecho (getvar "CMDECHO"))
  (setvar "CMDECHO" 0)
  (command "_.UNDO" "_Begin")
  (setq undo-open T)

  (if (member ans '("Checks" "Both"))
    (progn
      (foreach l (dchk:tut-checklist) (princ (strcat "\n" l)))
      (princ "\n")
      (if (cal:ask-yn "\n  Drop that list into the drawing as a reference sheet?" "Yes")
        (progn
          (cal:ensure-layer *dchk-report-layer* *dchk-report-color*)
          (setq ins (getpoint "\n  Pick the top-left corner for the sheet: "))
          (if ins
            (progn
              (setq h   (getdist (strcat "\n  Text height <" (rtos 2.5) ">: "))
                    h   (if h h 2.5)
                    ins (trans ins 1 0))
              (dchk:mtext ins h (* 70.0 h)
                          (dchk:join (dchk:tut-checklist) "\\P")
                          *dchk-report-layer*)
              (princ "\n  Reference sheet placed (one U removes it)."))
            (princ "\n  No point picked - sheet skipped."))))))

  (if (member ans '("Demo" "Both"))
    (dchk:tut-demo))

  (command "_.UNDO" "_End")
  (setq undo-open nil)
  (setvar "CMDECHO" oldecho)
  (princ (strcat "\n\n--- Tutorial finished ---"
                 "\n  DIMSCAN first if you want to look without touching anything;"
                 "\n  DIMCHECK to review and fix; DIMCHECKRESCUE to undo the marks."
                 "\n  One U undoes everything this tutorial drew."))
  (princ))

(defun c:TUTORIALDIMSCAN () (c:TUTORIALDIMCHECK))

(princ "\ndimcheck.lsp loaded - DIMCHECK reviews dimensions, arcs & overlapping")
(princ "\n  lines one at a time; DIMSCAN reports it read-only; DIMCHECKRESCUE undoes")
(princ "\n  DIMCHECK's marks. For steps, wall height, the liner pattern and the")
(princ "\n  title block border too, load linfincheck.lsp and run LINFINCHECK.")
(princ)


;;; ======================================================================
;;; >>> dim_continue.lsp
;;; ======================================================================

;;; ==================================================================
;;;  dim_continue.lsp
;;;
;;;  DIMCONTEND  ("Dimension - Continue to End")
;;;
;;;  Continue an existing linear/aligned dimension across a highlighted
;;;  part of the drawing.  The routine chains continued dimensions from
;;;  the seed dimension's far extension line to every feature point that
;;;  lies beyond it, marching in a straight line out to the last point
;;;  of the selection -- the "end of the drawing".  Each new dimension
;;;  inherits every property of the seed (dimension style, layer, text,
;;;  arrows, precision, ...) because it is created with AutoCAD's own
;;;  DIMCONTINUE command anchored on the seed.
;;;
;;;  Usage
;;;    Command: DIMCONTEND        (short alias: DCE)
;;;      1. Select the dimension to continue (a linear or aligned dim).
;;;      2. Highlight the drawing to dimension (window/crossing select).
;;;    The dimension chain is drawn automatically.
;;;
;;; SHARED BUILD: requires CALOFIN-LIB.lsp (load via CALOFIN-LOADER.lsp).
;;; Generic helpers live there under cal: - see STANDARDS.md.
;;;
;;;  Notes
;;;    * "Linear/aligned" means DXF dimension type 0 (rotated /
;;;      horizontal / vertical) or 1 (aligned).  Angular, radial,
;;;      diameter and ordinate dimensions are rejected as seeds.
;;;    * The travel direction and the measurement axis are taken from
;;;      the seed, so the continuation follows the seed's orientation
;;;      even if the geometry is rotated.
;;;    * Requires Visual LISP (standard in full AutoCAD).  AutoCAD LT
;;;      has no LISP engine and cannot run this file.
;;; ==================================================================

;; --- measurement-axis angle (radians) of a linear/aligned dimension
(setq *dimcontinue-version* "v1.0")   ; announced on load; release_lisp.py
                                         ; stamps the dated twin in releases/

(defun dce:axis (ed)
  (if (and (member '(100 . "AcDbRotatedDimension") ed) (assoc 50 ed))
    (cdr (assoc 50 ed))                       ; rotated dim: explicit angle
    (angle (cdr (assoc 13 ed)) (cdr (assoc 14 ed))))) ; aligned: 1st->2nd ext

;; --- signed distance of point P from ORIGIN along the axis at angle A
(defun dce:proj (p origin a)
  (+ (* (- (car  p) (car  origin)) (cos a))
     (* (- (cadr p) (cadr origin)) (sin a))))

;; --- feature points of one entity that are worth dimensioning
(defun dce:pts (en / ed typ pts en2 res)
  (setq ed  (entget en)
        typ (cdr (assoc 0 ed))
        pts nil)
  (cond
    ((= typ "LINE")
       (setq pts (list (cdr (assoc 10 ed)) (cdr (assoc 11 ed)))))
    ((= typ "LWPOLYLINE")
       (foreach g ed (if (= 10 (car g)) (setq pts (cons (cdr g) pts)))))
    ((= typ "POLYLINE")                       ; old-style / 3D polyline
       (setq en2 (entnext en))
       (while (and en2 (= "VERTEX" (cdr (assoc 0 (entget en2)))))
         (setq pts (cons (cdr (assoc 10 (entget en2))) pts)
               en2 (entnext en2))))
    ((member typ '("POINT" "CIRCLE"))
       (setq pts (list (cdr (assoc 10 ed)))))
    (t                                        ; any other curve object
       (setq res (vl-catch-all-apply
                   'vlax-curve-getStartPoint (list en)))
       (if (not (vl-catch-all-error-p res))
         (setq pts (list res (vlax-curve-getEndPoint en))))))
  pts)

;; ------------------------------------------------------------------
(defun c:DIMCONTEND ( / *error* olderr oce ocl oos
                        tref en ed a p14 seedstyle seedlayer seedt
                        ss i pl proj sorted kept prev pt tol )

  ;; -- restore state on error / cancel
  (setq olderr *error*)
  (defun *error* (m)
    (if oce (setvar "CMDECHO" oce))
    (if ocl (setvar "CLAYER"  ocl))
    (if oos (setvar "OSMODE"  oos))
    (setq *error* olderr)
    (if (and m (not (wcmatch (strcase m) "*BREAK*,*CANCEL*,*QUIT*,*EXIT*")))
      (princ (strcat "\n** Error: " m)))
    (princ))

  (setq oce (getvar "CMDECHO")
        ocl (getvar "CLAYER")
        oos (getvar "OSMODE")
        tol 1e-6)
  (vl-load-com)

  ;; -- 1. pick the seed dimension --------------------------------
  (setq en nil)
  (while (null en)
    (setq tref (entsel "\nSelect the dimension to continue: "))
    (cond
      ((null tref)                                   ; Enter / miss -> quit
         (setq en :none))
      ((/= "DIMENSION" (cdr (assoc 0 (entget (car tref)))))
         (princ " -- that is not a dimension, try again."))
      ((> (logand (cdr (assoc 70 (entget (car tref)))) 7) 1)
         (princ " -- only linear/aligned dimensions can be continued."))
      (t (setq en (car tref)))))

  (if (eq en :none)
    (princ "\nNo dimension selected -- nothing to do.")
    (progn
      (setq ed        (entget en)
            a         (dce:axis ed)
            p14       (cdr (assoc 14 ed))            ; seed far ext-line origin
            seedt     (dce:proj p14 p14 a)           ; == 0, kept for clarity
            seedstyle (cdr (assoc 3 ed))
            seedlayer (cdr (assoc 8 ed)))

      ;; -- 2. highlight the drawing to dimension -----------------
      (princ "\nHighlight the drawing to dimension (window/crossing): ")
      (setq ss (ssget))

      (if (null ss)
        (princ "\nNothing highlighted -- nothing to do.")
        (progn
          ;; -- gather candidate points beyond the seed's far ext line
          (setq pl nil i 0)
          (while (< i (sslength ss))
            (foreach p (dce:pts (ssname ss i))
              (setq proj (dce:proj p p14 a))
              (if (> proj tol)                       ; strictly beyond seed
                (setq pl (cons (cons proj p) pl))))
            (setq i (1+ i)))

          (if (null pl)
            (princ "\nNo feature points lie beyond the dimension -- nothing to continue.")
            (progn
              ;; -- sort by distance, drop duplicates within tolerance
              (setq sorted (vl-sort pl
                             (function (lambda (u v) (< (car u) (car v)))))
                    kept   nil
                    prev   nil)
              (foreach pr sorted
                (if (or (null prev) (> (- (car pr) prev) tol))
                  (setq kept (cons (cdr pr) kept)
                        prev (car pr))))
              (setq kept (reverse kept))

              ;; -- 3. draw the continued chain from the seed ------
              (setvar "CMDECHO" 0)
              (setvar "CLAYER"  seedlayer)
              (setvar "OSMODE"  0)
              (vl-catch-all-apply
                'command (list "._-DIMSTYLE" "_Restore" seedstyle))
              (command "._DIMCONTINUE" "_Select" (list en p14))
              (foreach pt kept (command pt))
              (command "" "")                        ; end + exit DIMCONTINUE

              (setvar "OSMODE"  oos)
              (setvar "CLAYER"  ocl)
              (setvar "CMDECHO" oce)
              (princ (strcat "\n" (itoa (length kept))
                             " continued dimension(s) added.")))))))
    )

  (setq *error* olderr)
  (princ))

;; short alias
(defun c:DCE () (c:DIMCONTEND))

(princ "\nDIMCONTEND / DCE loaded -- continue a dimension to the end of the drawing.")
(princ)


;;; ======================================================================
;;; >>> DroneDistortion.lsp
;;; ======================================================================

;;; ============================================================================
;;;  Drone Distortion Correction Tool for AutoCAD            (DroneDistortion.lsp)
;;; ----------------------------------------------------------------------------
;;;  Corrects the scale of pool features that are NOT at deck level after a
;;;  near-nadir drone photo has been rectified to deck scale (e.g. by Ariel /
;;;  Fisherlea using its 6 deck scale measurements) and exported as a DXF that
;;;  you open in AutoCAD. The photo itself is not in CAD - this tool works
;;;  purely on the traced geometry.
;;;
;;;  WHY THIS IS NEEDED
;;;  ------------------
;;;  The deck scale is only true ON the deck plane. A feature raised toward the
;;;  drone (a raised spa) is closer to the camera, so it traces LARGER than it
;;;  really is. A feature below the deck (a negative-edge catch basin) is farther
;;;  away, so it traces SMALLER than it really is.
;;;
;;;  THE MATH
;;;  --------
;;;  For a traced feature sitting a signed height z above the deck
;;;      z > 0  -> raised toward the drone
;;;      z < 0  -> sunken below the deck
;;;  and a drone height H above the deck, the TRUE geometry is the traced
;;;  geometry scaled by:
;;;
;;;         factor = (H - z) / H
;;;
;;;  The "distortion rate" is ~1/H to first order (at H = 100, about a 1% size
;;;  error per unit of height); the exact apparent/true ratio is H/(H - z),
;;;  which DDFIX reports for each feature you correct.
;;;
;;;  BASE POINT
;;;  ----------
;;;  DDFIX scales about the CENTRE of the selection by default, so the feature
;;;  stays put and only changes size. If a feature shares an edge with the pool
;;;  (e.g. a spillover spa), pick that shared corner as the base point instead
;;;  so the shared edge does not move.
;;;
;;;  COMMANDS
;;;  --------
;;;     DDFIX   - select a feature, enter its height, apply the correction
;;;     DDSET   - set/forget the drone height H (DDFIX also asks the first time)
;;;     DDALT   - read RelativeAltitude from the original DJI image and set H
;;;     DDCAL   - back-solve H from a feature of known true size (cross-check)
;;;     DDINFO  - show current settings and the distortion rate
;;;
;;;  UNITS
;;;  -----
;;;  The correction is a dimensionless ratio, so the DRAWING units do not matter.
;;;  Enter the DRONE HEIGHT (H) as a number in FEET (e.g. 62 or 62.25).
;;;  Enter each FEATURE HEIGHT in feet & inches - 6"  2'  1'6-1/2"  18'6.5" - and
;;;  put a - in front for a feature BELOW the deck (a bare number is read as
;;;  inches). Any size works; small ones get a tiny correction (1" at H=80' = ~0.1%).
;;;
;;;  H is the drone height ABOVE THE DECK, not above the take-off point. If the
;;;  drone took off from the deck, that is the logged "relative altitude" (DDALT
;;;  reads it straight out of the original DJI .JPG). If it took off X BELOW the
;;;  deck SUBTRACT X; if it took off X ABOVE the deck ADD X.
;;;
;;;  H is stored in the drawing and survives save/close/reopen.
;;; ============================================================================

;;; SHARED BUILD: requires CALOFIN-LIB.lsp (load via CALOFIN-LOADER.lsp).
;;; Generic helpers live there under cal: - see STANDARDS.md.
;;;

(setq *dronedistortion-version* "v1.0")   ; announced on load; release_lisp.py
                                             ; stamps the dated twin in releases/

(vl-load-com)

(setq *DD-STORE* "DRONE_DISTORTION")   ; LDATA dictionary key (per-drawing)

;; -- persistent storage helpers ---------------------------------------------
;; vlax-ldata-get returns the value with its original type, or nil if absent.
(defun dd-get (key)
  (vlax-ldata-get *DD-STORE* key))

(defun dd-put (key val)
  (vlax-ldata-put *DD-STORE* key val))

;; -- formatting helper ------------------------------------------------------
(defun dd-num (x) (rtos x 2 3))        ; trim a real to 3 decimals as a string

;; -- centre of the combined bounding box of a selection set (returns WCS) ----
(defun dd-ss-center (ss / i obj mn mx lo hi lomin himax)
  (setq i 0)
  (while (< i (sslength ss))
    (setq obj (vlax-ename->vla-object (ssname ss i)))
    (if (not (vl-catch-all-error-p
               (vl-catch-all-apply 'vla-getboundingbox (list obj 'mn 'mx))))
      (progn
        (setq lo (vlax-safearray->list mn)
              hi (vlax-safearray->list mx))
        (if lomin
          (setq lomin (mapcar 'min lomin lo)
                himax (mapcar 'max himax hi))
          (setq lomin lo himax hi))))
    (setq i (1+ i)))
  (if lomin
    (mapcar '(lambda (a b) (/ (+ a b) 2.0)) lomin himax)))

;; -- parse one numeric piece into a number of inches; nil if not numeric -------
;; "6"   "6.5"   "6-1/2"   "1/2"  ->  number
(defun dd-inchval (s / pos whole frac num den)
  (setq s (vl-string-trim " " s))
  (cond
    ((= s "") 0.0)
    ((setq pos (vl-string-search "-" s))               ; whole-and-fraction: 6-1/2
     (setq whole (dd-inchval (substr s 1 pos))
           frac  (dd-inchval (substr s (+ pos 2))))
     (if (and whole frac) (+ whole frac)))
    ((setq pos (vl-string-search "/" s))               ; fraction: 1/2
     (setq num (distof (substr s 1 pos) 2)
           den (distof (substr s (+ pos 2)) 2))
     (if (and num den (/= den 0.0)) (/ num den)))
    (t (distof s 2))))                                  ; plain decimal

;; -- ask for a height in feet & inches; return decimal FEET (nil if blank/bad) -
;; Accepts:  6"   18   2'   2'6"   1'6-1/2"   18'6.5"   -3'4"
;; A leading - means BELOW the deck; a bare number is read as inches. Splits on
;; the ' and " by hand, so it does not depend on the drawing's unit settings.
;; With BACK non-nil, typing B (Back; Undo works too) returns the symbol
;; DD-BACK instead - the caller re-opens its previous question.
(defun dd-parse-height (prompt back / s sign fpos ftxt itxt feet inch)
  (setq s (getstring T prompt))
  (cond
    ((or (null s) (= (vl-string-trim " \t" s) "")) nil)
    ((and back (cal:back-word-p s)) 'DD-BACK)
    (T
      (setq s (vl-string-trim " \t" s) sign 1.0)
      (while (member (substr s 1 1) '("-" "+"))
        (if (= (substr s 1 1) "-") (setq sign (- sign)))
        (setq s (vl-string-trim " " (substr s 2))))
      (setq fpos (vl-string-search "'" s))
      (if fpos
        (setq ftxt (substr s 1 fpos) itxt (substr s (+ fpos 2)))
        (setq ftxt "0" itxt s))
      (if (= ftxt "") (setq ftxt "0"))
      (setq itxt (vl-string-trim " \"" itxt))
      (if (= itxt "") (setq itxt "0"))
      (setq feet (distof ftxt 2) inch (dd-inchval itxt))
      (if (and feet inch)
        (* sign (+ feet (/ inch 12.0)))))))

;; ---------------------------------------------------------------------------
;;  DDFIX : correct a selected off-deck feature
;; ---------------------------------------------------------------------------
(defun c:DDFIX ( / *error* cmd ss h cur-h z base factor appf stage done)
  (setq cmd (getvar "CMDECHO"))
  (defun *error* (m)
    (setvar "CMDECHO" cmd)
    (if (and m (not (wcmatch (strcase m) "*BREAK*,*CANCEL*,*QUIT*,*EXIT*")))
      (princ (strcat "\nError: " m)))
    (princ))

  ;; The three questions are staged: Back (Undo works too) at the
  ;; height prompts re-opens the previous one, and a bad value re-asks
  ;; instead of aborting the command.
  (setq stage 1 done nil)
  (while (not done)
    (cond

      ;; 1) select the spa / obstacle (one or more objects)
      ((= stage 1)
       (princ "\nSelect the spa / obstacle to correct (one or more objects), then Enter.")
       (setq ss (ssget))
       (if (null ss)
         (progn (princ "\nNothing selected.") (setq done T))
         (setq stage 2)))

      ;; 2) drone height above the deck - remembered; Enter keeps last value
      ((= stage 2)
       (setq cur-h (dd-get "H"))
       (initget "Back Undo")
       (setq h (getreal (strcat "\nDrone height above the deck, in FEET"
                                (if cur-h (strcat " <" (dd-num cur-h) ">") "")
                                " [Back]: ")))
       (cond
         ((= (type h) 'STR) (setq stage 1))
         (t
          (if (and (null h) cur-h) (setq h cur-h))
          (if (or (null h) (<= h 0.0))
            (princ "\nNeed a drone height greater than 0.")
            (progn (dd-put "H" h) (setq stage 3))))))

      ;; 3) spa / obstacle height in feet & inches
      ((= stage 3)
       (setq z (dd-parse-height
                 (strcat "\nSpa / obstacle height relative to deck"
                         "\n  e.g. 6\"  2'  1'6-1/2\"  18'6.5\"   (- in front = below deck) [Back]: ")
                 T))
       (cond
         ((eq z 'DD-BACK) (setq stage 2))
         ((null z) (princ "\nNo valid height (try like 1'6\")."))
         ((equal z 0.0 1e-9)
          (princ "\nHeight is 0 - feature is at deck level, no change.")
          (setq done T))
         ((>= (abs z) h)
          (princ (strcat "\n|height| (" (dd-num z) " ft) >= drone height ("
                         (dd-num h) " ft). Check your value.")))
         (t (setq stage 4))))

      ;; 4) scale about the centre of the selection
      (t
       (setq base (dd-ss-center ss))
       (cond
         ((null base) (princ "\nCould not work out a centre point - aborting."))
         (t
          (setq base   (trans base 0 1)             ; WCS centre -> current UCS
                factor (/ (- h z) h))               ; (H - z) / H
          (setvar "CMDECHO" 0)
          ;; "_non" overrides any running osnap; vl-cmdf returns nil on failure
          (if (vl-cmdf "_.SCALE" ss "" "_non" base factor)
            (progn
              (setq appf (/ h (- h z)))             ; apparent / true
              (princ (strcat "\nApplied scale " (rtos factor 2 5) " ("
                             (rtos (* 100.0 (- factor 1.0)) 2 2) "% size change)."))
              (if (> z 0.0)
                (princ (strcat "\nRaised feature: it was traced ~"
                               (rtos (* 100.0 (- appf 1.0)) 2 2) "% too BIG."))
                (princ (strcat "\nSunken feature: it was traced ~"
                               (rtos (* 100.0 (- 1.0 appf)) 2 2) "% too SMALL."))))
            (princ "\nSCALE did not run - are the objects on a locked layer?"))))
       (setq done T))))
  (setvar "CMDECHO" cmd)
  (princ))

;; ---------------------------------------------------------------------------
;;  DDSET : set / change the drone height H for this drawing
;; ---------------------------------------------------------------------------
(defun c:DDSET ( / h cur-h)
  (setq cur-h (dd-get "H"))
  (setq h (getreal (strcat "\nDrone height ABOVE THE DECK, in FEET"
                           (if cur-h (strcat " <" (dd-num cur-h) ">") "")
                           ": ")))
  (if (and (null h) cur-h) (setq h cur-h))   ; <Enter> keeps the current value
  (cond
    ((null h)   (princ "\nNo height set."))
    ((<= h 0.0) (princ "\nHeight must be greater than 0."))
    (t
      (dd-put "H" h)
      (princ (strcat "\nSaved drone height  H = " (dd-num h)))
      (princ (strcat "\nDistortion rate: ~" (dd-num (/ 100.0 h))
                     "% size change per unit of height."))))
  (princ))

;; ---------------------------------------------------------------------------
;;  DDCAL : back-solve H from a feature whose true size you measured on site
;;          (independent cross-check on the logged altitude)
;;          H = Lapp * z / (Lapp - Ltrue)
;; ---------------------------------------------------------------------------
(defun c:DDCAL ( / lapp ltrue z h stage done)
  (princ "\nCalibrate drone height from a feature of known true size.")
  ;; staged: Back (or Undo) at the later prompts re-opens the previous one
  (setq stage 1 done nil)
  (while (not done)
    (cond
      ((= stage 1)
       (setq lapp (getdist "\nApparent (traced) size in the drawing - type it or pick 2 points: "))
       (setq stage 2))
      ((= stage 2)
       (initget "Back Undo")
       (setq ltrue (getreal "\nTrue size measured on site [Back]: "))
       (if (= (type ltrue) 'STR) (setq stage 1) (setq stage 3)))
      (t
       (setq z (dd-parse-height
                 "\nHeight of that feature, e.g. 6\"  2'  18'6.5\"  (- for sunken) [Back]: " T))
       (if (eq z 'DD-BACK) (setq stage 2) (setq done T)))))
  (cond
    ((or (null lapp) (null ltrue) (null z))
     (princ "\nMissing input - aborting."))
    ((equal z 0.0 1e-9)
     (princ "\nHeight is 0 - cannot solve H from a deck-level feature."))
    ((equal lapp ltrue (* 1e-4 (max (abs lapp) (abs ltrue) 1.0)))
     (princ "\nApparent and true sizes are too close - distortion too small to solve H reliably."))
    (t
      (setq h (/ (* lapp z) (- lapp ltrue)))
      (if (> h 0.0)
        (progn
          (dd-put "H" h)
          (princ (strcat "\nSolved drone height  H = " (dd-num h) "  (saved)."))
          (princ (strcat "\nDistortion rate: ~" (dd-num (/ 100.0 h)) "% per unit of height.")))
        (princ (strcat "\nGot a non-physical H = " (dd-num h)
                       "\nCheck the sign of the height and that apparent/true sizes "
                       "match a raised (app>true) or sunken (app<true) feature.")))))
  (princ))

;; ---------------------------------------------------------------------------
;;  DDINFO : report current settings
;; ---------------------------------------------------------------------------
(defun c:DDINFO ( / h)
  (setq h (dd-get "H"))
  (princ "\n--- Drone Distortion settings (this drawing) ---")
  (if h
    (progn
      (princ (strcat "\n  Drone height above deck (H): " (dd-num h)))
      (princ (strcat "\n  Distortion rate            : ~" (dd-num (/ 100.0 h))
                     "% size change per unit of height")))
    (princ "\n  Drone height (H)           : NOT SET  (run DDSET or DDFIX)"))
  (princ "\n------------------------------------------------")
  (princ))

;; ---------------------------------------------------------------------------
;;  RelativeAltitude reader  -  pull dji:RelativeAltitude out of a DJI image
;; ---------------------------------------------------------------------------
;;  DJI writes an XMP text packet inside the image holding, e.g.
;;      dji:RelativeAltitude="+18.90"     (METRES above the TAKE-OFF point)
;;  This reads the file's raw bytes (Windows ADODB.Stream) and scans for the
;;  tag, so the container does not matter - JPG and PNG both work as long as
;;  the packet survived. It only works on ORIGINAL camera files; screenshots,
;;  edited, emailed or re-exported copies have the metadata stripped.
;;  (Windows AutoCAD only.)

;; value string like "+18.90" -> real metres (drops a leading +, trims spaces)
(defun dd-relalt->num (s)
  (setq s (vl-string-trim " " s))
  (if (and (> (strlen s) 0) (= (substr s 1 1) "+")) (setq s (substr s 2)))
  (atof s))

;; read up to `cnt` bytes of a file as a list of ints (0-255), BINARY-SAFE,
;; via Windows' ADODB.Stream.  Plain (open ... "r") + read-char is TEXT mode and
;; quits at the first 0x1A byte - DJI JPEGs have dozens of those before the XMP -
;; so it cannot be used here.  Returns the byte list, or nil if unreadable.
(defun dd-file-bytes (file cnt / stm out err)
  (setq err
    (vl-catch-all-apply
      '(lambda ( / raw sa tmp)
         (setq stm (vlax-create-object "ADODB.Stream"))
         (vlax-put-property  stm 'Type 1)              ; 1 = adTypeBinary,
         ;; AutoLISP will not call a method whose parameters are all optional
         ;; unless they are supplied - a bare (Open) fails with "too few
         ;; actual parameters". Pass Stream.Open's documented defaults.
         (if (vl-catch-all-error-p
               (vl-catch-all-apply
                 '(lambda ()
                    (vlax-invoke-method stm 'Open (vlax-make-variant) 0 -1 "" ""))
                 '()))
           (vlax-invoke-method stm 'Open))
         (vlax-invoke-method stm 'LoadFromFile file)
         (setq raw (vlax-invoke-method stm 'Read cnt)) ; first cnt bytes
         (vlax-invoke-method stm 'Close)
         (cond
           ((listp raw) (setq out raw))                ; some builds return a list
           (t
            (setq tmp (vl-catch-all-apply 'vlax-variant-value (list raw)))
            (setq sa  (if (vl-catch-all-error-p tmp) raw tmp))
            (setq out (vlax-safearray->list sa)))))
      '()))
  (if stm (vl-catch-all-apply 'vlax-release-object (list stm)))
  (if (vl-catch-all-error-p err) nil out))

;; scan an image for  RelativeAltitude="..."  ; returns METRES (real) or nil.
;; tgt is the ASCII for  RelativeAltitude="  - we walk the raw bytes so the
;; binary image data does not trip us up; stop at the closing quote.
(defun dd-jpg-relalt (file / lst tgt tlen m val done b)
  (setq tgt  '(82 101 108 97 116 105 118 101 65 108 116 105 116 117 100 101 61 34)
        tlen (length tgt) m 0 val "" done nil)
  (setq lst (dd-file-bytes file 262144))            ; first 256 KB (XMP is near the front)
  (while (and lst (not done))
    (setq b (car lst) lst (cdr lst))
    (if (< b 0) (setq b (+ b 256)))                 ; normalise if returned signed
    (cond
      ((< m tlen)                                    ; still matching the tag
       (if (= b (nth m tgt))
         (setq m (1+ m))
         (setq m (if (= b (car tgt)) 1 0))))         ; reset (tag starts with R)
      ((= b 34) (setq done t))                       ; closing quote -> done
      (t (setq val (strcat val (chr b))))))          ; collect the value
  (if (and done (> (strlen val) 0))
    (dd-relalt->num val)))

;; ---------------------------------------------------------------------------
;;  DDALT : read RelativeAltitude from a drone image and (optionally) set H
;; ---------------------------------------------------------------------------
(defun c:DDALT ( / file m ft off h ans stage done)
  ;; staged: Back (or Undo) at a later prompt re-opens the previous
  ;; one, all the way back to the file dialog
  (setq stage 1 done nil)
  (while (not done)
    (cond

      ((= stage 1)
       (setq file (getfiled "Select the ORIGINAL drone image (PNG / JPG / TIF)" ""
                            "png;jpg;jpeg;tif;tiff" 20))
       (cond
         ((null file) (princ "\nNo file selected.") (setq done T))
         ((null (setq m (dd-jpg-relalt file)))
          (alert (strcat "NO RelativeAltitude IN THIS FILE"
                         "\nFile: " (vl-filename-base file)
                         (if (vl-filename-extension file) (vl-filename-extension file) "")
                         "\n\nCould not find dji:RelativeAltitude in the file."
                         "\nIs it the ORIGINAL camera file?  Screenshots / edited /"
                         "\nexported copies lose the metadata."
                         "\n\n(DDGPS reads more formats and also falls back to the"
                         "\nEXIF GPS block - try that.)"))
          (princ "\nCould not find dji:RelativeAltitude in that file.")
          (princ "\n  Is it the ORIGINAL camera file?  Screenshots / edited / exported copies lose it.")
          (setq done T))
         (t
          (setq ft (* m 3.280839895))
          (princ "\nRelativeAltitude (drone height above the TAKE-OFF point):")
          (princ (strcat "\n   " (dd-num m) " m   =   " (dd-num ft) " ft"))
          (setq stage 2))))

      ((= stage 2)
       (initget "Yes No Back Undo")
       (setq ans (getkword
                   "\nUse this to set the drone height H? [Yes/No/Back] <Yes>: "))
       (if (null ans) (setq ans "Yes"))
       (cond
         ((member ans '("Back" "Undo")) (setq stage 1))
         ((= ans "No") (princ "\nH not changed.") (setq done T))
         (t (setq stage 3))))

      (t
       (initget "Back Undo")
       (setq off (getreal (strcat "\nTake-off point vs deck, in FEET"
                                  "\n  (+ if take-off ABOVE deck, - if BELOW, Enter if it took off FROM the deck) [Back]: ")))
       (if (= (type off) 'STR)
         (setq stage 2)
         (progn
           (if (null off) (setq off 0.0))
           (setq h (+ ft off))
           (if (<= h 0.0)
             (princ (strcat "\nThat gives H = " (dd-num h)
                            " ft (<= 0) - not saved. Check the offset."))
             (progn
               (dd-put "H" h)
               (princ (strcat "\nSaved drone height  H = " (dd-num h) " ft"))
               (if (/= off 0.0)
                 (princ (strcat "   (" (dd-num ft) " ft relative "
                                (if (> off 0.0) "+ " "- ") (dd-num (abs off)) " ft offset)")))
               (princ (strcat "\nDistortion rate: ~" (dd-num (/ 100.0 h))
                              "% size change per unit of height."))))
           (setq done T))))))
  (princ))

(princ "\nDrone Distortion tool v3.4 loaded  (DDALT accepts PNG / JPG / TIF and fails loud).")
(princ "\n  Commands: DDFIX  DDSET  DDALT  DDCAL  DDINFO")
(princ)


;;; ======================================================================
;;; >>> DroneHeightGPS.lsp
;;; ======================================================================

;;; ============================================================================
;;;  Drone Height from GPS + Ground Elevation                (DroneHeightGPS.lsp)
;;; ----------------------------------------------------------------------------
;;;  Companion to DroneDistortion.lsp. Instead of guessing the drone height
;;;  above grade (the office default of "100 ft"), DDGPS works it out from the
;;;  photo itself:
;;;
;;;     1. File picker   - pick the ORIGINAL drone photo (starts on H:, then
;;;                        remembers the last folder you used).
;;;     2. Read the GPS  - latitude / longitude / AbsoluteAltitude straight
;;;                        out of the file. The DJI XMP text packet is tried
;;;                        first; if it is missing the binary EXIF GPS block
;;;                        is parsed instead. EXIF stores the hemisphere
;;;                        separately (GPSLatitudeRef / GPSLongitudeRef); if
;;;                        a file omits the E/W one, WEST is assumed, since
;;;                        every job is in the United States, and the run
;;;                        says so. A position that does not land in the US
;;;                        is flagged - that is what a wrong hemisphere
;;;                        looks like.
;;;     3. Click a point - pick where in the drawing to place the result.
;;;     4. Elevation     - ask a free online elevation service for the ground
;;;                        elevation at that latitude / longitude (HTTP
;;;                        request via the Windows MSXML2.XMLHTTP object).
;;;     5. The delta     - drone height above grade:
;;;
;;;              H  =  AbsoluteAltitude(ft)  -  ground elevation(ft)
;;;
;;;                    ...but only when the photo's altitude really is
;;;                    referenced to sea level. XMP AbsoluteAltitude always
;;;                    is; EXIF GPSAltitude often is NOT - plenty of DJI
;;;                    models put the height above the TAKE-OFF point in
;;;                    that tag. So both readings are worked out and the
;;;                    physically possible one is used: a drone cannot fly
;;;                    below the ground, and cannot legally fly above
;;;                    400 ft AGL. The run says which one it took, and so
;;;                    does the text placed in the drawing.
;;;
;;;        rounded to the nearest foot, written as text at the picked point,
;;;        AND saved to the SAME per-drawing store DroneDistortion.lsp uses,
;;;        so DDFIX immediately offers it as its default. This file also
;;;        works on its own - DroneDistortion.lsp does not need to be loaded.
;;;
;;;  FILE TYPES
;;;  ----------
;;;  PNG, JPG/JPEG and TIFF are all understood, PROVIDED the file still
;;;  carries its original camera metadata - this only works on an original
;;;  drone photo, not a video frame grab, screenshot, or an export that
;;;  stripped it. The reader does not trust the file extension - it looks for
;;;  the metadata containers themselves:
;;;    * XMP text packet   - JPEG APP1, PNG iTXt chunk, or anywhere else the
;;;                          "<x:xmpmeta" packet appears; both DJI's normal
;;;                          attribute form (Tag="...") and the element form
;;;                          (<ns:Tag>...</ns:Tag>) some converters re-write.
;;;    * binary EXIF GPS   - JPEG "Exif\0\0" APP1 block, PNG eXIf chunk, or a
;;;                          bare TIFF header (a .TIF file), either byte order.
;;;  The first 256 KB of the file is scanned; if nothing is found there the
;;;  LAST 256 KB is scanned too (PNG writers may park metadata after the
;;;  image data). If neither container has a usable GPS position and
;;;  altitude, DDGPS fails loudly and stops - use the file exactly as it
;;;  came off the drone.
;;;
;;;  ANNOTATION
;;;  ----------
;;;  After you click a point, DDGPS drops 5 lines of plain single-line TEXT
;;;  at that point (GPS position, drone altitude, ground elevation + source,
;;;  the subtraction, and the final rounded height) on the current layer, in
;;;  the current text style. Text height defaults to the drawing's current
;;;  TEXTSIZE the first time; after that it is remembered per drawing (same
;;;  store as H below) and offered as the default - press Enter to keep it,
;;;  or type a new height to change it.
;;;
;;;  ELEVATION SERVICES (tried in order until one answers; no API keys)
;;;  ------------------
;;;    1. USGS EPQS      - 3DEP ~1-10 m bare-earth model, answers in FEET
;;;                        (NAVD88). US only, public domain, no rate limits
;;;                        that matter at office volumes.
;;;    2. OpenTopoData   - NED 10 m dataset, metres. US only.
;;;    3. Open-Elevation - SRTM ~30 m grid, metres. Worldwide fallback.
;;;  If none can be reached, DDGPS lets you type a known site elevation
;;;  instead (e.g. from the survey) rather than losing the whole run.
;;;
;;;  ACCURACY - READ THIS ONCE
;;;  -------------------------
;;;  * The ground elevation is solid (USGS bare-earth is good to a couple of
;;;    feet). The weak link is the drone's ABSOLUTE altitude: consumer GPS
;;;    vertical error is routinely 10-30 ft, and DJI's sea-level reference
;;;    does not exactly match the USGS datum (a few more feet).
;;;  * That is still far better than a blind 100 ft guess.
;;;  * The GPS method shines exactly where the guess fails hardest: hillside
;;;    lots where the drone launched well above or below the pool deck.
;;;  * Remember 1/H: at H = 100 ft, 10 ft of H error changes a correction
;;;    that is itself only ~1% per foot of feature height - for a 2 ft raised
;;;    spa that is a 0.2% size difference. H does not need to be perfect.
;;;  * For a hard number, DDCAL (in DroneDistortion.lsp) back-solves H from
;;;    one feature of known true size. DDALT (also in DroneDistortion.lsp)
;;;    remains available as a no-internet, barometric-only alternative.
;;;
;;;  FAILURE REPORTING
;;;  -----------------
;;;  Every failure is LOUD: a dialog box pops up saying exactly WHAT failed
;;;  and HOW - "no camera metadata in this file", "no GPS data found",
;;;  "no GPS fix (position is 0,0)", "no altitude data", or which elevation
;;;  service failed and why (no answer / HTTP error / outside coverage) -
;;;  and the same detail is printed on the command line for the record.
;;;  The only quiet exits are the ones you choose yourself (cancelling the
;;;  file dialog, declining a point, or pressing Enter at an abort prompt).
;;;
;;;  REQUIREMENTS
;;;  ------------
;;;  Windows AutoCAD (uses ADODB.Stream + MSXML2.XMLHTTP ActiveX), internet
;;;  access for the elevation lookup, and an ORIGINAL drone photo that still
;;;  carries the camera metadata (see FILE TYPES above).
;;;
;;;  NOTE: the HTTP request is synchronous - AutoCAD sits for a second or two
;;;  while the service answers. If the network is down it can take ~30 s to
;;;  give up; Esc cannot interrupt an in-flight request.
;;;
;;;  COMMANDS
;;;  --------
;;;     DDGPS   - pick the drone photo, click a point, place the height
;;;               report there, and save H for DDFIX
;;;     DDELEV  - type a latitude / longitude, print the ground elevation
;;;               (handy as an internet-connectivity test)
;;;     DDTEST  - diagnose a photo that will not read: walks every step
;;;               (find the file, ADODB.Stream, local copy, certutil hex
;;;               dump, plain read), reports what this PC actually allows,
;;;               then says whether the file carries any GPS metadata at all
;;;
;;;  UNITS
;;;  -----
;;;  Altitude in the file is metres (DJI writes metres); everything is
;;;  reported and saved in FEET to match DroneDistortion.lsp.
;;; ============================================================================

;;; SHARED BUILD: requires CALOFIN-LIB.lsp (load via CALOFIN-LOADER.lsp).
;;; Generic helpers live there under cal: - see STANDARDS.md.
;;;

(setq *droneheightgps-version* "v1.0")   ; announced on load; release_lisp.py
                                            ; stamps the dated twin in releases/

(vl-load-com)

(setq *DDG-STORE* "DRONE_DISTORTION")  ; same per-drawing LDATA dictionary as
                                       ; DroneDistortion.lsp, so DDFIX sees H
(setq ddg-m->ft 3.280839895)

;; -- persistent storage helpers ---------------------------------------------
(defun ddg-get (key)     (vlax-ldata-get *DDG-STORE* key))
(defun ddg-put (key val) (vlax-ldata-put *DDG-STORE* key val))

;; -- formatting helpers -----------------------------------------------------
(defun ddg-n1 (x) (rtos x 2 1))        ; feet, 1 decimal
(defun ddg-n7 (x) (rtos x 2 7))        ; lat/long, 7 decimals (~1/2 inch)

;; file name without the folder, for messages
(defun ddg-fname (f / e)
  (setq e (vl-filename-extension f))
  (strcat (vl-filename-base f) (if e e "")))

;; -- loud failure -----------------------------------------------------------
;; Pops a modal alert box saying WHAT failed (title) and HOW (lines), and
;; prints the same detail on the command line for the record.
(defun ddg-fail (title lines / msg)
  (setq msg title)
  (foreach l lines (setq msg (strcat msg "\n" l)))
  (princ (strcat "\n*** " title " ***"))
  (foreach l lines (if (/= l "") (princ (strcat "\n  " l))))
  (alert msg)
  (princ))

;; same, without the failure framing - for DDTEST's report
(defun ddg-report (title lines / msg)
  (setq msg title)
  (foreach l lines (setq msg (strcat msg "\n" l)))
  (princ (strcat "\n--- " title " ---"))
  (foreach l lines (if (/= l "") (princ (strcat "\n  " l))))
  (alert msg)
  (princ))

;; "yes"/"no" for the report
(defun ddg-yn (x) (if x "yes" "NO"))

;; ===========================================================================
;;  Binary file access (Windows ADODB.Stream - same technique as DDALT;
;;  plain (open ... "r") is text mode and stops at the first 0x1A byte)
;; ===========================================================================

;; Windows AutoCAD has no binary file mode in plain AutoLISP, so the primary
;; reader is the ADODB.Stream ActiveX object. EVERY COM step is caught on its
;; own, so when it breaks we can say exactly which step failed and what
;; Windows said about it - run DDTEST to see the whole sequence.
;;
;; TAIL nil = read from the start of the file; TAIL non-nil = the LAST cnt
;; bytes (PNG writers may park the metadata chunks after the image data).
;; Returns (list bytes failed-step errmsg) - bytes nil if any step failed.
;;
;; NOTE on the order below: Type is set BEFORE Open. ADODB.Stream only allows
;; the mode to be changed while the stream is closed (or empty and at
;; position 0), and setting it first is the order every working example uses.
(defun ddg-adodb-read (file cnt tail / stm out steps err failed)
  (setq steps
    (list
      (cons "create the ADODB.Stream object"
            '(lambda () (setq stm (vlax-create-object "ADODB.Stream"))))
      (cons "switch the stream to binary mode"
            '(lambda () (vlax-put-property stm 'Type 1)))    ; 1 = adTypeBinary
      (cons "open the stream"
            ;; AutoLISP's COM bridge refuses to call a method whose parameters
            ;; are ALL optional unless they are supplied - a bare (Open) comes
            ;; back as "too few actual parameters". Stream.Open takes
            ;; (Source, Mode, OpenOptions, UserName, Password), so pass the
            ;; documented defaults: an empty variant, adModeUnknown (0),
            ;; adOpenStreamUnspecified (-1) and two empty strings. The bare
            ;; call is kept as a last resort for builds that accept it.
            '(lambda ( / e)
               (setq e (vl-catch-all-apply
                         '(lambda ()
                            (vlax-invoke-method stm 'Open
                              (vlax-make-variant) 0 -1 "" ""))
                         '()))
               (if (vl-catch-all-error-p e)
                 (setq e (vl-catch-all-apply
                           '(lambda ()
                              (vlax-invoke-method stm 'Open nil 0 -1 "" ""))
                           '())))
               (if (vl-catch-all-error-p e)
                 (vlax-invoke-method stm 'Open))))
      (cons "load the file into the stream"
            '(lambda () (vlax-invoke-method stm 'LoadFromFile file)))
      (cons "seek to the right place in the file"
            '(lambda ( / pos)
               (if tail
                 (progn
                   (setq pos (- (vlax-get-property stm 'Size) cnt))
                   (if (< pos 0) (setq pos 0))
                   (vlax-put-property stm 'Position pos)))))
      (cons "read the bytes out of the stream"
            '(lambda ( / raw sa tmp)
               (setq raw (vlax-invoke-method stm 'Read cnt))
               (cond
                 ((listp raw) (setq out raw))            ; some builds return a list
                 (t
                  (setq tmp (vl-catch-all-apply 'vlax-variant-value (list raw)))
                  (setq sa  (if (vl-catch-all-error-p tmp) raw tmp))
                  (setq out (vlax-safearray->list sa))))))))
  (foreach s steps
    (if (null failed)
      (progn
        (setq err (vl-catch-all-apply (cdr s) '()))
        (if (vl-catch-all-error-p err)
          (setq failed (list (car s) (vl-catch-all-error-message err)))))))
  (if stm (vl-catch-all-apply 'vlax-release-object (list stm)))
  (if failed
    (list nil (car failed) (cadr failed))
    (list out nil nil)))

;; plain byte list, or nil - the shape the rest of the file expects
(defun ddg-file-bytes (file cnt tail)
  (car (ddg-adodb-read file cnt tail)))

;; walk LST until the byte pattern TGT has just been matched;
;; return the remainder of the list AFTER the pattern, or nil if never found
(defun ddg-scan-to (lst tgt / tlen m b)
  (setq tlen (length tgt) m 0)
  (while (and lst (< m tlen))
    (setq b (car lst) lst (cdr lst))
    (if (< b 0) (setq b (+ b 256)))                    ; normalise if signed
    (if (= b (nth m tgt))
      (setq m (1+ m))
      (setq m (if (= b (car tgt)) 1 0))))
  (if (= m tlen) lst))

;; take up to N bytes off LST as a plain string (non-printables become spaces)
(defun ddg-grab-text (lst n / out chunk b)
  (setq out '() chunk "")
  (while (and lst (> n 0))
    (setq b (car lst) lst (cdr lst) n (1- n))
    (if (< b 0) (setq b (+ b 256)))
    (setq chunk (strcat chunk (if (and (> b 31) (< b 127)) (chr b) " ")))
    (if (>= (strlen chunk) 128)                        ; chunked to keep strcat cheap
      (setq out (cons chunk out) chunk "")))
  (apply 'strcat (reverse (cons chunk out))))

;; Fallback for when ADODB.Stream is not usable at all (blocked by policy on
;; locked-down PCs, or not registered). Plain AutoLISP file I/O is TEXT mode -
;; it stops at the first 0x1A byte, of which JPEGs have plenty - so this is no
;; use for the binary EXIF block. It is still worth trying, because it often
;; reaches the XMP text packet, which is all DDGPS really needs.
;; Returns (list bytes stopped-early-flag).
(defun ddg-plain-read (file cnt / f b out n fsz)
  (setq out '() n 0)
  (cond
    ((null (setq f (open file "r"))) (list nil nil))
    (t
     (while (and (< n cnt) (setq b (read-char f)))
       (setq out (cons b out) n (1+ n)))
     (close f)
     (setq fsz (vl-file-size file))
     (list (reverse out)
           (if (and fsz (< n (min cnt fsz))) T)))))     ; hit a 0x1A, not the end

(defun ddg-tohex (b / h)
  (setq h "0123456789abcdef")
  (strcat (substr h (1+ (/ b 16)) 1) (substr h (1+ (rem b 16)) 1)))

;; first N bytes of LST as "ff d8 ff e1" - so a report can show whether a
;; reader actually returned the file, or returned mush
(defun ddg-firstbytes (lst n / out b)
  (setq out "")
  (while (and lst (> n 0))
    (setq b (car lst) lst (cdr lst) n (1- n))
    (if (< b 0) (setq b (+ b 256)))
    (setq out (strcat out (if (= out "") "" " ") (ddg-tohex b))))
  out)

;; every JPEG starts FF D8; a reader that does not produce that is mangling
(defun ddg-looks-jpeg (lst)
  (and (equal (ddg-b lst 0) 255) (equal (ddg-b lst 1) 216)))

;; local temp folder, always with a trailing backslash ("" if unknown)
(defun ddg-tempdir ( / dir)
  (setq dir (getvar "TEMPPREFIX"))
  (if (or (null dir) (= dir "")) (setq dir (getenv "TEMP")))
  (cond
    ((or (null dir) (= dir "")) "")
    ((member (substr dir (strlen dir) 1) '("/" "\\")) dir)
    (t (strcat dir "\\"))))

;; split S on spaces; returns the non-empty pieces
(defun ddg-split (s / out pos tok)
  (setq out '())
  (while (setq pos (vl-string-search " " s))
    (setq tok (substr s 1 pos) s (substr s (+ pos 2)))
    (if (/= tok "") (setq out (cons tok out))))
  (if (/= s "") (setq out (cons s out)))
  (reverse out))

;; hex digit character code -> value, nil if not a hex digit
(defun ddg-hexval (b)
  (cond ((and (>= b 48) (<= b 57))  (- b 48))     ; 0-9
        ((and (>= b 97) (<= b 102)) (- b 87))     ; a-f
        ((and (>= b 65) (<= b 70))  (- b 55))))   ; A-F

;; "ff" -> 255; nil unless the token is exactly two hex digits
(defun ddg-hexbyte (s / a b)
  (if (= (strlen s) 2)
    (progn
      (setq a (ddg-hexval (ascii (substr s 1 1)))
            b (ddg-hexval (ascii (substr s 2 1))))
      (if (and a b) (+ (* 16 a) b)))))

;; one line of a certutil hex dump -> its byte values. Lines look like
;;   0000  ff d8 ff e1 00 18 45 78  69 66 00 00 49 49 2a 00   ......Exif..II*.
;; so drop the leading offset and take at most 16 two-hex-digit tokens, which
;; stops cleanly before the ASCII column on the right.
(defun ddg-hexline (line / toks out v n stop)
  (setq toks (ddg-split line))
  ;; Drop the leading offset column ONLY if it is not itself a byte. Dropping
  ;; it unconditionally shifts every line by one byte when the dump has no
  ;; address column, which corrupts the whole stream while still looking like
  ;; a successful read.
  (if (and toks (null (ddg-hexbyte (car toks)))) (setq toks (cdr toks)))
  (setq out '() n 0)
  (while (and toks (< n 16) (null stop))
    (setq v (ddg-hexbyte (car toks)) toks (cdr toks))
    (if v (setq out (cons v out) n (1+ n)) (setq stop T)))
  (reverse out))

;; Third-tier reader: have Windows' own certutil rewrite the file as a HEX
;; TEXT dump, then read that back with plain AutoLISP. The dump is pure ASCII,
;; so none of the binary-file problems apply - this is the fallback for PCs
;; where ADODB.Stream is blocked outright. Returns a byte list, or nil.
(defun ddg-certutil-read (file cnt / sh dst err f line out n dir)
  (setq dir (ddg-tempdir))
  (cond
    ((= dir "") nil)
    (t
     (setq dst (strcat dir "DDGPS_hex.txt"))
     (if (findfile dst) (vl-file-delete dst))
     (setq err
       (vl-catch-all-apply
         '(lambda ()
            (setq sh (vlax-create-object "WScript.Shell"))
            (vlax-invoke-method sh 'Run
              (strcat "cmd /c certutil -encodehex \"" file "\" \"" dst "\"")
              0 :vlax-true))                       ; 0 = hidden, T = wait for it
         '()))
     (if sh (vl-catch-all-apply 'vlax-release-object (list sh)))
     (cond
       ((vl-catch-all-error-p err) nil)
       ((null (setq f (open dst "r"))) nil)
       (t
        (setq out '() n 0)
        (while (and (< n cnt) (setq line (read-line f)))
          (foreach b (ddg-hexline line)
            (if (< n cnt) (setq out (cons b out) n (1+ n)))))
        (close f)
        (if out (reverse out)))))))

;; copy FILE into the local temp folder and return the local path, or nil.
;; Reading straight off a mapped drive can fail for reasons that have nothing
;; to do with the photo; a plain local copy sidesteps those.
(defun ddg-local-copy (file / dir dst)
  (setq dir (ddg-tempdir))
  (if (/= dir "")
    (progn
      (setq dst (strcat dir "DDGPS_photo"
                        (if (vl-filename-extension file)
                          (vl-filename-extension file) ".dat")))
      (if (findfile dst) (vl-file-delete dst))    ; vl-file-copy won't overwrite
      (if (vl-file-copy file dst) dst))))

;; Get the first CNT bytes of the photo, trying, in order: a straight ADODB
;; read; an ADODB read of a local copy (unreadable network paths); a plain
;; text-mode read (ADODB blocked).
;;   success -> (list bytes path note)   PATH = what actually got read, so the
;;              tail scan reads the same thing; NOTE = a line to print, or nil
;;   failure -> (list nil nil nil reason-lines)   for the loud alert
(defun ddg-open-photo (file cnt / r lst path note tmp step msg pr)
  (setq r (ddg-adodb-read file cnt nil))
  (if (car r)
    (setq lst (car r) path file)
    (setq step (cadr r) msg (caddr r)))
  ;; ADODB worked but on a copy? (mapped drive / locked original)
  (if (null lst)
    (progn
      (setq tmp (ddg-local-copy file))
      (if tmp
        (progn
          (setq r (ddg-adodb-read tmp cnt nil))
          (if (car r)
            (setq lst  (car r) path tmp
                  note "\n  (could not read it in place - used a local copy)"))))))
  ;; ADODB unusable entirely - let certutil turn the file into hex text
  (if (null lst)
    (progn
      (setq lst (ddg-certutil-read (if tmp tmp file) cnt))
      (if lst
        (setq path (if tmp tmp file)
              note "\n  (ADODB.Stream failed - read it through certutil instead)"))))
  ;; last resort: a plain text-mode read, which may stop early
  (if (null lst)
    (progn
      (setq pr (ddg-plain-read (if tmp tmp file) cnt))
      (if (car pr)
        (setq lst  (car pr) path (if tmp tmp file)
              note (strcat "\n  (ADODB.Stream failed - fell back to a plain read"
                           (if (cadr pr)
                             ", which stopped early at a 0x1A byte)"
                             ")"))))))
  (if lst
    (list lst path note)
    (list nil nil nil
      (append
        (list (strcat "File: " file) "")
        (if (findfile file)
          (list "AutoCAD CAN see the file, so this is not a missing path -"
                "it could not be read into memory."
                "")
          (list "AutoCAD cannot even find that path."
                ""))
        (if step
          (list (strcat "ADODB.Stream failed trying to " step ".")
                (if msg (strcat "Windows said: " msg) ""))
          '())
        (list ""
              "Run DDTEST on this same file - it walks every step and"
              "reports exactly what your PC allows.")))))

;; ===========================================================================
;;  XMP route (all modern DJI aircraft) - the image carries a text packet like
;;    drone-dji:AbsoluteAltitude="+247.66"
;;    drone-dji:GpsLatitude="+32.7157380"  drone-dji:GpsLongtitude="-117.16..."
;;  ("GpsLongtitude" is DJI's own long-standing typo; newer firmware also
;;   writes the correctly-spelt tag - both are checked.)
;;  The packet is found by content, not by container, so JPEG APP1 and PNG
;;  iTXt chunks both work: anchor on "<x:xmpmeta" (any container), then the
;;  JPEG APP1 signature, then the DJI namespace itself as a last resort.
;; ===========================================================================

;; the XMP packet (as one printable string), or "" if the file has none
(defun ddg-xmp-text (lst / rest)
  (setq rest (ddg-scan-to lst (vl-string->list "<x:xmpmeta")))
  (if (null rest)
    (setq rest (ddg-scan-to lst (vl-string->list "ns.adobe.com/xap/1.0/"))))
  (if (null rest)
    (setq rest (ddg-scan-to lst (vl-string->list "drone-dji:"))))
  (if rest (ddg-grab-text rest 6144) ""))

;; value of   TAG="..."   (DJI's attribute form) or   <ns:TAG>...</ns:TAG>
;; (the element form some converters re-write XMP into), or nil
(defun ddg-xmp-attr (txt tag / pos rest end)
  (setq pos (vl-string-search (strcat tag "=\"") txt))
  (if pos
    (progn
      (setq rest (substr txt (+ pos (strlen tag) 3)))  ; just past the ="
      (setq end (vl-string-search "\"" rest))
      (if end (substr rest 1 end)))
    (progn
      (setq pos (vl-string-search (strcat tag ">") txt))
      (if pos
        (progn
          (setq rest (substr txt (+ pos (strlen tag) 2)))   ; just past the >
          (setq end (vl-string-search "<" rest))
          (if end (substr rest 1 end)))))))

;; "+18.90" / "-117.16" / "18.90" -> real, or nil
(defun ddg-numstr (s)
  (setq s (vl-string-trim " " s))
  (if (and (> (strlen s) 0) (= "+" (substr s 1 1))) (setq s (substr s 2)))
  (if (> (strlen s) 0) (distof s 2)))

(defun ddg-xmp-num (txt tag / s)
  (if (setq s (ddg-xmp-attr txt tag)) (ddg-numstr s)))

;; ===========================================================================
;;  EXIF route (fallback) - parse the binary GPS IFD out of the APP1 segment.
;;  Handles both byte orders; every read is nil-safe so a truncated or odd
;;  file just returns nils instead of crashing.
;; ===========================================================================

;; byte at OFF (0-255), or nil past the end
(defun ddg-b (lst off / b)
  (if (setq b (nth off lst))
    (if (< b 0) (+ b 256) b)))

(defun ddg-u16 (lst off le / a b)
  (setq a (ddg-b lst off) b (ddg-b lst (1+ off)))
  (if (and a b) (if le (+ a (* 256 b)) (+ (* 256 a) b))))

;; 32-bit value as a REAL (AutoLISP ints are 32-bit signed - a raw u32 can overflow)
(defun ddg-u32 (lst off le / a b c d)
  (setq a (ddg-b lst off)       b (ddg-b lst (+ off 1))
        c (ddg-b lst (+ off 2)) d (ddg-b lst (+ off 3)))
  (if (and a b c d)
    (if le
      (+ a (* 256.0 b) (* 65536.0 c) (* 16777216.0 d))
      (+ d (* 256.0 c) (* 65536.0 b) (* 16777216.0 a)))))

;; 32-bit value as an INT for use as an offset; nil if missing or absurd
(defun ddg-u32i (lst off le / r)
  (if (and (setq r (ddg-u32 lst off le)) (< r 1.0e9)) (fix r)))

;; unsigned rational (u32 numerator, u32 denominator) -> real, or nil
(defun ddg-rat (lst off le / n d)
  (if off
    (progn
      (setq n (ddg-u32 lst off le) d (ddg-u32 lst (+ off 4) le))
      (if (and n d (/= d 0.0)) (/ n d)))))

;; find TAG in the IFD at offset IFD; return the offset of its 12-byte entry
(defun ddg-ifd-find (lst ifd le tag / n i e r)
  (if (setq n (ddg-u16 lst ifd le))
    (progn
      (setq i 0)
      (while (and (< i n) (null r))
        (setq e (+ ifd 2 (* 12 i)))
        (if (equal (ddg-u16 lst e le) tag) (setq r e))
        (setq i (1+ i)))))
  r)

;; GPS coordinate entry (3 rationals: deg min sec) -> decimal degrees
(defun ddg-gps-coord (lst ent le / off d m s)
  (if (setq off (ddg-u32i lst (+ ent 8) le))
    (progn
      (setq d (ddg-rat lst off le)
            m (ddg-rat lst (+ off 8) le)
            s (ddg-rat lst (+ off 16) le))
      (if (and d m s) (+ d (/ m 60.0) (/ s 3600.0))))))

;; the character of a GPS*Ref entry ("N"/"S"/"E"/"W"), or nil if absent.
;; These are ASCII fields of count 2, so the value sits inline in the entry.
(defun ddg-refchar (lst ent / b)
  (if (setq b (ddg-b lst (+ ent 8)))
    (if (and (> b 32) (< b 127)) (chr b))))

;; does REST start with a TIFF header?  ("II" 42 0  /  "MM" 0 42) -> REST or nil
(defun ddg-tiff-at (rest / b0 b1)
  (setq b0 (ddg-b rest 0) b1 (ddg-b rest 1))
  (cond
    ((and (equal b0 73) (equal b1 73)
          (equal (ddg-b rest 2) 42) (equal (ddg-b rest 3) 0)) rest)
    ((and (equal b0 77) (equal b1 77)
          (equal (ddg-b rest 2) 0) (equal (ddg-b rest 3) 42)) rest)))

;; find the EXIF TIFF block whatever the container:
;;   * a bare .TIF file        - TIFF header at byte 0
;;   * JPEG (and HEIC) style   - "Exif" 0 0, then the TIFF header
;;   * PNG eXIf chunk          - the TIFF header directly follows the type
;; A match is only accepted if a valid TIFF magic follows, so a stray "Exif"
;; inside compressed image data is skipped and the scan continues.
(defun ddg-find-tiff (lst / tif rest)
  (setq tif (ddg-tiff-at lst))
  (setq rest lst)
  (while (and (null tif)
              (setq rest (ddg-scan-to rest (vl-string->list "Exif"))))
    (if (and (equal (ddg-b rest 0) 0) (equal (ddg-b rest 1) 0))
      (setq tif (ddg-tiff-at (cddr rest)))))
  (setq rest lst)
  (while (and (null tif)
              (setq rest (ddg-scan-to rest (vl-string->list "eXIf"))))
    (setq tif (ddg-tiff-at rest)))
  tif)

;; TIFF header -> IFD0 -> GPS IFD; returns (lat lon alt-metres), any may be nil
(defun ddg-exif-gps (lst / tif le ifd0 ent gps lat lon altm latref lonref r)
  (setq tif (ddg-find-tiff lst))
  (if tif
    (progn
      (setq le (equal (ddg-b tif 0) 73))       ; "II" little / "MM" big endian
      (setq ifd0 (ddg-u32i tif 4 le))
      (if ifd0 (setq ent (ddg-ifd-find tif ifd0 le 34853)))  ; 0x8825 GPS IFD
      (if ent  (setq gps (ddg-u32i tif (+ ent 8) le)))
      (if gps
        (progn
          (if (setq ent (ddg-ifd-find tif gps le 2))         ; GPSLatitude
            (setq lat (ddg-gps-coord tif ent le)))
          (if (and (setq ent (ddg-ifd-find tif gps le 1))    ; GPSLatitudeRef
                   (setq r (ddg-refchar tif ent)))
            (setq latref (strcase r)))
          (if (and lat (equal latref "S")) (setq lat (- lat)))
          (if (setq ent (ddg-ifd-find tif gps le 4))         ; GPSLongitude
            (setq lon (ddg-gps-coord tif ent le)))
          (if (and (setq ent (ddg-ifd-find tif gps le 3))    ; GPSLongitudeRef
                   (setq r (ddg-refchar tif ent)))
            (setq lonref (strcase r)))
          (if (and lon (equal lonref "W")) (setq lon (- lon)))
          (if (setq ent (ddg-ifd-find tif gps le 6))         ; GPSAltitude
            (setq altm (ddg-rat tif (ddg-u32i tif (+ ent 8) le) le)))
          (if (and altm (setq ent (ddg-ifd-find tif gps le 5))
                   (equal (ddg-b tif (+ ent 8)) 1))          ; below sea level
            (setq altm (- altm)))))))
  ;; 4th: was an EXIF block found at all?  5th/6th: the hemisphere letters,
  ;; nil when the file simply does not record them - in which case the SIGN
  ;; of the coordinate is unknown, not positive.
  (list lat lon altm (if tif T) latref lonref))

;; everything the file tells us: (absalt-m lat lon xmp-found exif-found)
;; XMP text packet first (JPEG APP1 / PNG iTXt), the binary EXIF GPS block
;; filling any gaps (JPEG APP1 / PNG eXIf / bare TIFF). The last two flags
;; say whether an XMP packet / EXIF block was present at all - failure
;; reporting uses them to tell "stripped file" apart from "metadata without
;; GPS".
(defun ddg-read-meta (lst / xtxt exif absm lat lon xmpf tiff lonok altmsl)
  (setq xtxt (ddg-xmp-text lst))
  (setq xmpf (> (strlen xtxt) 0))
  (setq absm (ddg-xmp-num xtxt "AbsoluteAltitude")
        lat  (ddg-xmp-num xtxt "GpsLatitude")
        lon  (ddg-xmp-num xtxt "GpsLongitude"))
  (if (null lon) (setq lon (ddg-xmp-num xtxt "GpsLongtitude")))
  (if lon (setq lonok T))              ; XMP writes the sign into the number
  (if absm (setq altmsl T))            ; XMP AbsoluteAltitude IS sea-level
  (if (or (null lat) (null lon) (null absm))
    (progn
      (setq exif (ddg-exif-gps lst))
      (if (null lat)  (setq lat  (nth 0 exif)))
      (if (null lon)
        (progn
          (setq lon (nth 1 exif))
          (if (nth 5 exif) (setq lonok T))))   ; only if E/W was recorded
      ;; EXIF GPSAltitude is left un-flagged: plenty of DJI models write the
      ;; height above the TAKE-OFF point into it rather than height above sea
      ;; level, so which one it is has to be worked out from the numbers.
      (if (null absm) (setq absm (nth 2 exif)))
      (setq tiff (nth 3 exif))))
  (list absm lat lon xmpf tiff lonok altmsl))

;; ===========================================================================
;;  HTTP + JSON (MSXML2.XMLHTTP ActiveX; synchronous GET)
;; ===========================================================================

;; one attempt with a given ProgID.  Returns (list rank payload):
;;   rank 2 - HTTP 200, payload = the response text
;;   rank 1 - reached a server but got a bad answer (payload = how it failed)
;;   rank 0 - the request never completed        (payload = how it failed)
(defun ddg-http-try (prog url / xh err txt sts)
  (setq err
    (vl-catch-all-apply
      '(lambda ()
         (setq xh (vlax-create-object prog))
         (vlax-invoke-method xh 'Open "GET" url :vlax-false)
         ;; some builds want (Send) bare, some want an (empty) body argument
         (if (vl-catch-all-error-p
               (vl-catch-all-apply '(lambda () (vlax-invoke-method xh 'Send)) '()))
           (vlax-invoke-method xh 'Send ""))
         (setq sts (vlax-get-property xh 'Status))
         (setq txt (vlax-get-property xh 'ResponseText)))
      '()))
  (if xh (vl-catch-all-apply 'vlax-release-object (list xh)))
  (cond
    ((vl-catch-all-error-p err)
     (list 0 (if xh
               "no answer (no internet / DNS / firewall / timeout)"
               (strcat prog " is not available on this PC"))))
    ((not (and (numberp sts) (= sts 200)))
     (list 1 (strcat "server answered HTTP "
                     (if (numberp sts) (itoa (fix sts)) "?")
                     " instead of 200")))
    ((or (null txt) (= (strlen txt) 0))
     (list 1 "server sent back an empty response"))
    (t (list 2 txt))))

;; GET URL trying several ProgIDs (XMLHTTP follows the office/IE proxy
;; settings; ServerXMLHTTP is the last resort).
;; Returns (list T text) on success, else (list nil how-it-failed) - the
;; reason kept is from the attempt that got the furthest.
(defun ddg-http-get (url / best r)
  (foreach prog '("MSXML2.XMLHTTP.6.0" "MSXML2.XMLHTTP" "MSXML2.ServerXMLHTTP.6.0")
    (if (or (null best) (< (car best) 2))
      (progn
        (setq r (ddg-http-try prog url))
        (if (or (null best) (> (car r) (car best)))
          (setq best r)))))
  (if (= (car best) 2)
    (list T (cadr best))
    (list nil (cadr best))))

;; first number that follows KEY in TXT - skips :, =, [, quotes and blanks in
;; between; nil on null / absent
(defun ddg-num-after (txt key / pos rest len i numstr)
  (setq pos (vl-string-search key txt))
  (if pos
    (progn
      (setq rest (substr txt (+ pos (strlen key) 1))   ; just past the key
            len  (strlen rest)
            i    1)
      (while (and (<= i len)
                  (member (substr rest i 1) '(" " ":" "=" "[" "\"" "\t")))
        (setq i (1+ i)))
      (setq numstr "")
      (while (and (<= i len)
                  (member (substr rest i 1)
                          '("-" "+" "." "0" "1" "2" "3" "4"
                            "5" "6" "7" "8" "9" "e" "E")))
        (setq numstr (strcat numstr (substr rest i 1)))
        (setq i (1+ i)))
      (if (> (strlen numstr) 0) (ddg-numstr numstr)))))

;; JSON flavour: the key sits in quotes ("value":"296.61" / "elevation": 251.3)
(defun ddg-json-num (txt key)
  (ddg-num-after txt (strcat "\"" key "\"")))

;; ground elevation in FEET at LAT/LON. Services tried in order; each answer
;; is sanity-ranged before being trusted.
;;   success -> (list feet source-name)
;;   failure -> (list nil notes)   notes = one "service: how it failed" line
;;                                 for every service that was tried
(defun ddg-ground-elev (lat lon / la lo r v res notes)
  (setq la (ddg-n7 lat) lo (ddg-n7 lon) notes '())
  ;; 1) USGS EPQS - 3DEP bare earth, NAVD88, answers in FEET. US only.
  (setq r (ddg-http-get (strcat "https://epqs.nationalmap.gov/v1/json?x=" lo
                                "&y=" la "&wkid=4326&units=Feet")))
  (if (car r)
    (progn
      (setq v (ddg-json-num (cadr r) "value"))
      (if (and v (> v -1500.0) (< v 25000.0))          ; filters the -1000000
        (setq res (list v "USGS 3DEP"))                ; no-data flag
        (setq notes (cons "USGS EPQS: answered, but has no elevation for this spot (outside US coverage?)"
                          notes))))
    (setq notes (cons (strcat "USGS EPQS: " (cadr r)) notes)))
  ;; 2) OpenTopoData NED 10 m - metres. US only.
  (if (null res)
    (progn
      (setq r (ddg-http-get (strcat "https://api.opentopodata.org/v1/ned10m?locations="
                                    la "," lo)))
      (if (car r)
        (progn
          (setq v (ddg-json-num (cadr r) "elevation"))
          (if (and v (> v -500.0) (< v 7000.0))
            (setq res (list (* v ddg-m->ft) "OpenTopoData NED10m"))
            (setq notes (cons "OpenTopoData: answered, but has no elevation for this spot (outside US coverage?)"
                              notes))))
        (setq notes (cons (strcat "OpenTopoData: " (cadr r)) notes)))))
  ;; 3) Open-Elevation - SRTM ~30 m, metres. Worldwide fallback.
  (if (null res)
    (progn
      (setq r (ddg-http-get (strcat "https://api.open-elevation.com/api/v1/lookup?locations="
                                    la "," lo)))
      (if (car r)
        (progn
          (setq v (ddg-json-num (cadr r) "elevation"))
          (if (and v (> v -500.0) (< v 7000.0))
            (setq res (list (* v ddg-m->ft) "Open-Elevation SRTM"))
            (setq notes (cons "Open-Elevation: answered without a usable elevation"
                              notes))))
        (setq notes (cons (strcat "Open-Elevation: " (cadr r)) notes)))))
  (if res res (list nil (reverse notes))))

;; ===========================================================================
;;  Drawing annotation helpers
;; ===========================================================================

;; round-half-away-from-zero (AutoLISP has no built-in ROUND; FIX truncates
;; toward zero, so nudge by +/- 0.5 first)
(defun ddg-round (x) (fix (+ x (if (>= x 0.0) 0.5 -0.5))))

;; annotation text height: defaults to the drawing's current TEXTSIZE, then
;; remembers a per-drawing override under the same store as H - same
;; "current value in <brackets>, Enter keeps it" idiom as DDSET/DDFIX/DDALT.
;; With BACK non-nil the prompt also takes Back (Undo works too),
;; returning the symbol DDG-BACK.
(defun ddg-txt-height (back / cur ht)
  (setq cur (ddg-get "TXTHT"))
  (if (null cur) (setq cur (getvar "TEXTSIZE")))
  (if (or (null cur) (<= cur 0.0)) (setq cur 1.0))   ; TEXTSIZE can legitimately be 0
  (if back (initget "Back Undo"))
  (setq ht (getreal (strcat "\nAnnotation text height <" (ddg-n1 cur) ">"
                            (if back " [Back]" "") ": ")))
  (if (= (type ht) 'STR)
    'DDG-BACK
    (progn
      (if (or (null ht) (<= ht 0.0)) (setq ht cur))
      (ddg-put "TXTHT" ht)
      ht)))

;; erase everything created after entity MARK (nil = an empty drawing)
;; - the rollback when a Back takes a placed report down again
(defun ddg-eraseafter (mark / en nx)
  (setq en (if mark (entnext mark) (entnext)))
  (while en
    (setq nx (entnext en))
    (if (entget en) (entdel en))
    (setq en nx)))

;; place LINES (strings, top to bottom) as stacked single-line TEXT entities
;; starting at BASEPT-UCS (a point in the CURRENT UCS, e.g. straight out of
;; getpoint). Each point is converted UCS -> WCS right before entmake (entity
;; data needs WCS; mirrors the (trans base 0 1) idiom DroneDistortion.lsp
;; uses the other way around before feeding a point to a command). Returns T
;; if every line was created.
(defun ddg-place-text (basept-ucs lines height layer style / y pt ok)
  (setq y 0.0 ok T)
  (foreach ln lines
    (setq pt (list (car basept-ucs) (- (cadr basept-ucs) y) (caddr basept-ucs)))
    (if (null (entmake (list '(0 . "TEXT")
                              (cons 8 layer)
                              (cons 10 (trans pt 1 0))     ; UCS -> WCS
                              (cons 40 height)
                              (cons 1 ln)
                              (cons 7 style))))
      (setq ok nil))
    (setq y (+ y (* height 1.667))))   ; AutoCAD's standard single-line spacing
  ok)

;; ---------------------------------------------------------------------------
;;  DDGPS : pick the drone photo -> read GPS -> click a point -> look up
;;          ground elevation -> place the height report -> save H
;; ---------------------------------------------------------------------------
(defun c:DDGPS ( / *error* def c file rd rpath lst meta fsize absm lat lon xmpf tiff lonok
                   altmsl hmsl hrel okmsl okrel mode
                   pt g gft gsrc absft hraw hsel ht lines placed ans
                   stage done manual mark)
  (defun *error* (m)
    (if (and m (not (wcmatch (strcase m) "*BREAK*,*CANCEL*,*QUIT*,*EXIT*")))
      (princ (strcat "\nError: " m)))
    (princ))

  ;; 1) pick the photo - start in the last-used folder, else the H: drive
  (setq def (getenv "DDGPS_LastDir"))
  (if (or (null def) (= def "") (not (vl-file-directory-p def)))
    (setq def (if (vl-file-directory-p "H:/") "H:/" "")))
  (if (> (strlen def) 0)
    (progn
      (setq c (substr def (strlen def) 1))
      (if (and (/= c "/") (/= c "\\")) (setq def (strcat def "\\")))))
  (setq file (getfiled "Select the ORIGINAL drone photo (PNG / JPG / TIF)" def
                       "png;jpg;jpeg;tif;tiff" 16))
  (cond
    ((null file) (princ "\nNo file selected."))
    (t
     (if (vl-filename-directory file)
       (setenv "DDGPS_LastDir" (vl-filename-directory file)))
     (princ "\nReading the photo ...")
     ;; metadata usually sits up front; ddg-open-photo falls back to a local
     ;; copy if the file cannot be read where it sits (mapped-drive trouble)
     (setq rd    (ddg-open-photo file 262144)
           lst   (nth 0 rd)
           rpath (nth 1 rd))
     (cond
       ((null lst)
        (ddg-fail "COULD NOT READ THE FILE" (nth 3 rd)))
       (t
        (if (nth 2 rd) (princ (nth 2 rd)))
        ;; 2) XMP first (every modern DJI), binary EXIF GPS block as fallback
        (setq meta (ddg-read-meta lst)
              absm (nth 0 meta) lat  (nth 1 meta) lon  (nth 2 meta)
              xmpf (nth 3 meta) tiff (nth 4 meta) lonok (nth 5 meta)
              altmsl (nth 6 meta))
        ;; some PNG writers park the metadata after the image data - if the
        ;; front window came up short, scan the tail of the file too
        (if (and (or (null lat) (null lon) (null absm))
                 (setq fsize (vl-file-size rpath))
                 (> fsize 262144)
                 (setq lst (car (ddg-file-bytes rpath 262144 T))))
          (progn
            (setq meta (ddg-read-meta lst))
            (if (null absm) (setq absm (nth 0 meta)))
            (if (null lat)  (setq lat  (nth 1 meta)))
            (if (null lon)  (setq lon  (nth 2 meta)))
            (if (nth 3 meta) (setq xmpf T))
            (if (nth 4 meta) (setq tiff T))
            (if (nth 5 meta) (setq lonok T))
            (if (nth 6 meta) (setq altmsl T))))
        ;; 2b) say EXACTLY what is wrong if the file cannot be used - this is
        ;; a hard stop, no rescue: use the file exactly as it came off the
        ;; drone. Everything past this point lives in the final (t ...)
        ;; branch below, so a failure here truly stops the command.
        (cond
          ((and (or (null lat) (null lon)) (not xmpf) (not tiff))
           (ddg-fail "NO CAMERA METADATA IN THIS FILE"
             (list (strcat "File: " (ddg-fname file))
                   ""
                   "No XMP packet and no EXIF block anywhere in the file"
                   "(searched the first 256 KB and the last 256 KB)."
                   ""
                   "This copy was saved WITHOUT metadata - screenshots,"
                   "video frame grabs and most export / share / convert"
                   "steps strip it. Use the file exactly as it came off"
                   "the drone.")))
          ((or (null lat) (null lon))
           (ddg-fail "NO GPS DATA FOUND"
             (list (strcat "File: " (ddg-fname file))
                   ""
                   (strcat "The file DOES contain camera metadata ("
                           (cond ((and xmpf tiff) "an XMP packet and an EXIF block")
                                 (xmpf "an XMP packet")
                                 (t "an EXIF block"))
                           ")")
                   "but there is no GPS position in it."
                   ""
                   "Either the drone had no GPS fix recorded, or the"
                   "conversion that made this file kept only part of the"
                   "metadata. Use the file exactly as it came off the drone.")))
          ((and (equal lat 0.0 1e-9) (equal lon 0.0 1e-9))
           (ddg-fail "NO GPS FIX"
             (list (strcat "File: " (ddg-fname file))
                   ""
                   "The GPS position stored in the file is 0, 0 - the drone"
                   "had no satellite fix when this shot was taken."
                   ""
                   "Pick a different shot from the same flight.")))
          ((or (> (abs lat) 90.0) (> (abs lon) 180.0))
           (ddg-fail "BAD GPS DATA"
             (list (strcat "File: " (ddg-fname file))
                   ""
                   (strcat "The stored GPS position (" (ddg-n7 lat) ", "
                           (ddg-n7 lon) ")")
                   "is not a valid latitude / longitude - corrupt metadata.")))
          ((null absm)
           (ddg-fail "NO ALTITUDE DATA"
             (list (strcat "File: " (ddg-fname file))
                   ""
                   (strcat "GPS position found (" (ddg-n7 lat) ", "
                           (ddg-n7 lon) "), but the file holds no")
                   "AbsoluteAltitude / EXIF GPSAltitude."
                   ""
                   "Use the file exactly as it came off the drone, or set H"
                   "manually with DDSET.")))
          (t
           ;; 2c) all good - show what came from the file
           ;; Some files record the coordinate but not the E/W hemisphere, so
           ;; the sign is unknown. Every job this tool is used for is in the
           ;; United States, so take the western hemisphere - the alternative
           ;; silently moves a Pennsylvania pool to China. Assumed, not asked,
           ;; but said out loud, because it IS an assumption.
           (if (null lonok)
             (progn
               (setq lon (- (abs lon)))
               (princ "\n  NOTE: the photo does not record E/W - assuming WEST (United States).")))
           (princ "\n--- position & altitude ------------------------------------")
           (princ (strcat "\n  GPS position     : " (ddg-n7 lat) ", " (ddg-n7 lon)))
           ;; Jobs are in the United States, so anything outside it is worth
           ;; flagging - it usually means a hemisphere or a datum is wrong.
           ;; A warning only: the lookup still runs, and the worldwide service
           ;; will answer if the site really is abroad.
           (if (not (and (> lat 17.0) (< lat 72.0)
                         (> lon -180.0) (< lon -64.0)))
             (princ (strcat "\n  WARNING: that position is not in the United States."
                            "\n           Check the photo - a wrong E/W reference looks exactly like this.")))
           (princ (strcat "\n  AbsoluteAltitude : " (ddg-n1 (* absm ddg-m->ft))
                          " ft above sea level   (" (ddg-n1 absm) " m)"))
           ;; 3)-7) staged: Back (or Undo) at a later prompt re-opens
           ;; the previous one - the lookup and the altitude reasoning
           ;; re-run on the way forward
           (setq stage 1 done nil manual nil)
           (while (not done)
             (cond

               ;; 3) click a point in the drawing for the report
               ((= stage 1)
                (setq pt (getpoint "\nPick a point in the drawing for the height report: "))
                (if (null pt)
                  (progn (princ "\nAborted - no point picked.") (setq done T))
                  (setq stage 2)))

               ;; 4) ground elevation at the photo position
               ((= stage 2)
                (princ "\nLooking up ground elevation (internet, a few seconds) ...")
                (setq g (ddg-ground-elev lat lon) manual nil)
                (if (car g)
                  (setq gft (car g) gsrc (cadr g) stage 4)
                  (progn
                    (ddg-fail "ELEVATION LOOKUP FAILED"
                      (append
                        (list (strcat "No ground elevation could be fetched for "
                                      (ddg-n7 lat) ", " (ddg-n7 lon) ":")
                              "")
                        (cadr g)
                        (list ""
                              "Check the internet connection (DDELEV is a quick"
                              "test), or type the site elevation by hand at the"
                              "next prompt.")))
                    (setq stage 3))))
               ((= stage 3)
                (initget "Back Undo")
                (setq gft (getreal "\nGround elevation at the site in FEET, if you know it (Enter to abort) [Back]: "))
                (cond
                  ((= (type gft) 'STR) (setq stage 1))
                  ((null gft) (princ "\nAborted - H unchanged.") (setq done T))
                  (t (setq gsrc "entered by hand" manual T stage 4))))

               ((= stage 4)
                (princ (strcat "\n  Ground elevation : " (ddg-n1 gft) " ft   [" gsrc "]"))
                ;; 5) work out WHICH altitude the photo actually recorded.
                ;; XMP AbsoluteAltitude is sea-level by definition. EXIF
                ;; GPSAltitude is not so simple: many DJI models write the
                ;; height above the TAKE-OFF point into that tag instead. Both
                ;; readings are computed and the physically possible one wins
                ;; - a drone cannot fly below the ground, and cannot legally
                ;; fly above 400 ft AGL.
                (setq absft (* absm ddg-m->ft)
                      hmsl  (- absft gft)          ; if it is above sea level
                      hrel  absft                  ; if it is above take-off
                      okmsl (and (> hmsl 1.0) (<= hmsl 400.0))
                      okrel (and (> hrel 1.0) (<= hrel 400.0)))
                (cond
                  ((or altmsl (and okmsl (not okrel)))
                   (setq hraw hmsl mode "MSL"))
                  ((and okrel (not okmsl))
                   (setq hraw hrel mode "REL"))
                  (okmsl                            ; both possible - prefer MSL
                   (setq hraw hmsl mode "MSL?"))
                  (t (setq hraw nil)))
                (setq hsel (if hraw (float (ddg-round hraw))))
                (cond
                  ((or (null hsel) (<= hsel 0.0))
                   (ddg-fail "ALTITUDE DOES NOT MAKE SENSE"
                     (list (strcat "Photo altitude    : " (ddg-n1 absft) " ft")
                           (strcat "Ground elevation  : " (ddg-n1 gft) " ft")
                           ""
                           "Neither reading of that altitude is possible:"
                           (strcat "  as above sea level -> " (ddg-n1 hmsl)
                                   " ft above ground")
                           (strcat "  as above take-off  -> " (ddg-n1 hrel) " ft")
                           ""
                           "Nothing was saved or drawn. Set H with DDSET, or"
                           "back-solve it with DDCAL."))
                   (setq done T))
                  (t
                   (if (= mode "REL")
                     (progn
                       (princ "\n  The photo altitude is BELOW the ground here, so it is not a")
                       (princ "\n  sea-level figure - it is the height above the TAKE-OFF point.")
                       (princ (strcat "\n  Using it directly:  H = " (ddg-n1 hsel) " ft"))
                       (princ "\n  (true if the drone took off at deck level - see DDALT/DDCAL)"))
                     (progn
                       (if (= mode "MSL?")
                         (princ "\n  NOTE: both readings of the altitude are possible; taking it as sea-level."))
                       (princ (strcat "\n  " (ddg-n1 absft) " - " (ddg-n1 gft) " = "
                                      (ddg-n1 hraw) " ft  ->  H = " (ddg-n1 hsel) " ft"))))
                   (setq stage 5))))

               ;; 6) place the report in the drawing
               ((= stage 5)
                (setq ht (ddg-txt-height T))
                (if (eq ht 'DDG-BACK)
                  (setq stage (if manual 3 1))
                  (progn
                    ;; the middle lines say which reading of the altitude
                    ;; was used, so the drawing carries its own
                    ;; justification
                    (setq lines
                      (if (= mode "REL")
                        (list
                          (strcat "GPS position: " (ddg-n7 lat) ", " (ddg-n7 lon))
                          (strcat "Drone altitude: " (ddg-n1 absft) " ft above take-off")
                          (strcat "Ground elevation (MSL): " (ddg-n1 gft) " ft   [" gsrc "]")
                          "Photo altitude is not sea-level referenced - used as-is"
                          (strcat "Height above grade: " (itoa (fix hsel)) " ft"))
                        (list
                          (strcat "GPS position: " (ddg-n7 lat) ", " (ddg-n7 lon))
                          (strcat "Drone altitude (MSL): " (ddg-n1 absft) " ft")
                          (strcat "Ground elevation (MSL): " (ddg-n1 gft) " ft   [" gsrc "]")
                          (strcat (ddg-n1 absft) " - " (ddg-n1 gft) " = " (ddg-n1 hraw) " ft")
                          (strcat "Height above grade: " (itoa (fix hsel)) " ft"))))
                    (setq mark (entlast))
                    (setq placed (ddg-place-text pt lines ht (getvar "CLAYER") (getvar "TEXTSTYLE")))
                    (if (null placed)
                      (ddg-fail "COULD NOT CREATE THE ANNOTATION TEXT"
                        (list "entmake failed partway through - check whether"
                              "the current layer is locked or frozen, or the"
                              "current text style is invalid."
                              ""
                              "H is still valid below - you can still save it.")))
                    (setq stage 6))))

               ;; 7) save H for DDFIX - Back takes the placed report
               ;; down again and re-asks the text height
               (t
                (initget "Yes No Back Undo")
                (setq ans (getkword (strcat "\nSave H = " (ddg-n1 hsel)
                                            " ft for DDFIX? [Yes/No/Back] <Yes>: ")))
                (if (null ans) (setq ans "Yes"))
                (cond
                  ((member ans '("Back" "Undo"))
                   (ddg-eraseafter mark)
                   (setq stage 5))
                  ((= ans "Yes")
                   (ddg-put "H" hsel)
                   (ddg-put "GPS_LAT" lat)
                   (ddg-put "GPS_LON" lon)
                   (ddg-put "GPS_GROUND" gft)
                   (ddg-put "GPS_SRC" gsrc)
                   (princ (strcat "\nSaved drone height  H = " (ddg-n1 hsel)
                                  " ft   (DDFIX now offers it as the default)"))
                   (princ (strcat "\nDistortion rate: ~" (rtos (/ 100.0 hsel) 2 3)
                                  "% size change per unit of height."))
                   (setq done T))
                  (t (princ "\nH unchanged.") (setq done T))))))))))))
  (princ))

;; ---------------------------------------------------------------------------
;;  DDELEV : ground elevation at a typed latitude / longitude
;; ---------------------------------------------------------------------------
(defun c:DDELEV ( / lat lon g stage done)
  ;; staged: Back (or Undo) at the longitude re-asks the latitude
  (setq stage 1 done nil)
  (while (not done)
    (if (= stage 1)
      (progn
        (setq lat (getreal "\nLatitude  (decimal degrees, negative = South): "))
        (setq stage 2))
      (progn
        (initget "Back Undo")
        (setq lon (getreal "\nLongitude (decimal degrees, negative = West) [Back]: "))
        (if (= (type lon) 'STR) (setq stage 1) (setq done T)))))
  (cond
    ((or (null lat) (null lon)) (princ "\nNeed both numbers."))
    ((or (> (abs lat) 90.0) (> (abs lon) 180.0))
     (princ "\nThat is not a valid latitude / longitude."))
    (t
     (princ "\nLooking up ground elevation ...")
     (setq g (ddg-ground-elev lat lon))
     (if (car g)
       (princ (strcat "\nGround elevation: " (ddg-n1 (car g)) " ft   ("
                      (ddg-n1 (/ (car g) ddg-m->ft)) " m)   [" (cadr g) "]"))
       (ddg-fail "ELEVATION LOOKUP FAILED"
         (append
           (list (strcat "No ground elevation could be fetched for "
                         (ddg-n7 lat) ", " (ddg-n7 lon) ":")
                 "")
           (cadr g)
           (list ""
                 "Check the internet connection / firewall, then try again."))))))
  (princ))

;; ---------------------------------------------------------------------------
;;  DDTEST : why can't this PC read the photo?
;;  Walks every step DDGPS uses and reports what your machine actually allows.
;;  Run this once on a file that fails and send the report.
;; ---------------------------------------------------------------------------
(defun c:DDTEST ( / file out fsz r pr cu tmp lst n m)
  (setq file (getfiled "Pick the photo that will not read" "" "png;jpg;jpeg;tif;tiff" 16))
  (cond
    ((null file) (princ "\nNo file selected."))
    (t
     (setq out (list (strcat "File: " file) ""))
     ;; --- what AutoCAD itself can see ---
     (setq fsz (vl-file-size file))
     (setq out (append out
       (list (strcat "AutoCAD can find it   : " (ddg-yn (findfile file)))
             (strcat "Size on disk          : "
                     (if fsz (strcat (itoa fsz) " bytes") "unknown"))
             "")))
     ;; --- ADODB, step by step ---
     (setq r (ddg-adodb-read file 262144 nil))
     (setq out (append out
       (if (car r)
         (list (strcat "ADODB.Stream read     : OK, "
                       (itoa (length (car r))) " bytes"))
         (list "ADODB.Stream read     : FAILED"
               (strcat "   failed trying to " (cadr r))
               (if (caddr r) (strcat "   Windows said: " (caddr r)) "")))))
     (if (car r) (setq lst (car r)))
     ;; --- local copy ---
     (setq tmp (ddg-local-copy file))
     (setq out (append out
       (list (strcat "Copy to local temp    : " (ddg-yn tmp)))))
     (if (and (null lst) tmp)
       (progn
         (setq r (ddg-adodb-read tmp 262144 nil))
         (setq out (append out
           (list (strcat "ADODB on the copy     : "
                         (if (car r) "OK" "FAILED")))))
         (if (car r) (setq lst (car r)))))
     ;; --- certutil hex dump (works where ADODB is blocked) ---
     (setq cu (ddg-certutil-read (if tmp tmp file) 262144))
     (setq out (append out
       (list (strcat "certutil hex read     : "
                     (if cu (strcat "OK, " (itoa (length cu)) " bytes") "FAILED")))))
     (if cu (setq out (append out
       (list (strcat "   first bytes        : " (ddg-firstbytes cu 8)
                     (if (ddg-looks-jpeg cu)
                       "   (valid JPEG start)"
                       "   (NOT a JPEG start - these bytes are wrong)"))))))
     (if (null lst) (setq lst cu))
     ;; --- plain AutoLISP read ---
     (setq pr (ddg-plain-read (if tmp tmp file) 262144))
     (setq n (length (car pr)))
     (setq out (append out
       (list (strcat "Plain AutoLISP read   : "
                     (if (car pr) (strcat "OK, " (itoa n) " bytes") "FAILED")
                     (if (cadr pr) "  (stopped early at a 0x1A byte)" "")))))
     (if (car pr) (setq out (append out
       (list (strcat "   first bytes        : " (ddg-firstbytes (car pr) 8)
                     (if (ddg-looks-jpeg (car pr))
                       "   (valid JPEG start)"
                       "   (NOT a JPEG start)"))))))
     (if (null lst) (setq lst (car pr)))
     ;; --- does the file even carry metadata? ---
     (setq out (append out (list "")))
     (if lst
       (progn
         (setq m (ddg-read-meta lst))
         (setq out (append out
           (list (strcat "XMP packet in it      : "
                         (ddg-yn (> (strlen (ddg-xmp-text lst)) 0)))
                 (strcat "EXIF block in it      : "
                         (ddg-yn (ddg-find-tiff lst)))
                 (strcat "GPS position found    : "
                         (ddg-yn (and (nth 1 m) (nth 2 m))))
                 (strcat "   E/W recorded?      : " (ddg-yn (nth 5 m))
                         (if (and (nth 2 m) (null (nth 5 m)))
                           "  (sign unknown - DDGPS will ask)" ""))
                 (strcat "Altitude found        : "
                         (ddg-yn (nth 0 m)))))))
       (setq out (append out (list "Could not get ANY bytes out of this file."))))
     (ddg-report "DDGPS READ TEST" out)))
  (princ))

(princ "\nDrone Height from GPS v2.6 loaded  (pick a photo, click a point, place the height report).")
(princ "\n  Commands: DDGPS (photo -> click a point -> height report)   DDELEV (elevation at a lat/long)   DDTEST (why will this photo not read?)")
(princ)


;;; ======================================================================
;;; >>> FITABHD.lsp
;;; ======================================================================

;;; ======================================================================
;;; FITABHD.lsp  --  fit a TYPED pool template through surveyed points
;;; ----------------------------------------------------------------------
;;; For AutoCAD 2018 and later (plain AutoLISP, no external libraries).
;;;
;;; Commands:  FITABHD     ask what type of pool the survey is, fit that
;;;                        type's template through the points, then
;;;                        offer the standard-hopper pool bottom
;;;            FITABHDVER  print the loaded version
;;;
;;; SHARED BUILD: requires CALOFIN-LIB.lsp (load via CALOFIN-LOADER.lsp).
;;; Generic helpers live there under cal: - see STANDARDS.md.
;;;
;;; WHAT THE TYPE IS FOR.  The type is not a promise about the shape,
;;; it is what lets the survey be READ: it says which walls belong
;;; together, which corner is a corner, which end is an end.  The
;;; POINTS decide where all of that actually goes.  An AB pool is
;;; built, not drawn, so the points are imperfect - and the shape that
;;; comes out of them is meant to be imperfect too.  Every deviation
;;; the tool can draw is fitted FROM the points and kept only where
;;; they prove it: out of square, bowed walls, eased corners, an end
;;; that caved in.  Hold the template rigid and the error does not go
;;; away, it just moves into the points, where nobody can see it.
;;;
;;; ABHD traces whatever shape the survey points make.  FITABHD is its
;;; typed sibling: you TELL it what kind of typical pool was surveyed -
;;; Rectangle, Grecian, Roman, Oval, L, Lazy L or Round (POOL's own
;;; shape vocabulary) - and the type does half the work:
;;;
;;;   * Wall DIRECTIONS come from the template, never from the points.
;;;     A rectangle's walls come out dead parallel and square; a Lazy
;;;     L's bend walls sit at exactly 45 degrees.  The survey only says
;;;     WHERE each wall is, by an iterative nearest-wall fit.
;;;   * The pool's rotation is found automatically (every survey edge
;;;     votes, folded so parallel and perpendicular walls agree), and
;;;     every placement the type allows - four rotations, mirrored for
;;;     the chiral L shapes, eight rotations for the Lazy L - is tried;
;;;     the one that hugs the points best wins.  A placement whose
;;;     template collapsed (a wall fitted backwards) is thrown out
;;;     however well it scores.
;;;   * Corner treatments use the standard question (Square / Radius /
;;;     Cut / NotGiven) and the SIZE is measured from the points: one
;;;     shared fillet radius (or cut face) fitted over every corner
;;;     that turns hard enough to measure.  A Rectangle with Cut
;;;     corners rides the same eight-wall template as a Grecian.
;;;   * A GRECIAN'S CUT CORNERS MAY BE EASED: the nominal drawing is
;;;     sharp, but an as-built very often rounds the eight vertices.
;;;     Answer Radius (or Cut) at step 2 and one shared easing is
;;;     measured over all eight 45-degree corners, with the zone sized
;;;     to that gentler turn - and kept only when it beats the sharp
;;;     outline on the corner points by a clear margin, so noise never
;;;     invents a radius on a genuinely sharp pool.
;;;   * A ROMAN OR OVAL'S SIDE WALLS ARE NOT HELD PARALLEL.  A gunite
;;;     shell slumps as it cures, so one wall very often slants away
;;;     from the other; out of square, each answers its own points and
;;;     the two may lean up to fit:*cap-oos-max* (10 degrees) apart.
;;;     Each end cap is then fitted across the body AT ITS OWN END, and
;;;     the frame angle is fitted too - the edge vote cannot find the
;;;     body's axis when the walls disagree, and a crooked axis draws a
;;;     crooked flat end.
;;;   * AN ARC IS NOT PROMISED TO BE ONE RADIUS.  What a drawing
;;;     calls one R is, on a built shell, very often a run of arcs -
;;;     it slumps as it cures.  An arc a single radius cannot hold
;;;     within the typed tolerance is rebuilt as a polyline of arcs
;;;     whose joints sit on survey points, and the run keeps going
;;;     while each extra arc clearly earns its place, not just until
;;;     it scrapes inside the tolerance.  Every joint is held to
;;;     ABHD's own tangency window - fit:*tang-tol*, 8 degrees,
;;;     stretched through fit:*tang-steps* rather than abandoned - so
;;;     the run reads as a curve rather than a row of facets while
;;;     the POINTS still choose inside that window.  An end that
;;;     really is one radius stays one arc.
;;;   * Roman and Oval ends are found, not declared: square-end and
;;;     arc-end placements (one end and both ends) all compete, and a
;;;     both-ends fit must beat a single-ended one by a clear margin -
;;;     extra freedom is not evidence.  A Roman end reports its bulge
;;;     (S) and stubs (S1) like POOL draws them.
;;;   * NICE DIMENSIONS: each headline dimension - length, width,
;;;     corner radius, cut face, body length - is snapped to the first
;;;     friendly increment (whole feet, half feet, inches, half
;;;     inches) the points can live with: the snapped outline must
;;;     stay within the run tolerance, or move nothing more than
;;;     fit:*snap-eps* when an outlier already sits beyond it.  The
;;;     points outrank pretty numbers.
;;;
;;; The fitted outline previews on POOL-FIT with a hit report (points
;;; on the line, off within tolerance, beyond it - the strays ringed
;;; on FGStep, only FITABHD's own rings ever erased) and the fitted
;;; dimensions printed in feet and inches.  Keep it and it moves to
;;; the POOL layer in ByLayer colour, like ABHD's.
;;;
;;; THE POOL BOTTOM assumes a STANDARD HOPPER, so it is generated, not
;;; traced: pick which end is deep, type where the two breaks fall and
;;; the hopper's side and back offsets, and the bottom is drawn square
;;; to the pool's own frame - the deep break as the classic three
;;; collinear pieces (dashed stubs, solid run between the hopper
;;; corners), the hopper as the offset rectangle, dead-straight slope
;;; lines to the shallow break ends, and the K/L/M dimension string a
;;; foot off the deep break on the shallow side.  On an L or Lazy L
;;; the deep end picks which leg the hopper lives in, angled leg
;;; included.  A Round pool gets a concentric hopper ring instead.
;;; Anything fancier than a standard hopper is ABHD/ADAB's job.
;;;
;;; Everything is fitted on the 2D plane - Z coordinates are ignored.
;;; tests/test_fitabhd.py mirrors the whole engine in Python, and its
;;; structural checks hold this file to the conventions above.
;;; ======================================================================

;; Cover mode: the pool-bottom question answers No without being asked,
;; so a cover sheet is fitted to its perimeter and stops there.  Set by
;; FITABHDCOVER, cleared on both exits from c:FITABHD.
(setq fit:*nobottom* nil)

(setq *fitabhd-version* "v1.9")    ; announced on load; release_lisp.py
                                   ; reads this banner and stamps the
                                   ; dated twin in releases/ from it

;; ---- configuration ---------------------------------------------------
(setq fit:*pool-layer*  "POOL")    ; layer the kept fit and bottom go on
(setq fit:*point-layer* "POINTS")  ; layer holding plain survey POINTs
(setq fit:*point-block* "ab_pt")   ; block whose INSERTs mark survey
                                   ; points; insertion point = location
(setq fit:*pt-tag*      "number")  ; attribute tag carrying the point
                                   ; number, for the miss report
(setq fit:*out-layer*   "POOL-FIT"); layer the preview outline goes on
(setq fit:*miss-layer*  "FGStep")  ; layer the stray-point rings go on;
                                   ; may already be in use, so FITABHD
                                   ; stamps its objects and only ever
                                   ; erases its own
(setq fit:*miss-radius* 4.0)       ; radius of those rings (4 inches)
(setq fit:*exact-eps*   0.001)     ; duplicate-point fuzz (units)
(setq fit:*on-eps*      0.25)      ; a point within this of the outline
                                   ; counts as ON it (ABHD's threshold)
(setq fit:*tol-max*     2.0)       ; ceiling on the max-distance prompt
                                   ; (2 inches): looser than that and
                                   ; the fit is no longer a trace
(setq fit:*corner-zone* 18.0)      ; starting radius of the corner
                                   ; zones: points inside belong to the
                                   ; corner feature, not the walls
(setq fit:*zone-pad*    4.0)       ; the zone refit sizes itself to
                                   ; 1.2 x the fitted radius plus this
(setq fit:*icp-iters*   12)        ; assignment/update rounds per
                                   ; placement - each is cheap and the
                                   ; walls settle in well under this
(setq fit:*rad-iters*   15)        ; centre/radius rounds for a Round
(setq fit:*rad-max*     120.0)     ; fillet-radius search ceiling (10')
(setq fit:*rad-turn-min* (/ pi 3.0)) ; only corners turning at least
                                   ; this (60 deg) vote for the shared
                                   ; radius or cut: a 45-degree bend's
                                   ; fillet apex sits under an inch off
                                   ; the sharp corner, so its zone
                                   ; holds mostly wall points, which
                                   ; would drag the fit way off
(setq fit:*both-edge*   0.8)       ; a both-ends cap fit must beat the
                                   ; best single-ended one by this
                                   ; factor: a big flat arc can always
                                   ; shave a little error off a
                                   ; genuinely square end
(setq fit:*snap-eps*    0.02)      ; a nice-dim snap may move the fit
                                   ; at most this far beyond where it
                                   ; already sat when a stray point is
                                   ; past the tolerance anyway
(setq fit:*vsize-min*   1.0)       ; a fitted corner easing smaller
                                   ; than this reads as sharp
(setq fit:*miss-pct*    0.15)      ; the standard share of the points
                                   ; allowed to sit beyond the distance;
                                   ; asked per run, and what a snap to a
                                   ; whole foot is allowed to spend
(setq fit:*bow-min*     1.0)       ; a bow shallower than this reads as
                                   ; a straight wall - an inch over
                                   ; thirty feet is drafting noise, and
                                   ; survey scatter alone can fake it
(setq fit:*bow-max*     12.0)      ; a wall bowed more than a foot is
                                   ; not a straight wall any more
(setq fit:*bow-max-frac* 0.04)     ; nor one bowed more than this share
                                   ; of its own length
(setq fit:*bow-pts-min* 4)         ; and one shot fewer times than this
                                   ; cannot tell a bow from noise
(setq fit:*oos-max* (/ pi 36.0))   ; how far a wall may swing off its
                                   ; template direction (5 degrees):
                                   ; further than that and the survey
                                   ; is not this type of pool at all
(setq fit:*cap-oos-max* (/ pi 18.0)); how far a Roman or Oval side
                                   ; wall may lean, and how far the two
                                   ; may diverge from each other (10
                                   ; degrees).  An arc-ended shell
                                   ; slumps as it cures and the walls
                                   ; slant away, so they are NEVER held
                                   ; parallel the way a rectangle's
                                   ; template holds its own: they are
                                   ; two independent walls that happen
                                   ; to start out parallel
(setq fit:*arc-pts-min* 3)         ; points each arc of a run needs
                                   ; before it means anything - and so,
                                   ; the only thing that limits how many
                                   ; arcs a curve may be broken into: a
                                   ; curve carrying N points may become
                                   ; at most N/3 arcs.  There is no
                                   ; fixed ceiling.  A shell that
                                   ; wandered over forty shots has
                                   ; earned more arcs than one shot ten
                                   ; times, and the earning rule below
                                   ; stops the run long before this
                                   ; limit on anything that is really
                                   ; one radius
(setq fit:*tang-tol* (/ pi 22.5))  ; ABHD's own tangency window (8
                                   ; degrees): how far the next arc of
                                   ; a run may start off the tangent
                                   ; the last one ended on.  A run that
                                   ; only shares its joints is
                                   ; continuous but not SMOOTH - the
                                   ; end of the pool reads as a row of
                                   ; facets - and holding the joints
                                   ; perfectly tangent would take them
                                   ; off the survey points.  A window
                                   ; keeps both: smooth to the eye,
                                   ; with the points still choosing
                                   ; inside it
(setq fit:*tang-steps* '(1.0 1.25 1.5)) ; when nothing inside the window
                                   ; holds the points, stretch it by
                                   ; these in turn rather than abandon
                                   ; it - ABHD's rule, and for ABHD's
                                   ; reason: smoothness is worth more
                                   ; than an exact hit
(setq fit:*oos-min*     1.0)       ; the drift from one end of a wall
                                   ; to the other below which the wall
                                   ; reads as true and is held there
(setq fit:*feat-snap*   0.1)       ; snapping a MEASURED feature (a
                                   ; corner radius, a cut face, a
                                   ; roman end radius) may grow the
                                   ; worst deviation by at most this -
                                   ; an 8" as-built corner must not
                                   ; become a foot just because the
                                   ; tolerance would absorb it
(setq fit:*nice-dims* '(12.0 6.0 1.0 0.5)) ; snapping increments, tried
                                   ; in order: whole feet, half feet,
                                   ; inches, half inches
(setq fit:*types* "Rectangle Grecian ROman Oval L LAzyl ROUnd")
                                   ; POOL's shape vocabulary, minus the
                                   ; shapes a template cannot say
                                   ; (Octagon rides Grecian, Mutt and
                                   ; freeform are ABHD's job)
(setq fit:*dim-off*     12.0)      ; the K/L/M string sits this far off
                                   ; the deep break, on the shallow side
(if (null fit:*tol*) (setq fit:*tol* 1.0))       ; remembered per session
;; The rest of the answers a session remembers, so a second run is
;; mostly Enter.  Reading an unset symbol yields nil, so this declares
;; them beside the others without clobbering what a run put there.
(setq fit:*ptype*  fit:*ptype*)
(setq fit:*treat*  fit:*treat*)
(setq fit:*gtreat* fit:*gtreat*)
(if (null fit:*oos*) (setq fit:*oos* T))  ; as-builts are never true
(if (null fit:*bowed*) (setq fit:*bowed* T))  ; nor are their walls
(if (null fit:*brk-deep*) (setq fit:*brk-deep* (cons 96.0 T)))
(if (null fit:*brk-shal*) (setq fit:*brk-shal* (cons 240.0 T)))
(if (null fit:*hop-side*) (setq fit:*hop-side* (cons 18.0 nil)))
(if (null fit:*hop-back*) (setq fit:*hop-back* (cons 18.0 nil)))

;; the template wall directions, one CCW ring per type (see below)
(setq fit:*rect-dirs* (list 0.0 (/ pi 2.0) pi (* pi 1.5)))
(setq fit:*grec-dirs* (list 0.0 (/ pi 4.0) (/ pi 2.0) (* pi 0.75)
                            pi (* pi 1.25) (* pi 1.5) (* pi 1.75)))
(setq fit:*l-dirs*    (list 0.0 (/ pi 2.0) pi (* pi 1.5) pi (* pi 1.5)))
(setq fit:*lazy-dirs* (list 0.0 (/ pi 4.0) (* pi 0.75) (* pi 1.25)
                            pi (* pi 1.5)))

;; ---- embedded shared helpers -----------------------------------------
;; Copies of the CALOFIN-LIB helpers this tool uses, under its own
;; prefix so the file loads alone with APPLOAD (the shared/ twin calls
;; cal: instead).  Bodies identical to the library's.

;; ---- circle / arc geometry -------------------------------------------
;; The 2-element circumcenter abhd and lhd also keep locally - the
;; library's 3-element form is deliberately not used here (the fitter
;; is strictly 2D).

(defun fit:circumcenter (pa pb pc / x1 y1 x2 y2 x3 y3 d s1 s2 s3)
  (setq x1 (car pa) y1 (cadr pa)
        x2 (car pb) y2 (cadr pb)
        x3 (car pc) y3 (cadr pc)
        d  (* 2.0 (+ (* x1 (- y2 y3)) (* x2 (- y3 y1)) (* x3 (- y1 y2)))))
  (if (< (abs d) 1.0e-10)
    nil
    (progn
      (setq s1 (+ (* x1 x1) (* y1 y1))
            s2 (+ (* x2 x2) (* y2 y2))
            s3 (+ (* x3 x3) (* y3 y3)))
      (list (/ (+ (* s1 (- y2 y3)) (* s2 (- y3 y1)) (* s3 (- y1 y2))) d)
            (/ (+ (* s1 (- x3 x2)) (* s2 (- x1 x3)) (* s3 (- x2 x1))) d)))))

;; Arc geometry of a bulged segment: (center radius angStart angEnd);
;; nil for a straight segment.
(defun fit:arc-geom (p1 p2 b / ch dir apex c)
  (if (< (abs b) 1.0e-9)
    nil
    (progn
      (setq p1   (cal:2d p1)
            p2   (cal:2d p2)
            ch   (cal:dist p1 p2))
      (if (< ch 1.0e-12)
        nil
        (progn
          (setq dir  (cal:v* (cal:v- p2 p1) (/ 1.0 ch))
                ;; a positive (CCW) bulge apex lies to the RIGHT of the
                ;; p1->p2 chord direction
                apex (cal:v+ (cal:mid p1 p2)
                             (cal:v* (cal:perp dir) (* -0.5 ch b)))
                c    (fit:circumcenter p1 apex p2))
          (if (null c)
            nil
            (list c (cal:dist c p1) (angle c p1) (angle c p2))))))))

;; Distance from point P to segment (p1 p2 bulge).
(defun fit:seg-dist (p seg / p1 p2 b v w len2 t2 g c r a1 a2 ap sweep rel)
  (setq p  (cal:2d p)
        p1 (cal:2d (car seg))
        p2 (cal:2d (cadr seg))
        b  (caddr seg))
  (if (< (abs b) 1.0e-9)
    (progn
      (setq v    (cal:v- p2 p1)
            w    (cal:v- p p1)
            len2 (cal:dot v v))
      (if (< len2 1.0e-20)
        (cal:dist p p1)
        (progn
          (setq t2 (/ (cal:dot w v) len2))
          (if (< t2 0.0) (setq t2 0.0))
          (if (> t2 1.0) (setq t2 1.0))
          (cal:dist p (cal:v+ p1 (cal:v* v t2))))))
    (progn
      (setq g (fit:arc-geom p1 p2 b))
      (if (null g)
        (min (cal:dist p p1) (cal:dist p p2))
        (progn
          (setq c  (car g)  r (cadr g)
                a1 (caddr g) a2 (cadddr g)
                ap (angle c p))
          (if (> b 0.0)
            (setq sweep (cal:angnorm (- a2 a1)) rel (cal:angnorm (- ap a1)))
            (setq sweep (cal:angnorm (- a1 a2)) rel (cal:angnorm (- ap a2))))
          (if (<= rel sweep)
            (abs (- (cal:dist p c) r))
            (min (cal:dist p p1) (cal:dist p p2))))))))

;; Every point's distance to the nearest piece of the outline.
(defun fit:outline-dists (pts segs / out q s d dmin)
  (setq out nil)
  (foreach q pts
    (setq dmin nil)
    (foreach s segs
      (setq d (fit:seg-dist q s))
      (if (or (null dmin) (< d dmin)) (setq dmin d)))
    (setq out (cons dmin out)))
  (reverse out))

;; (worst rms) distance of the points from an outline.
(defun fit:outline-dev (pts segs / ds worst ssum d)
  (setq ds (fit:outline-dists pts segs) worst 0.0 ssum 0.0)
  (foreach d ds
    (if (> d worst) (setq worst d))
    (setq ssum (+ ssum (* d d))))
  (list worst (sqrt (/ ssum (length ds)))))

;; COUNT elements of LST starting at index K.
(defun fit:sublist (lst k count / out)
  (while (> k 0) (setq lst (cdr lst) k (1- k)))
  (setq out nil)
  (while (> count 0)
    (setq out   (cons (car lst) out)
          lst   (cdr lst)
          count (1- count)))
  (reverse out))

;; LST without ONE element equal to V.
(defun fit:drop-one (v lst / out done x)
  (setq out nil done nil)
  (foreach x lst
    (if (and (not done) (equal x v 1.0e-12))
      (setq done T)
      (setq out (cons x out))))
  (reverse out))

;; The worst deviation once the ALLOW worst points are set aside - what
;; the fit actually has to hold.  ALLOW = 0 is the plain worst.  This
;; is where the percent answered at step 4 gets spent: a snap to a
;; whole foot only has to convince all but that share of the points.
(defun fit:held-worst (dists allow / rest best d)
  (setq rest dists)
  (repeat allow
    (if rest
      (progn
        (setq best nil)
        (foreach d rest (if (or (null best) (> d best)) (setq best d)))
        (setq rest (fit:drop-one best rest)))))
  (setq best 0.0)
  (foreach d rest (if (> d best) (setq best d)))
  best)

;; What counts as ON the outline for this run.  It scales with the
;; tolerance (a quarter of it, never below fit:*on-eps*), exactly as
;; ABHD's does: if the user accepts 2 inches of error, a point half an
;; inch off is plainly still on the wall, and counting it against the
;; allowance would spend the whole budget on the first snap.
(defun fit:on-eps (tol)
  (max fit:*on-eps* (/ tol 4.0)))

;; Can the points live with this snap?
;;
;; A measured FEATURE - a corner radius, a cut face, an end radius -
;; may not grow the worst deviation at all beyond fit:*feat-snap*: it
;; is what it is.  A DESIGN dimension may spend the allowance: at most
;; ALLOW points may be pushed further off, and the snap may never push
;; a point past the tolerance that was not already there.  What
;; matters is what the snap CHANGES, not where the survey noise
;; already sits.
(defun fit:snap-ok (before after tol allow feature / on pushed badb bada
                                                    rest a b)
  (if feature
    (<= (fit:held-worst after 0)
        (+ (fit:held-worst before 0) fit:*feat-snap*))
    (progn
      (setq on     (fit:on-eps tol)
            pushed 0 badb 0 bada 0
            rest   after)
      (foreach b before
        (setq a    (car rest)
              rest (cdr rest))
        (if (> a (+ b on)) (setq pushed (1+ pushed)))
        (if (> b tol) (setq badb (1+ badb)))
        (if (> a tol) (setq bada (1+ bada))))
      (and (<= pushed allow) (<= bada badb)))))

;; ---- ordering and the frame ------------------------------------------

;; Remove every element equal (within fuzz) to VAL from LST.
(defun fit:remove (val lst / out x)
  (foreach x lst
    (if (not (equal x val 1.0e-9)) (setq out (cons x out))))
  (reverse out))

;; The member of LST nearest to P.
(defun fit:nearest (p lst / best bd q d)
  (setq best nil bd nil)
  (foreach q lst
    (setq d (cal:dist p q))
    (if (or (null bd) (< d bd)) (setq best q bd d)))
  best)

;; Order points into a closed tour: nearest-neighbour walk from the
;; leftmost point, then 2-opt passes to remove crossings (ABHD's).
(defun fit:order-points (pts / start cur tour rest best bd q d n i j k
                               pass improved ti ti1 tj tj1 delta head
                               midl taill)
  (setq start (car pts))
  (foreach q (cdr pts)
    (if (or (< (car q) (car start))
            (and (= (car q) (car start)) (< (cadr q) (cadr start))))
      (setq start q)))
  (setq cur  start
        rest (fit:remove start pts)
        tour (list start))
  (while rest
    (setq best nil bd nil)
    (foreach q rest
      (setq d (cal:dist cur q))
      (if (or (null bd) (< d bd)) (setq best q bd d)))
    (setq tour (cons best tour)
          cur  best
          rest (fit:remove best rest)))
  (setq tour (reverse tour)
        n    (length tour)
        pass 0
        improved T)
  (while (and improved (< pass 40))
    (setq improved nil pass (1+ pass) i 0)
    (while (< i (1- n))
      (setq j (1+ i))
      (while (< j n)
        (if (not (and (= i 0) (= j (1- n))))
          (progn
            (setq ti    (nth i tour)
                  ti1   (nth (1+ i) tour)
                  tj    (nth j tour)
                  tj1   (nth (rem (1+ j) n) tour)
                  delta (- (+ (cal:dist ti tj) (cal:dist ti1 tj1))
                           (+ (cal:dist ti ti1) (cal:dist tj tj1))))
            (if (< delta -1.0e-9)
              (progn                    ; reverse tour[i+1 .. j]
                (setq head nil midl nil taill nil k 0)
                (foreach q tour
                  (cond ((<= k i) (setq head (cons q head)))
                        ((<= k j) (setq midl (cons q midl)))
                        (T        (setq taill (cons q taill))))
                  (setq k (1+ k)))
                (setq tour     (append (reverse head) midl (reverse taill))
                      improved T)))))
        (setq j (1+ j)))
      (setq i (1+ i))))
  tour)

;; Dominant wall direction folded modulo (2pi/fold).  Every edge of the
;; ordered ring votes with its length; folding by 4 makes parallel and
;; perpendicular walls reinforce each other, and folding by 8 pulls the
;; 45-degree walls of a Lazy L into the same vote instead of letting
;; the two families cancel.
(defun fit:frame-angle (tour fold / sx sy n i a b ln d)
  (setq sx 0.0 sy 0.0 n (length tour) i 0)
  (while (< i n)
    (setq a  (nth i tour)
          b  (nth (rem (1+ i) n) tour)
          ln (cal:dist a b))
    (if (> ln 1.0e-9)
      (progn
        (setq d (* fold (angle a b)))
        (setq sx (+ sx (* ln (cos d)))
              sy (+ sy (* ln (sin d))))))
    (setq i (1+ i)))
  (if (and (< (abs sx) 1.0e-12) (< (abs sy) 1.0e-12))
    0.0
    (rem (/ (cal:angnorm (atan sy sx)) fold) (/ (* 2.0 pi) fold))))

;; rotate P by angle A about the origin
(defun fit:rot (p a / c s)
  (setq c (cos a) s (sin a))
  (list (- (* (car p) c) (* (cadr p) s))
        (+ (* (car p) s) (* (cadr p) c))))

;; World -> frame: rotate by -A, then mirror across X if asked.
(defun fit:to-frame (pts a mirror / out p q)
  (setq out nil)
  (foreach p pts
    (setq q (fit:rot (cal:2d p) (- a)))
    (setq out (cons (if mirror (list (car q) (- (cadr q))) q) out)))
  (reverse out))

;; one point back out of the frame
(defun fit:from-frame (p a mirror)
  (fit:rot (if mirror (list (car p) (- (cadr p))) p) a))

;; Bounding box of a point list, as (minx miny maxx maxy).
(defun fit:bbox (pts / x0 y0 x1 y1 q)
  (foreach q pts
    (if (null x0)
      (setq x0 (car q) x1 (car q) y0 (cadr q) y1 (cadr q))
      (setq x0 (min x0 (car q)) x1 (max x1 (car q))
            y0 (min y0 (cadr q)) y1 (max y1 (cadr q)))))
  (list x0 y0 x1 y1))

;; ---- the fixed-direction polygon fit (the ICP core) ------------------
;; A template polygon is a CCW ring of walls whose DIRECTIONS are fixed
;; by the pool type; only each wall's offset along its outward normal
;; is fitted.  That is what knowing the type buys: a Lazy L's bend
;; walls are at exactly 45 degrees, so the survey only has to say
;; WHERE they are, never what they are.

;; Outward normal of a CCW ring edge with direction angle D.
(defun fit:wall-normal (d)
  (list (sin d) (- (cos d))))

;; Corner list: corner i joins wall i-1 to wall i.  nil when two
;; neighbouring walls are parallel.
(defun fit:poly-corners (dirs offs / n i n1 n2 d1 d2 det out prev bad)
  (setq n (length dirs) i 0 out nil bad nil)
  (while (and (< i n) (not bad))
    (setq prev (rem (+ i n -1) n)
          n1   (fit:wall-normal (nth prev dirs))
          d1   (nth prev offs)
          n2   (fit:wall-normal (nth i dirs))
          d2   (nth i offs)
          det  (- (* (car n1) (cadr n2)) (* (cadr n1) (car n2))))
    (if (< (abs det) 1.0e-12)
      (setq bad T)
      (setq out (cons (list (/ (- (* d1 (cadr n2)) (* d2 (cadr n1))) det)
                            (/ (- (* d2 (car n1)) (* d1 (car n2))) det))
                      out)))
    (setq i (1+ i)))
  (if bad nil (reverse out)))

;; A fitted polygon is only believable when every edge still runs in
;; its template direction - a collapsed or bow-tied fit reverses one,
;; and can still hug the points, so it must be rejected.
(defun fit:poly-valid (dirs offs / c n i u v ok)
  (setq c (fit:poly-corners dirs offs))
  (if (null c)
    nil
    (progn
      (setq n (length c) i 0 ok T)
      (while (< i n)
        (setq u (list (cos (nth i dirs)) (sin (nth i dirs)))
              v (cal:v- (nth (rem (1+ i) n) c) (nth i c)))
        (if (<= (cal:dot u v) 1.0e-6) (setq ok nil))
        (setq i (1+ i)))
      ok)))

;; N empty buckets / cons P onto bucket I.
(defun fit:empty-buckets (n / out)
  (repeat n (setq out (cons nil out)))
  out)
(defun fit:bucket-add (bkts i p / out k b)
  (setq out nil k 0)
  (foreach b bkts
    (setq out (cons (if (= k i) (cons p b) b) out)
          k   (1+ k)))
  (reverse out))

;; Nearest-wall buckets, with points inside a corner's ZONE pulled into
;; that corner's bucket instead.  Returns (wallpts cornerpts), each a
;; list of per-index point lists.  Corner i sits between wall i-1 and
;; wall i.
(defun fit:assign-walls (pts dirs offs zone / corners n wallpts cornerpts
                                              segs i p best bd d dc1 dc2 k)
  (setq corners (fit:poly-corners dirs offs)
        n       (length dirs)
        wallpts (fit:empty-buckets n)
        cornerpts (fit:empty-buckets n))
  (if corners
    (progn
      (setq segs nil i 0)
      (while (< i n)
        (setq segs (cons (list (nth i corners)
                               (nth (rem (1+ i) n) corners) 0.0) segs)
              i    (1+ i)))
      (setq segs (reverse segs))
      (foreach p pts
        (setq best 0 bd nil i 0)
        (foreach d (mapcar '(lambda (s) (fit:seg-dist p s)) segs)
          (if (or (null bd) (< d bd)) (setq best i bd d))
          (setq i (1+ i)))
        (setq dc1 (cal:dist p (nth best corners))
              dc2 (cal:dist p (nth (rem (1+ best) n) corners)))
        (if (or (< dc1 zone) (< dc2 zone))
          (progn
            (setq k (if (<= dc1 dc2) best (rem (1+ best) n)))
            (setq cornerpts (fit:bucket-add cornerpts k p)))
          (setq wallpts (fit:bucket-add wallpts best p))))))
  (list wallpts cornerpts))

;; Iterate assignment / offset update.  Offsets a wall never sees a
;; point for stay where they are.
(defun fit:fit-polygon (pts dirs offs zone iters / wallpts new i nrm b
                                                   ssum c)
  (repeat iters
    (setq wallpts (car (fit:assign-walls pts dirs offs zone)))
    (setq new nil i 0)
    (foreach b wallpts
      (if b
        (progn
          (setq nrm  (fit:wall-normal (nth i dirs))
                ssum 0.0)
          (foreach c b
            (setq ssum (+ ssum (cal:dot nrm c))))
          (setq new (cons (/ ssum (length b)) new)))
        (setq new (cons (nth i offs) new)))
      (setq i (1+ i)))
    (setq new (reverse new))
    (if (fit:poly-corners dirs new) (setq offs new)))
  offs)

;; (turn angle, fillet-centre direction unit) at corner i (between wall
;; i-1 and wall i).  A convex corner's fillet centre sits along the
;; interior bisector; a concave (notch) corner's sits along the
;; exterior one - the arc bows out of the pool there.
(defun fit:corner-frame (dirs i / n prev turn n1 n2 s bx by ln)
  (setq n    (length dirs)
        prev (rem (+ i n -1) n)
        turn (cal:signed-dang (nth prev dirs) (nth i dirs))
        n1   (fit:wall-normal (nth prev dirs))
        n2   (fit:wall-normal (nth i dirs))
        s    (if (> turn 0.0) -1.0 1.0)
        bx   (* s (+ (car n1) (car n2)))
        by   (* s (+ (cadr n1) (cadr n2)))
        ln   (sqrt (+ (* bx bx) (* by by))))
  (if (< ln 1.0e-9)
    (list turn (list 0.0 0.0))
    (list turn (list (/ bx ln) (/ by ln)))))

;; Mean squared radial error of the shared fillet radius R over the
;; corner-zone points (a list of (index . point) pairs).
(defun fit:corner-err (allpts corners dirs r / ssum n ip cf turn bis half
                                               cc e)
  (setq ssum 0.0 n 0)
  (foreach ip allpts
    (setq cf   (fit:corner-frame dirs (car ip))
          turn (car cf)
          bis  (cadr cf)
          half (/ (abs turn) 2.0))
    ;; the centre sits r / cos(turn/2) from the vertex - the interior
    ;; half-angle is 90 - turn/2, so this equals the familiar r*sqrt(2)
    ;; only at a square corner
    (if (>= (cos half) 1.0e-9)
      (progn
        (setq cc (cal:v+ (nth (car ip) corners)
                         (cal:v* bis (/ r (cos half))))
              e  (- (cal:dist (cdr ip) cc) r))
        (setq ssum (+ ssum (* e e))
              n    (1+ n)))))
  (if (> n 0) (/ ssum n)))

;; One shared fillet radius over the corners listed in VOTERS, fitted
;; by golden-section search - the direct fixed-point update is unstable
;; for this geometry.  nil when nothing landed in a zone.
(defun fit:fit-corner-radius (cpts corners dirs voters / allpts i p gr lo
                                                         hi a b fa fb)
  (setq allpts nil)
  (foreach i voters
    (foreach p (nth i cpts)
      (setq allpts (cons (cons i p) allpts))))
  (if (null allpts)
    nil
    (progn
      (setq gr 0.6180339887
            lo 0.25
            hi fit:*rad-max*
            a  (- hi (* gr (- hi lo)))
            b  (+ lo (* gr (- hi lo)))
            fa (fit:corner-err allpts corners dirs a)
            fb (fit:corner-err allpts corners dirs b))
      (if (or (null fa) (null fb))
        nil
        (progn
          (repeat 48
            (if (<= fa fb)
              (setq hi b  b a  fb fa
                    a  (- hi (* gr (- hi lo)))
                    fa (fit:corner-err allpts corners dirs a))
              (setq lo a  a b  fa fb
                    b  (+ lo (* gr (- hi lo)))
                    fb (fit:corner-err allpts corners dirs b))))
          (/ (+ lo hi) 2.0))))))

;; One shared cut-face length: the chamfer line's perpendicular inset
;; from each corner, fitted as a plain mean.  Notch corners take no
;; cut.  nil when nothing landed in a zone.
(defun fit:fit-corner-cut (cpts corners dirs voters / hsum n i cf turn bis
                                                      p h)
  (setq hsum 0.0 n 0 turn nil)
  (foreach i voters
    (setq cf (fit:corner-frame dirs i))
    (if (> (car cf) 0.0)
      (progn
        (setq turn (car cf)
              bis  (cadr cf))
        (foreach p (nth i cpts)
          (setq hsum (+ hsum (cal:dot bis (cal:v- p (nth i corners))))
                n    (1+ n))))))
  (if (or (= n 0) (null turn))
    nil
    (progn
      (setq h (/ hsum n))
      ;; face length from the perpendicular inset: f = 2h / tan(turn/2)
      ;; (the familiar f = 2h only at a square corner)
      (if (<= h 0.0)
        nil
        (/ (* 2.0 h) (cal:tan (/ (abs turn) 2.0)))))))

;; ---- building the drawn outline --------------------------------------

;; The vertex run replacing sharp corner V: a list of (pt bulge).  The
;; bulge on an entry curves the segment LEAVING that point.
(defun fit:corner-verts (vprev v vnext turn treat size / u1 u2 t2 s p1 p2)
  (cond
    ((and (= treat "Radius") size (> size 1.0e-6))
     (setq u1 (angle vprev v)
           u2 (angle v vnext)
           t2 (* size (cal:tan (/ (abs turn) 2.0)))
           p1 (list (- (car v) (* (cos u1) t2))
                    (- (cadr v) (* (sin u1) t2)))
           p2 (list (+ (car v) (* (cos u2) t2))
                    (+ (cadr v) (* (sin u2) t2))))
     (list (list p1 (cal:tan (/ turn 4.0))) (list p2 0.0)))
    ((and (= treat "Cut") size (> size 1.0e-6) (> turn 0.0))
     (setq u1 (angle vprev v)
           u2 (angle v vnext)
           s  (/ size (* 2.0 (cos (/ (abs turn) 2.0))))
           p1 (list (- (car v) (* (cos u1) s))
                    (- (cadr v) (* (sin u1) s)))
           p2 (list (+ (car v) (* (cos u2) s))
                    (+ (cadr v) (* (sin u2) s))))
     (list (list p1 0.0) (list p2 0.0)))
    (T (list (list v 0.0)))))

;; Bulge for the drawn chord A->B carrying the bow fitted as sagitta S
;; over the corner-to-corner chord CFIT.  The RADIUS is what is
;; preserved, so an eased corner shortening the wall does not deepen
;; its bow.  A positive sagitta bows OUTWARD: on a CCW ring a positive
;; bulge puts the arc's apex to the right of travel, which is the
;; outward side.
(defun fit:bow-bulge (s cfit a b / c r x half bl)
  (setq c (cal:dist a b))
  (if (or (null s) (equal s 0.0 1.0e-12) (< cfit 1.0e-9) (< c 1.0e-9))
    0.0
    (progn
      (setq r (+ (/ (* cfit cfit) (* 8.0 (abs s))) (/ (abs s) 2.0))
            x (/ c (* 2.0 r)))
      (if (>= x 1.0)
        0.0
        (progn
          ;; half the included angle: asin(x), written with atan
          (setq half (atan (/ x (sqrt (- 1.0 (* x x)))))
                bl   (cal:tan (/ half 2.0)))
          (if (> s 0.0) bl (- bl)))))))

;; closed (pt bulge) vertex list -> (p1 p2 bulge) segment list
(defun fit:verts-to-segs (verts / n i out)
  (setq n (length verts) i 0 out nil)
  (while (< i n)
    (setq out (cons (list (car (nth i verts))
                          (car (nth (rem (1+ i) n) verts))
                          (cadr (nth i verts)))
                    out)
          i   (1+ i)))
  (reverse out))

;; Closed vertex list for the fitted polygon; WHICH non-nil applies the
;; corner treatment to every corner (nil leaves them all sharp), and
;; BOWS (nil = none) gives each wall its own fitted bow.  A bow never
;; moves a corner: it vanishes at both ends of its wall by
;; construction, so every design dimension taken between corners
;; survives it untouched.
(defun fit:build-polygon (dirs offs treat size which bows / corners n
                                                            verts leaves
                                                            i cf m k a b
                                                            cfit)
  (setq corners (fit:poly-corners dirs offs)
        n       (length corners)
        verts   nil
        leaves  nil
        i       0)
  (while (< i n)
    (setq cf (fit:corner-frame dirs i))
    (if which
      (setq verts (append verts
                          (fit:corner-verts
                            (nth (rem (+ i n -1) n) corners)
                            (nth i corners)
                            (nth (rem (1+ i) n) corners)
                            (car cf) treat size)))
      (setq verts (append verts (list (list (nth i corners) 0.0)))))
    (setq leaves (cons (1- (length verts)) leaves)   ; wall i leaves here
          i      (1+ i)))
  (setq leaves (reverse leaves))
  (if bows
    (progn
      (setq m (length verts) i 0)
      (while (< i n)
        (if (and (nth i bows) (not (equal (nth i bows) 0.0 1.0e-12)))
          (setq k     (nth i leaves)
                a     (car (nth k verts))
                b     (car (nth (rem (1+ k) m) verts))
                cfit  (cal:dist (nth i corners)
                                (nth (rem (1+ i) n) corners))
                verts (fit:setnth verts k
                                  (list a (fit:bow-bulge (nth i bows)
                                                         cfit a b)))))
        (setq i (1+ i)))))
  verts)

;; ---- bowed walls -----------------------------------------------------
;; "Straight" is a drafting convention, not a site measurement: a
;; gunite wall shot dead straight on the order sheet is very often a
;; very long radius on the ground.  When the user says the walls may
;; be bowed, each wall is refitted as a constant offset plus a
;; parabolic bow that vanishes at both corners - so the corners, and
;; every dimension taken between them, stay exactly where the straight
;; fit put them, and only the wall between them breathes.

;; Small Gauss-Jordan with partial pivoting; nil when singular.  MAT is
;; a list of rows, RHS a list; both N long.
(defun fit:solve-lin (mat rhs n / aug i c r piv d f row cr out)
  (setq aug nil i 0)
  (while (< i n)
    (setq aug (cons (append (nth i mat) (list (nth i rhs))) aug)
          i   (1+ i)))
  (setq aug (reverse aug) c 0)
  (while (and aug (< c n))
    (setq piv c r c)
    (while (< r n)
      (if (> (abs (nth c (nth r aug))) (abs (nth c (nth piv aug))))
        (setq piv r))
      (setq r (1+ r)))
    (if (< (abs (nth c (nth piv aug))) 1.0e-12)
      (setq aug nil)                        ; singular
      (progn
        ;; swap rows c and piv
        (setq row (nth c aug)
              aug (fit:setnth aug c (nth piv aug))
              aug (fit:setnth aug piv row)
              d   (nth c (nth c aug))
              aug (fit:setnth aug c
                              (mapcar '(lambda (v) (/ v d)) (nth c aug)))
              cr  (nth c aug)
              r   0)
        (while (< r n)
          (if (/= r c)
            (progn
              (setq f (nth c (nth r aug)))
              (if (/= f 0.0)
                (setq aug (fit:setnth
                            aug r
                            (mapcar '(lambda (v w) (- v (* f w)))
                                    (nth r aug) cr))))))
          (setq r (1+ r)))
        (setq c (1+ c)))))
  (if (null aug)
    nil
    (progn
      (setq out nil i 0)
      (while (< i n)
        (setq out (cons (nth n (nth i aug)) out) i (1+ i)))
      (reverse out))))

;; Least-squares wall through its own points, in the wall's own frame
;; (t along the chord A->B, y outward):
;;
;;     y = A + B*t + C*4t(1-t)
;;
;; A is where the wall sits, B how far it DRIFTS from one end to the
;; other - the wall swinging off its template direction, which is what
;; an out-of-square pool is made of - and C how far it BOWS at
;; mid-wall.  Terms not asked for are held at zero and left out of the
;; solve.  Returns (A B C), or nil when the wall has too few points to
;; tell any of it from noise.
(defun fit:fit-wall-line (wpts a b want-swing want-bow / c ux uy nx ny use
                                                        k mat rhs row i j
                                                        p dx dy tt f y got
                                                        out)
  (setq c (cal:dist a b))
  (if (< c 1.0e-9)
    nil
    (progn
      (setq use (list 0))
      (if want-swing (setq use (append use (list 1))))
      (if want-bow (setq use (append use (list 2))))
      (setq k (length use))
      (if (< (length wpts) (max fit:*bow-pts-min* (1+ k)))
        nil
        (progn
          (setq ux (/ (- (car b) (car a)) c)
                uy (/ (- (cadr b) (cadr a)) c)
                nx uy                       ; right of travel = outward
                ny (- ux)
                mat nil rhs nil i 0)
          (while (< i k)
            (setq row nil j 0)
            (while (< j k) (setq row (cons 0.0 row) j (1+ j)))
            (setq mat (cons row mat)
                  rhs (cons 0.0 rhs)
                  i   (1+ i)))
          (foreach p wpts
            (setq dx (- (car p) (car a))
                  dy (- (cadr p) (cadr a))
                  tt (/ (+ (* dx ux) (* dy uy)) c)
                  f  (list 1.0 tt (* 4.0 tt (- 1.0 tt)))
                  y  (+ (* dx nx) (* dy ny))
                  i  0)
            (while (< i k)
              (setq rhs (fit:setnth
                          rhs i (+ (nth i rhs)
                                   (* (nth (nth i use) f) y)))
                    j   0)
              (while (< j k)
                (setq mat (fit:setnth
                            mat i
                            (fit:setnth (nth i mat) j
                                        (+ (nth j (nth i mat))
                                           (* (nth (nth i use) f)
                                              (nth (nth j use) f)))))
                      j   (1+ j)))
              (setq i (1+ i))))
          (setq got (fit:solve-lin mat rhs k))
          (if (null got)
            nil
            (progn
              (setq out (list 0.0 0.0 0.0) i 0)
              (while (< i k)
                (setq out (fit:setnth out (nth i use) (nth i got))
                      i   (1+ i)))
              out)))))))

;; The wall line A->B (template direction D) after its fitted offset
;; and drift are applied: (new-direction new-outward-offset).  The
;; drift is a ROTATION, so the wall stays a straight line - the pool
;; goes out of square, it does not go crooked.
(defun fit:swung-wall (a b d coef / c ux uy nx ny d2 q n2)
  (setq c  (cal:dist a b)
        ux (/ (- (car b) (car a)) c)
        uy (/ (- (cadr b) (cadr a)) c)
        nx uy
        ny (- ux)
        d2 (- d (atan (cadr coef) c))
        q  (list (+ (car a) (* nx (car coef)))
                 (+ (cadr a) (* ny (car coef))))
        n2 (fit:wall-normal d2))
  (list d2 (cal:dot n2 q)))

;; RMS of the points about the straight line with direction D at
;; outward offset OFF - the wall as the template would hold it.
(defun fit:flat-rms (wpts d off / nrm ssum p e)
  (setq nrm (fit:wall-normal d) ssum 0.0)
  (if (null wpts)
    0.0
    (progn
      (foreach p wpts
        (setq e (- (cal:dot nrm p) off) ssum (+ ssum (* e e))))
      (sqrt (/ ssum (length wpts))))))

;; RMS of the points about the drawn segment A->B with this bulge.
(defun fit:wall-rms (wpts a b bulge)
  (if (null wpts) 0.0 (cadr (fit:outline-dev wpts (list (list a b bulge))))))

;; The mean outward offset of a wall's own points - the wall as the
;; template holds it, with no drift and no bow.
(defun fit:flat-off (wpts d dflt / nrm ssum p)
  (if (null wpts)
    dflt
    (progn
      (setq nrm (fit:wall-normal d) ssum 0.0)
      (foreach p wpts (setq ssum (+ ssum (cal:dot nrm p))))
      (/ ssum (length wpts)))))

;; A bow may not be deeper than a wall can bow and still be a wall.
(defun fit:bow-cap (s c / smax)
  (setq smax (min fit:*bow-max* (* fit:*bow-max-frac* c)))
  (max (- smax) (min smax s)))

;; A bow is kept only when it is deep enough to read, shallow enough to
;; still be a wall, and beats the straight wall on that wall's own
;; points by a clear margin.  Noise is not a bow.
(defun fit:keep-bow (wpts a b s / c rs rb)
  (setq c (cal:dist a b))
  (if (or (null s) (equal s 0.0 1.0e-12) (< c 1.0e-9)
          (< (length wpts) fit:*bow-pts-min*)
          (< (abs s) fit:*bow-min*))
    0.0
    (progn
      (setq rs (cadr (fit:outline-dev wpts (list (list a b 0.0))))
            rb (cadr (fit:outline-dev
                       wpts
                       (list (list a b (fit:bow-bulge s c a b))))))
      (if (<= rb (* rs fit:*both-edge*)) s 0.0))))

;; ---- template starting guesses ---------------------------------------

;; Largest n.p over the points for wall direction D - the outermost
;; line the cloud supports in that normal direction.
(defun fit:support (pts d / nrm best p v)
  (setq nrm (fit:wall-normal d) best nil)
  (foreach p pts
    (setq v (cal:dot nrm p))
    (if (or (null best) (> v best)) (setq best v)))
  best)

(defun fit:rect-init (pts / d out)
  (setq out nil)
  (foreach d fit:*rect-dirs*
    (setq out (cons (fit:support pts d) out)))
  (reverse out))

(defun fit:grec-init (pts / i d out)
  (setq out nil i 0)
  (foreach d fit:*grec-dirs*
    ;; axis walls at their support line, cut walls a nominal 15" in
    (setq out (cons (if (= 0 (rem i 2))
                      (fit:support pts d)
                      (- (fit:support pts d) 15.0))
                    out)
          i   (1+ i))
    )
  (reverse out))

;; Starting hexagon for the L shapes, from the bounding box: the true L
;; guesses its notch at the middle, the lazy L a constant-width channel
;; bent at 45 degrees.
(defun fit:l-init (pts lazy / bb x0 y0 x1 y1 ex ey w0 cyy b c d t2 e
                             corners dirs offs i nrm)
  (setq bb (fit:bbox pts)
        x0 (car bb) y0 (cadr bb) x1 (caddr bb) y1 (cadddr bb))
  (if (not lazy)
    (progn
      (setq ex (+ x0 (* 0.5 (- x1 x0)))
            ey (+ y0 (* 0.5 (- y1 y0)))
            corners (list (list x0 y0) (list x1 y0) (list x1 y1)
                          (list ex y1) (list ex ey) (list x0 ey))
            dirs fit:*l-dirs*))
    (progn
      (setq w0  (* 0.45 (min (- x1 x0) (- y1 y0)))
            cyy (+ y0 (* 0.5 (- y1 y0)))
            b   (list (- x1 (- cyy y0)) y0)
            c   (list x1 cyy)
            d   (list (- x1 (- y1 cyy)) y1)
            t2  (/ (- y1 (+ y0 w0)) 0.7071067812)
            e   (list (- (car d) (* t2 0.7071067812)) (+ y0 w0))
            corners (list (list x0 y0) b c d e (list x0 (+ y0 w0)))
            dirs fit:*lazy-dirs*)))
  (setq offs nil i 0)
  (while (< i 6)
    (setq nrm  (fit:wall-normal (nth i dirs))
          offs (cons (cal:dot nrm (nth i corners)) offs)
          i    (1+ i)))
  (reverse offs))

;; Where the four AXIS walls of an eight-wall template would meet if
;; the cuts were not there - the pool's nominal corners.  Taken from
;; the walls themselves, so it still means something once they have
;; swung out of square.
(defun fit:grec-axis-corners (dirs offs)
  (fit:poly-corners (list (nth 0 dirs) (nth 2 dirs)
                          (nth 4 dirs) (nth 6 dirs))
                    (list (nth 0 offs) (nth 2 offs)
                          (nth 4 offs) (nth 6 offs))))

;; A cut wall bisects the corner it crosses, whatever the two axis
;; walls are doing - exactly 45 degrees on a true pool, and still a
;; real cut on an out-of-square one.
(defun fit:grec-cut-dir (dirs k / d0 d1)
  (setq d0 (nth (* 2 k) dirs)
        d1 (nth (rem (+ (* 2 k) 2) 8) dirs))
  (+ d0 (/ (cal:signed-dang d0 d1) 2.0)))

;; The mean cut-face length the four fitted cut walls imply.
(defun fit:grec-face (dirs offs / sq k i nrm vc hsum)
  (setq sq (fit:grec-axis-corners dirs offs))
  (if (null sq)
    0.0
    (progn
      (setq hsum 0.0 k 0)
      (while (< k 4)
        (setq i   (1+ (* 2 k))
              nrm (fit:wall-normal (nth i dirs))
              vc  (nth (rem (1+ k) 4) sq))
        (setq hsum (+ hsum (- (cal:dot nrm vc) (nth i offs)))
              k    (1+ k)))
      (* 2.0 (/ hsum 4.0)))))

;; Re-derive the four cut walls from the four axis walls: each bisects
;; its corner and sits the same perpendicular inset (face/2) in from
;; where the axis walls would meet.  Returns (dirs offs).
(defun fit:grec-cuts (dirs offs face / sq k i nrm vc h)
  (setq sq (fit:grec-axis-corners dirs offs))
  (if (null sq)
    (list dirs offs)
    (progn
      (setq h (/ face 2.0) k 0)
      (while (< k 4)
        (setq i    (1+ (* 2 k))
              dirs (fit:setnth dirs i (fit:grec-cut-dir dirs k))
              nrm  (fit:wall-normal (nth i dirs))
              vc   (nth (rem (1+ k) 4) sq)
              offs (fit:setnth offs i (- (cal:dot nrm vc) h))
              k    (1+ k)))
      (list dirs offs))))

(defun fit:setnth (lst i v / out k x)
  (setq out nil k 0)
  (foreach x lst
    (setq out (cons (if (= k i) v x) out)
          k   (1+ k)))
  (reverse out))

;; The as-built easing of an 8-wall template's vertices: one shared
;; fillet radius (or chamfer face) over all eight 45-degree corners.
;; A nominal grecian is drawn sharp, but an as-built very often is
;; not.  The corner zone is sized to the 45-degree turn (tangent
;; length 0.414r), so wall points stay out of the vote, and the easing
;; is kept only when it beats the sharp outline on the corner points
;; by a clear margin - noise is not evidence, and neither is a fit
;; below fit:*vsize-min*.  Returns (vsize offs face).
(defun fit:fit-vertex-feature (pts dirs offs treat / tanh cosh which zone
                                                    vs cpts face asg got2
                                                    corners czpts b p
                                                    sharp eased rs re2)
  (setq tanh  (cal:tan (/ pi 8.0))
        cosh  (cos (/ pi 8.0))
        which '(0 1 2 3 4 5 6 7)
        zone  (* fit:*corner-zone* tanh)
        vs    nil
        cpts  nil
        face  (fit:grec-face dirs offs))
  (repeat 2
    (setq asg     (fit:assign-walls pts dirs offs zone)
          cpts    (cadr asg)
          corners (fit:poly-corners dirs offs)
          vs      (if (= treat "Radius")
                    (fit:fit-corner-radius cpts corners dirs which)
                    (fit:fit-corner-cut cpts corners dirs which)))
    (if vs
      (progn
        ;; a fillet longer than the cut face cannot exist
        (setq vs   (min vs (/ face (* 2.0 tanh)))
              zone (if (= treat "Radius")
                     (+ (* 1.2 vs tanh) fit:*zone-pad*)
                     (+ (/ (* 1.2 vs) (* 2.0 cosh)) fit:*zone-pad*))
              offs (fit:fit-polygon pts dirs offs zone fit:*icp-iters*)
              face (fit:grec-face dirs offs)
              got2 (fit:grec-cuts dirs offs face)
              dirs (car got2)
              offs (cadr got2)))))
  (if (and vs (>= vs fit:*vsize-min*) cpts)
    (progn
      (setq czpts nil)
      (foreach b cpts
        (foreach p b (setq czpts (cons p czpts))))
      (if czpts
        (progn
          (setq sharp (fit:verts-to-segs
                        (fit:build-polygon dirs offs treat nil nil
                                           nil))
                eased (fit:verts-to-segs
                        (fit:build-polygon dirs offs treat vs T nil))
                rs    (cadr (fit:outline-dev czpts sharp))
                re2   (cadr (fit:outline-dev czpts eased)))
          (if (> re2 (* rs fit:*both-edge*)) (setq vs nil)))
        (setq vs nil)))
    (setq vs nil))
  (setq face (fit:grec-face dirs offs)
        got2 (fit:grec-cuts dirs offs face)
        dirs (car got2)
        offs (cadr got2))
  (list vs offs face))

;; Shared fit for the all-straight-wall types: walls, then the corner
;; feature, then walls again with the zone sized to it.  Returns
;; (offs size).
(defun fit:fit-polytype (pts dirs offs0 treat / zone offs size voters n i
                                                cpts corners)
  (setq zone (if (member treat '("Radius" "Cut")) fit:*corner-zone* 0.0)
        offs (fit:fit-polygon pts dirs offs0 zone fit:*icp-iters*)
        size nil)
  (if (member treat '("Radius" "Cut"))
    (progn
      ;; only corners that turn hard enough vote for the size (see
      ;; fit:*rad-turn-min*)
      (setq voters nil n (length dirs) i 0)
      (while (< i n)
        (if (>= (abs (cal:signed-dang (nth (rem (+ i n -1) n) dirs)
                                      (nth i dirs)))
                (- fit:*rad-turn-min* 1.0e-9))
          (setq voters (cons i voters)))
        (setq i (1+ i)))
      (setq voters  (reverse voters)
            cpts    (cadr (fit:assign-walls pts dirs offs zone))
            corners (fit:poly-corners dirs offs)
            size    (if (= treat "Radius")
                      (fit:fit-corner-radius cpts corners dirs voters)
                      (fit:fit-corner-cut cpts corners dirs voters)))
      (if (and size (= treat "Radius"))
        (progn
          ;; the zone refit: size the corner zones to the radius found,
          ;; refit the walls without their fillet points, re-fit the
          ;; radius.  (A cut keeps its first pass - a wide second zone
          ;; would drag wall points into the face estimate.)
          (setq zone    (+ (* 1.2 size) fit:*zone-pad*)
                offs    (fit:fit-polygon pts dirs offs zone
                                         fit:*icp-iters*)
                cpts    (cadr (fit:assign-walls pts dirs offs zone))
                corners (fit:poly-corners dirs offs)
                size    (fit:fit-corner-radius cpts corners dirs
                                               voters))))))
  (list offs size))

;; Let every wall answer to its own points.
;;
;; The template fixed each wall's DIRECTION, which is what makes the
;; type mean anything - but a real as-built is never true, and holding
;; a rectangle perfectly square just pushes the error into the points.
;; So each wall is refitted here: its offset always, its direction when
;; the pool may be out of square, its bow when the walls may be bowed.
;; Each of those is then kept only where the points prove it, so a pool
;; that really is square comes out square.
;;
;; Returns (dirs offs bows).
(defun fit:refine-walls (pts dirs offs zone oos bowed / n base coefs
                                                       wallpts corners nd
                                                       no i a b got d2o
                                                       bows wpts swing
                                                       drift flat got2)
  (setq n     (length dirs)
        base  dirs
        coefs nil
        i     0)
  (repeat n (setq coefs (cons nil coefs)))
  (repeat 3
    (setq wallpts (car (fit:assign-walls pts dirs offs zone))
          corners (fit:poly-corners dirs offs))
    (if corners
      (progn
        (setq nd dirs no offs i 0)
        (while (< i n)
          (setq a   (nth i corners)
                b   (nth (rem (1+ i) n) corners)
                got (fit:fit-wall-line (nth i wallpts) a b oos bowed))
          (if got
            (progn
              (setq coefs (fit:setnth coefs i got)
                    d2o   (fit:swung-wall a b (nth i dirs) got))
              (if (<= (abs (cal:signed-dang (nth i base) (car d2o)))
                      fit:*oos-max*)
                (setq nd (fit:setnth nd i (car d2o))
                      no (fit:setnth no i (cadr d2o)))
                (setq no (fit:setnth no i (+ (nth i offs) (car got)))))))
          (setq i (1+ i)))
        ;; on an eight-wall template the cut corners are not free
        ;; walls: each bisects its own corner and all four share one
        ;; face, however far the axis walls have swung
        (if (= n 8)
          (setq got2 (fit:grec-cuts nd no (fit:grec-face nd no))
                nd   (car got2)
                no   (cadr got2)))
        (if (fit:poly-valid nd no) (setq dirs nd offs no)))))
  ;; ---- what did the points actually earn? --------------------------
  (setq wallpts (car (fit:assign-walls pts dirs offs zone))
        corners (fit:poly-corners dirs offs))
  (if (null corners)
    (list base offs nil)
    (progn
      (setq bows nil i 0)
      (while (< i n)
        (setq wpts  (nth i wallpts)
              a     (nth i corners)
              b     (nth (rem (1+ i) n) corners)
              swing (cal:signed-dang (nth i base) (nth i dirs))
              ;; the drift the TOTAL swing represents, end to end, in
              ;; inches - not the residual the last pass measured,
              ;; which is near zero once the wall has already been
              ;; swung onto its points
              drift (* (abs (cal:tan swing)) (cal:dist a b)))
        (if (and (= n 8) (= 1 (rem i 2)))
          (setq swing 0.0))                 ; a derived cut wall
        (if (> (abs swing) 1.0e-9)
          (progn
            (setq flat (fit:flat-off wpts (nth i base) (nth i offs)))
            (if (not (and (>= drift fit:*oos-min*)
                          wpts
                          (<= (fit:wall-rms wpts a b 0.0)
                              (* (fit:flat-rms wpts (nth i base) flat)
                                 fit:*both-edge*))))
              (setq dirs (fit:setnth dirs i (nth i base))
                    offs (fit:setnth offs i flat)))))
        (setq bows (cons (if (and bowed (nth i coefs))
                           (fit:keep-bow wpts a b
                                         (fit:bow-cap
                                           (caddr (nth i coefs))
                                           (cal:dist a b)))
                           0.0)
                         bows)
              i    (1+ i)))
      (setq bows (reverse bows))
      (if (= n 8)
        (setq got2 (fit:grec-cuts dirs offs (fit:grec-face dirs offs))
              dirs (car got2)
              offs (cadr got2)))
      (if (fit:poly-valid dirs offs)
        (list dirs offs (if (fit:any-bow bows) bows nil))
        (list base offs nil)))))

;; ---- the arc-ended types (Roman / Oval) ------------------------------

;; A cap body's side wall at X.  The template holds the two walls
;; parallel; once the pool is allowed out of square each carries its
;; own slope, and By/Ty are its height at the body's middle.
(defun fit:wall-y (prm side x / off slope)
  (if (= side "b")
    (setq off   (fit:pget prm 'By)
          slope (cond ((fit:pget prm 'sb)) (0.0)))
    (setq off   (fit:pget prm 'Ty)
          slope (cond ((fit:pget prm 'st)) (0.0))))
  (+ off (* slope (- x (cond ((fit:pget prm 'xm)) (0.0))))))

;; The body's centreline at X - level on a true pool, tilted on one
;; built wider at one end.
(defun fit:cap-cy (prm x)
  (/ (+ (fit:wall-y prm "b" x) (fit:wall-y prm "t" x)) 2.0))

;; Half the body's width at X.
(defun fit:cap-half (prm x)
  (/ (- (fit:wall-y prm "t" x) (fit:wall-y prm "b" x)) 2.0))

;; A side wall's own least-squares line through the points that chose
;; it, as (base mid slope): its height at MID, and how that height
;; rises with x.
(defun fit:cap-wall (wpts / n sx sy num den mid base p)
  (setq n   (length wpts)
        sx  0.0
        sy  0.0
        num 0.0
        den 0.0)
  (foreach p wpts (setq sx (+ sx (car p)) sy (+ sy (cadr p))))
  (setq mid (/ sx n) base (/ sy n))
  (foreach p wpts
    (setq num (+ num (* (- (car p) mid) (cadr p)))
          den (+ den (* (- (car p) mid) (- (car p) mid)))))
  (list base mid (if (> den 1.0e-9) (/ num den) 0.0)))

;; The angles the two side walls of an arc-ended body may really take.
;; They are not held parallel: a gunite shell slumps as it cures, so
;; one wall very often slants away from the other, and forcing them
;; parallel would push that lean straight back into the points.  Two
;; limits, both fit:*cap-oos-max* (10 degrees): how far one wall may
;; lean, and how far the two may diverge from each other.  Past either
;; the offender is CLAMPED, never zeroed - the points still know which
;; way the wall leans, only how far is in doubt.
(defun fit:cap-slopes (sb st / m ab at dv mid)
  (setq m  fit:*cap-oos-max*
        ab (max (- m) (min m (atan sb)))
        at (max (- m) (min m (atan st)))
        dv (- at ab))
  (if (> (abs dv) m)
    (setq mid (/ (+ ab at) 2.0)
          dv  (if (> dv 0.0) m (- m))
          ab  (- mid (/ dv 2.0))
          at  (+ mid (/ dv 2.0))))
  (list (cal:tan ab) (cal:tan at)))

;; How far off parallel the two side walls came out, in radians.
(defun fit:cap-divergence (prm)
  (- (atan (cond ((fit:pget prm 'st)) (0.0)))
     (atan (cond ((fit:pget prm 'sb)) (0.0)))))

;; Half-height of the spring points where the end arc leaves the end
;; line, clamped inside the side walls.
(defun fit:endcap-h (re cx r by ty / d)
  (setq d (- (* r r) (* (- re cx) (- re cx))))
  (if (<= d 0.0)
    0.0
    (min (sqrt d) (- (/ (- ty by) 2.0) 1.0e-6))))

;; endcap parameter access: PRM is an assoc list keyed by symbols
(defun fit:pget (prm key) (cdr (assoc key prm)))
(defun fit:pput (prm key val)
  (if (assoc key prm)
    (subst (cons key val) (assoc key prm) prm)
    (cons (cons key val) prm)))

;; Vertex run for one end cap: SIGN +1 = the +x end (walked bottom to
;; top), -1 = the -x end (walked top to bottom).  Stubs appear when the
;; arc springs meaningfully inside the corners.  CHAIN, when given,
;; replaces the single arc with the run of arcs the points asked for.
;; The end line runs between the side walls AT THIS END, so a pool
;; built wider at one end still closes on both.
(defun fit:cap-verts (re cx r sign prm chain / by ty cy h stub lo hi a1
                                              a2 b out)
  (setq by   (fit:wall-y prm "b" re)
        ty   (fit:wall-y prm "t" re)
        cy   (/ (+ by ty) 2.0)
        h    (fit:endcap-h re cx r by ty)
        stub (> (- (/ (- ty by) 2.0) h) 0.25)
        out  nil)
  (if (> sign 0)
    (progn
      (setq lo (list re (- cy h))
            hi (list re (+ cy h))
            a1 (angle (list cx cy) lo)
            a2 (angle (list cx cy) hi)
            b  (cal:tan (/ (cal:angnorm (- a2 a1)) 4.0)))
      (if stub (setq out (list (list (list re by) 0.0))))
      (setq out (append out (if chain chain (list (list lo b)))))
      (if stub
        (setq out (append out (list (list hi 0.0)
                                    (list (list re ty) 0.0))))
        (setq out (append out (list (list hi 0.0))))))
    (progn
      (setq hi (list re (+ cy h))
            lo (list re (- cy h))
            a1 (angle (list cx cy) hi)
            a2 (angle (list cx cy) lo)
            b  (cal:tan (/ (cal:angnorm (- a2 a1)) 4.0)))
      (if stub (setq out (list (list (list re ty) 0.0))))
      (setq out (append out (if chain chain (list (list hi b)))))
      (if stub
        (setq out (append out (list (list lo 0.0)
                                    (list (list re by) 0.0))))
        (setq out (append out (list (list lo 0.0)))))))
  out)

;; Outline vertex list of the fitted end-capped body, frame coords.
;; BOWS (nil = none) is (bottom top): the two side walls may bow like
;; any other straight wall.  CHAINS (nil = none) is (right left): an
;; end a single radius could not hold, rebuilt as a run of arcs.
(defun fit:endcap-verts (prm kind both bows chains / verts itop ibot
                                                    m a b)
  (setq verts (fit:cap-verts (fit:pget prm 'Re) (fit:pget prm 'cx)
                             (fit:pget prm 'r) 1 prm (car chains))
        itop  (1- (length verts)))        ; the TOP wall leaves here
  (if both
    (setq verts (append verts
                        (fit:cap-verts (fit:pget prm 'Re2)
                                       (fit:pget prm 'cx2)
                                       (fit:pget prm 'r2) -1 prm
                                       (cadr chains))))
    (setq verts (append verts
                        (list (list (list (fit:pget prm 'Lx)
                                          (fit:wall-y prm "t"
                                                      (fit:pget prm 'Lx)))
                                    0.0)
                              (list (list (fit:pget prm 'Lx)
                                          (fit:wall-y prm "b"
                                                      (fit:pget prm 'Lx)))
                                    0.0)))))
  (setq ibot (1- (length verts)))         ; the BOTTOM wall leaves here
  (if bows
    (progn
      (setq m (length verts))
      (foreach a (list (cons 1 itop) (cons 0 ibot))
        (if (not (equal (nth (car a) bows) 0.0 1.0e-12))
          (setq b     (car (nth (rem (1+ (cdr a)) m) verts))
                verts (fit:setnth
                        verts (cdr a)
                        (list (car (nth (cdr a) verts))
                              (fit:bow-bulge
                                (nth (car a) bows)
                                (cal:dist (car (nth (cdr a) verts)) b)
                                (car (nth (cdr a) verts)) b))))))))
  verts)

;; (xl xr) - the x range the two side walls of a cap body run over.
(defun fit:cap-wall-span (prm both)
  (list (if both (fit:pget prm 'Re2) (fit:pget prm 'Lx))
        (fit:pget prm 'Re)))

;; The Roman/Oval side walls, refitted as shallow arcs.  Returns
;; (prm (bow-bottom bow-top)); the cap ends are left exactly as the
;; template fit left them.
(defun fit:fit-cap-bows (pts prm both / span lo hi yb yt bot top p k wpts
                                        a b got shift s bows)
  (setq span (fit:cap-wall-span prm both)
        lo   (min (car span) (cadr span))
        hi   (max (car span) (cadr span))
        yb   (fit:pget prm 'By)
        yt   (fit:pget prm 'Ty)
        bot  nil top nil)
  (foreach p pts
    (if (and (<= lo (car p)) (<= (car p) hi))
      (if (< (abs (- (cadr p) yb)) (abs (- (cadr p) yt)))
        (setq bot (cons p bot))
        (setq top (cons p top)))))
  (setq bows (list 0.0 0.0) k 0)
  (foreach wpts (list bot top)
    (setq a   (if (= k 0) (list lo yb) (list hi yt))
          b   (if (= k 0) (list hi yb) (list lo yt))
          got (fit:fit-wall-line wpts a b nil T))
    (if got
      (progn
        (setq shift (car got)
              s     (fit:bow-cap (caddr got) (cal:dist a b)))
        (if (= k 0)
          (setq yb  (- yb shift)
                prm (fit:pput prm 'By yb)
                a   (list (car a) yb)
                b   (list (car b) yb))
          (setq yt  (+ yt shift)
                prm (fit:pput prm 'Ty yt)
                a   (list (car a) yt)
                b   (list (car b) yt)))
        (setq bows (fit:setnth bows k (fit:keep-bow wpts a b s)))))
    (setq k (1+ k)))
  (list prm bows))

;; ICP for a rectangle body with a Roman or radius (Oval) end cap on
;; the +x end - and on the -x end too when BOTH.  Returns the fitted
;; parameter assoc list.
(defun fit:fit-endcap (pts kind both oos / bb x0 y0 x1 y1 w prm r0 yb yt
                                          cy cy1 cy2 byr tyr byl tyl
                                          inband lb lt sl
                                       xr xl bpts tpts lpts a1pts a2pts e1pts
                                       e2pts p darc1 darc2 dbot dtop dlft
                                       dend1 dend2 h1 h2 best bd cand cc
                                       ssum n d q)
  (setq bb (fit:bbox pts)
        x0 (car bb) y0 (cadr bb) x1 (caddr bb) y1 (cadddr bb)
        w  (- y1 y0)
        r0 (if (= kind "Oval") (/ w 2.0) (* 0.6 w))
        prm (list (cons 'By y0) (cons 'Ty y1) (cons 'Lx x0)
                  (cons 'sb 0.0) (cons 'st 0.0)
                  (cons 'xm (/ (+ x0 x1) 2.0))
                  (cons 'r r0) (cons 'cx (- x1 r0))))
  (setq prm (fit:pput prm 'Re
              (if (= kind "Oval")
                (fit:pget prm 'cx)
                (+ (fit:pget prm 'cx)
                   (sqrt (max 0.0 (- (* r0 r0) (* 0.16 w w))))))))
  (if both
    (progn
      (setq prm (fit:pput prm 'r2 r0)
            prm (fit:pput prm 'cx2 (+ x0 r0)))
      (setq prm (fit:pput prm 'Re2
                  (if (= kind "Oval")
                    (fit:pget prm 'cx2)
                    (- (fit:pget prm 'cx2)
                       (sqrt (max 0.0 (- (* r0 r0) (* 0.16 w w))))))))))
  (repeat fit:*icp-iters*
    (setq yb  (fit:pget prm 'By)
          yt  (fit:pget prm 'Ty)
          cy  (/ (+ yb yt) 2.0)
          xr  (fit:pget prm 'Re)
          xl  (if both (fit:pget prm 'Re2) (fit:pget prm 'Lx))
          prm (fit:pput prm 'xm (/ (+ xl xr) 2.0))
          cy1 (fit:cap-cy prm (fit:pget prm 'cx))
          cy2 (if both (fit:cap-cy prm (fit:pget prm 'cx2)) cy)
          byr (fit:wall-y prm "b" xr)
          tyr (fit:wall-y prm "t" xr)
          byl (fit:wall-y prm "b" xl)
          tyl (fit:wall-y prm "t" xl)
          h1  (fit:endcap-h (fit:pget prm 'Re) (fit:pget prm 'cx)
                            (fit:pget prm 'r) byr tyr)
          h2  (if both
                (fit:endcap-h (fit:pget prm 'Re2) (fit:pget prm 'cx2)
                              (fit:pget prm 'r2) byl tyl))
          bpts nil tpts nil lpts nil a1pts nil a2pts nil e1pts nil e2pts nil)
    (foreach p pts
      ;; distance to each feature; a point left of an arc's centre
      ;; falls back to its spring corners so side points never claim it
      (setq inband (and (<= xl (car p)) (<= (car p) xr))
            darc1 (if (< (car p) (fit:pget prm 'cx))
                    (min (cal:dist p (list (fit:pget prm 'Re) byr))
                         (cal:dist p (list (fit:pget prm 'Re) tyr)))
                    (abs (- (cal:dist p (list (fit:pget prm 'cx) cy1))
                            (fit:pget prm 'r))))
            darc2 (if both
                    (if (> (car p) (fit:pget prm 'cx2))
                      (min (cal:dist p (list (fit:pget prm 'Re2) byl))
                           (cal:dist p (list (fit:pget prm 'Re2) tyl)))
                      (abs (- (cal:dist p (list (fit:pget prm 'cx2) cy2))
                              (fit:pget prm 'r2)))))
            dbot  (if inband
                    (abs (- (cadr p) (fit:wall-y prm "b" (car p)))) 1.0e9)
            dtop  (if inband
                    (abs (- (cadr p) (fit:wall-y prm "t" (car p)))) 1.0e9)
            dlft  (if both 1.0e9 (abs (- (car p) (fit:pget prm 'Lx))))
            dend1 (if (> (abs (- (cadr p) cy1)) h1)
                    (abs (- (car p) (fit:pget prm 'Re))) 1.0e9)
            dend2 (if (and both (> (abs (- (cadr p) cy2)) h2))
                    (abs (- (car p) (fit:pget prm 'Re2))) 1.0e9))
      (setq cand (list (list dbot 'K-BOT) (list dtop 'K-TOP)
                       (list darc1 'K-ARC1)))
      (if both
        (setq cand (cons (list darc2 'K-ARC2) cand))
        (setq cand (cons (list dlft 'K-LFT) cand)))
      (if (= kind "ROman")
        (progn
          (setq cand (cons (list dend1 'K-END1) cand))
          (if both (setq cand (cons (list dend2 'K-END2) cand)))))
      (setq best nil bd nil)
      (foreach q cand
        (if (or (null bd) (< (car q) bd))
          (setq best (cadr q) bd (car q))))
      (cond
        ((eq best 'K-BOT)  (setq bpts (cons p bpts)))
        ((eq best 'K-TOP)  (setq tpts (cons p tpts)))
        ((eq best 'K-LFT)  (setq lpts (cons p lpts)))
        ((eq best 'K-ARC1) (setq a1pts (cons p a1pts)))
        ((eq best 'K-ARC2) (setq a2pts (cons p a2pts)))
        ((eq best 'K-END1) (setq e1pts (cons p e1pts)))
        ((eq best 'K-END2) (setq e2pts (cons p e2pts)))))
    ;; wall updates: a plain mean while the walls are held parallel,
    ;; two INDEPENDENT lines once the pool may be out of square - the
    ;; swing has to be in here, with the caps refitting against it each
    ;; round, not bolted on after the caps have settled.  Each wall
    ;; answers its own points and neither is tied to the other's
    ;; direction; fit:cap-slopes only says how far either may go.
    (if (not oos)
      (progn
        (if bpts
          (progn
            (setq ssum 0.0)
            (foreach p bpts (setq ssum (+ ssum (cadr p))))
            (setq prm (fit:pput prm 'By (/ ssum (length bpts))))))
        (if tpts
          (progn
            (setq ssum 0.0)
            (foreach p tpts (setq ssum (+ ssum (cadr p))))
            (setq prm (fit:pput prm 'Ty (/ ssum (length tpts)))))))
      (progn
        (setq lb (if bpts (fit:cap-wall bpts))
              lt (if tpts (fit:cap-wall tpts))
              sl (fit:cap-slopes
                   (if lb (caddr lb) (cond ((fit:pget prm 'sb)) (0.0)))
                   (if lt (caddr lt) (cond ((fit:pget prm 'st)) (0.0))))
              prm (fit:pput prm 'sb (car sl))
              prm (fit:pput prm 'st (cadr sl)))
        ;; the offset is the fitted line read at the body's middle, so
        ;; it has to follow the slope the clamp actually allowed
        (if lb
          (setq prm (fit:pput prm 'By
                              (+ (car lb)
                                 (* (car sl) (- (fit:pget prm 'xm)
                                                (cadr lb)))))))
        (if lt
          (setq prm (fit:pput prm 'Ty
                              (+ (car lt)
                                 (* (cadr sl) (- (fit:pget prm 'xm)
                                                 (cadr lt)))))))))
    (if (and lpts (not both))
      (progn
        (setq ssum 0.0)
        (foreach p lpts (setq ssum (+ ssum (car p))))
        (setq prm (fit:pput prm 'Lx (/ ssum (length lpts))))))
    (setq cy1 (fit:cap-cy prm (fit:pget prm 'cx))
          cy2 (if both (fit:cap-cy prm (fit:pget prm 'cx2)) cy1))
    ;; the +x cap
    (if a1pts
      (progn
        (if (= kind "Oval")
          (setq prm (fit:pput prm 'r (fit:cap-half prm (fit:pget prm 'cx))))
          (progn
            (setq ssum 0.0 cc (list (fit:pget prm 'cx) cy1))
            (foreach p a1pts (setq ssum (+ ssum (cal:dist p cc))))
            (setq prm (fit:pput prm 'r (/ ssum (length a1pts))))))
        (setq ssum 0.0 n 0)
        (foreach p a1pts
          (setq d (- (* (fit:pget prm 'r) (fit:pget prm 'r))
                     (* (- (cadr p) cy1) (- (cadr p) cy1))))
          (if (> d 0.0)
            (setq ssum (+ ssum (- (car p) (sqrt d)))
                  n    (1+ n))))
        (if (> n 0) (setq prm (fit:pput prm 'cx (/ ssum n))))))
    (if (= kind "Oval")
      (setq prm (fit:pput prm 'r (fit:cap-half prm (fit:pget prm 'cx)))
            prm (fit:pput prm 'Re (fit:pget prm 'cx)))
      (if e1pts
        (progn
          (setq ssum 0.0)
          (foreach p e1pts (setq ssum (+ ssum (car p))))
          (setq prm (fit:pput prm 'Re (/ ssum (length e1pts)))))))
    (setq prm (fit:pput prm 'Re
                (min (fit:pget prm 'Re)
                     (- (+ (fit:pget prm 'cx) (fit:pget prm 'r)) 0.5))))
    ;; the -x cap
    (if both
      (progn
        (if a2pts
          (progn
            (if (= kind "Oval")
              (setq prm (fit:pput prm 'r2
                                  (fit:cap-half prm (fit:pget prm 'cx2))))
              (progn
                (setq ssum 0.0 cc (list (fit:pget prm 'cx2) cy2))
                (foreach p a2pts (setq ssum (+ ssum (cal:dist p cc))))
                (setq prm (fit:pput prm 'r2 (/ ssum (length a2pts))))))
            (setq ssum 0.0 n 0)
            (foreach p a2pts
              (setq d (- (* (fit:pget prm 'r2) (fit:pget prm 'r2))
                         (* (- (cadr p) cy2) (- (cadr p) cy2))))
              (if (> d 0.0)
                (setq ssum (+ ssum (+ (car p) (sqrt d)))
                      n    (1+ n))))
            (if (> n 0) (setq prm (fit:pput prm 'cx2 (/ ssum n))))))
        (if (= kind "Oval")
          (setq prm (fit:pput prm 'r2
                              (fit:cap-half prm (fit:pget prm 'cx2)))
                prm (fit:pput prm 'Re2 (fit:pget prm 'cx2)))
          (if e2pts
            (progn
              (setq ssum 0.0)
              (foreach p e2pts (setq ssum (+ ssum (car p))))
              (setq prm (fit:pput prm 'Re2 (/ ssum (length e2pts)))))))
        (setq prm (fit:pput prm 'Re2
                    (max (fit:pget prm 'Re2)
                         (+ (- (fit:pget prm 'cx2) (fit:pget prm 'r2))
                            0.5)))))))
  prm)

;; ---- arcs that are not one arc ---------------------------------------
;;
;; A drawn end is one clean radius.  A built one very often is not: a
;; gunite shell caves in a little as it cures, and a single arc through
;; those points either misses them or lies about them.  So an end that
;; a single arc cannot hold within the distance the user typed is
;; rebuilt as a POLYLINE OF ARCS - each joint sitting on a survey
;; point, so the chain is continuous by construction and every joint is
;; a real measurement.  Extra arcs have to earn their place: the run
;; keeps the fewest that hold the points.  A symmetric cave-in is still
;; a circle and one arc handles it; this is for the ends that slumped
;; to one side.

;; Bulge of the arc P1 -> Q -> P2; 0.0 when degenerate.  ABHD's,
;; unchanged.
(defun fit:bulge-3pt (p1 q p2 / c a1 a2 aq dccw dq)
  (setq p1 (cal:2d p1) q (cal:2d q) p2 (cal:2d p2)
        c  (fit:circumcenter p1 q p2))
  (if (null c)
    0.0
    (progn
      (setq a1   (angle c p1)
            a2   (angle c p2)
            aq   (angle c q)
            dccw (cal:angnorm (- a2 a1))
            dq   (cal:angnorm (- aq a1)))
      (cond
        ((< dccw 1.0e-9) 0.0)
        ((> dccw (- (* 2.0 pi) 1.0e-9)) 0.0)
        ((<= dq dccw) (cal:tan (/ dccw 4.0)))
        (T (- (cal:tan (/ (- (* 2.0 pi) dccw) 4.0))))))))

;; Worst distance from any of QS to the arc (A B bulge).
(defun fit:span-dev (a b bul qs / seg mx d q)
  (setq seg (list a b bul) mx 0.0)
  (foreach q qs
    (setq d (fit:seg-dist q seg))
    (if (> d mx) (setq mx d)))
  mx)

;; The one arc from A to B that best fits QS: the exact 3-point arcs
;; through each point, plus their average, judged on worst deviation.
(defun fit:best-bulge (a b qs / bls sum q bl best bd d)
  (if (null qs)
    0.0
    (progn
      (setq bls (mapcar '(lambda (q) (fit:bulge-3pt a q b)) qs)
            sum 0.0)
      (foreach bl bls (setq sum (+ sum bl)))
      (setq bls (append bls (list (/ sum (length bls))))
            best 0.0 bd nil)
      (foreach bl bls
        (setq d (fit:span-dev a b bl qs))
        (if (or (null bd) (< d bd)) (setq best bl bd d)))
      best)))

;; ---- tangency: ABHD's continuity, on FITABHD's runs -----------------
;; At each joint the next arc's start tangent may differ from the
;; previous arc's end tangent by at most fit:*tang-tol*, so the curve
;; stays smooth while the POINTS still choose inside that window.

;; Tangent direction at the END of the arc A->B: the chord direction
;; plus half the included angle.
(defun fit:end-tangent (a b bul)
  (+ (angle (cal:2d a) (cal:2d b)) (* 2.0 (atan bul))))

;; Tangent direction where the arc A->B leaves A.
(defun fit:start-tangent (a b bul)
  (- (angle (cal:2d a) (cal:2d b)) (* 2.0 (atan bul))))

;; The bulges the span A->B may take if its START tangent is to stay
;; within WF * fit:*tang-tol* of the incoming tangent TE, as (lo . hi).
;; The edges are clamped so U-turn geometry stays finite.
(defun fit:tang-window (te a b wf / tt phi lo hi)
  (setq tt  (* fit:*tang-tol* wf)
        phi (cal:signed-dang te (angle (cal:2d a) (cal:2d b)))
        lo  (cal:tan (max -1.373 (min 1.373 (/ (- phi tt) 2.0))))
        hi  (cal:tan (max -1.373 (min 1.373 (/ (+ phi tt) 2.0)))))
  (if (<= lo hi) (cons lo hi) (cons hi lo)))

;; The bulges the CLOSING span A->B may take if its END tangent is to
;; stay within WF * fit:*tang-tol* of the ring's start tangent TS0.
(defun fit:end-window (ts0 a b wf / tt psi lo hi)
  (setq tt  (* fit:*tang-tol* wf)
        psi (cal:signed-dang (angle (cal:2d a) (cal:2d b)) ts0)
        lo  (cal:tan (max -1.373 (min 1.373 (/ (- psi tt) 2.0))))
        hi  (cal:tan (max -1.373 (min 1.373 (/ (+ psi tt) 2.0)))))
  (if (<= lo hi) (cons lo hi) (cons hi lo)))

;; Where two bulge windows overlap; nil when they do not.
(defun fit:isect-win (w1 w2 / lo hi)
  (cond
    ((null w1) w2)
    ((null w2) w1)
    (T (setq lo (max (car w1) (car w2))
             hi (min (cdr w1) (cdr w2)))
       (if (<= lo hi) (cons lo hi)))))

;; BUL held inside the window W.
(defun fit:clamp-bulge (bul w)
  (max (car w) (min (cdr w) bul)))

;; fit:best-bulge, but every candidate held inside the window W - so
;; the arc answers its points as well as it can WITHOUT leaving the
;; joint visibly kinked.
(defun fit:best-bulge-win (a b qs w / bls sum q bl best bd d)
  (cond
    ((null w) (fit:best-bulge a b qs))
    ((null qs) (fit:clamp-bulge 0.0 w))
    (T
     (setq bls (mapcar '(lambda (q) (fit:bulge-3pt a q b)) qs)
           sum 0.0)
     (foreach bl bls (setq sum (+ sum bl)))
     (setq bls  (mapcar '(lambda (bl) (fit:clamp-bulge bl w))
                        (append bls (list (/ sum (length bls)))))
           best (car bls) bd nil)
     (foreach bl bls
       (setq d (fit:span-dev a b bl qs))
       (if (or (null bd) (< d bd)) (setq best bl bd d)))
     best)))

;; The arc that continues the tangent TE smoothly and still answers QS.
;; The window is STRETCHED through fit:*tang-steps* rather than
;; abandoned, and the first stretch whose arc holds the points within
;; TOL wins.  TS0, on the closing span of a ring, also holds the far
;; end to the tangent the ring started with.
(defun fit:smooth-bulge (te a b qs tol ts0 / out done wf w)
  (setq out nil done nil)
  (foreach wf fit:*tang-steps*
    (if (not done)
      (progn
        (setq w (fit:tang-window te a b wf))
        (if ts0 (setq w (fit:isect-win w (fit:end-window ts0 a b wf))))
        (if w
          (progn
            (setq out (fit:best-bulge-win a b qs w))
            (if (<= (fit:span-dev a b out qs) tol) (setq done T)))))))
  (if (null out)                       ; the two ends cannot agree
    (setq out (fit:best-bulge-win
                a b qs (fit:tang-window te a b (last fit:*tang-steps*)))))
  out)

;; The worst joint in a run: how far the next arc's start tangent
;; departs from the previous arc's end tangent, in radians.  CLOSED
;; counts the seam as a joint too.
(defun fit:chain-kink (chain z closed / segs worst n i s1 s2 k)
  (setq segs  (fit:chain-segs chain z)
        n     (length segs)
        worst 0.0
        i     1)
  (while (< i n)
    (setq s1 (nth (1- i) segs)
          s2 (nth i segs)
          k  (abs (cal:signed-dang
                    (fit:end-tangent (car s1) (cadr s1) (caddr s1))
                    (fit:start-tangent (car s2) (cadr s2) (caddr s2)))))
    (if (> k worst) (setq worst k))
    (setq i (1+ i)))
  (if (and closed (> n 1))
    (progn
      (setq s1 (nth (1- n) segs)
            s2 (car segs)
            k  (abs (cal:signed-dang
                      (fit:end-tangent (car s1) (cadr s1) (caddr s1))
                      (fit:start-tangent (car s2) (cadr s2) (caddr s2)))))
      (if (> k worst) (setq worst k))))
  worst)

;; The (p1 p2 bulge) segments of a (point bulge) run ending at Z.
(defun fit:chain-segs (chain z / pts out i n)
  (setq pts (append (mapcar 'car chain) (list z))
        n   (length chain)
        out nil i 0)
  (while (< i n)
    (setq out (cons (list (nth i pts) (nth (1+ i) pts)
                          (cadr (nth i chain)))
                    out)
          i   (1+ i)))
  (reverse out))

;; A run of K arcs from A to Z through the ordered points QS.  The K-1
;; joints are survey points themselves, and every one of them is
;; SMOOTH: the first arc is free, each one after it starts inside the
;; tangency window of the arc before it.
(defun fit:arc-chain (qs a z k tol / n bounds s lo hi start end sub bl te
                                     out)
  (setq n      (length qs)
        bounds (list 0)
        s      1)
  (while (< s k)
    (setq bounds (append bounds (list (/ (* s n) k))) s (1+ s)))
  (setq bounds (append bounds (list n))
        out    nil te nil s 0)
  (while (< s k)
    (setq lo    (nth s bounds)
          hi    (nth (1+ s) bounds)
          start (if (= s 0) a (nth lo qs))
          end   (if (= s (1- k)) z (nth hi qs))
          sub   (fit:sublist qs lo (- hi lo))
          bl    (if te
                  (fit:smooth-bulge te start end sub tol nil)
                  (fit:best-bulge start end sub))
          out   (cons (list start bl) out)
          te    (fit:end-tangent start end bl)
          s     (1+ s)))
  (reverse out))

;; Worst distance from QS to a whole run.
(defun fit:chain-worst (chain z qs / segs mx q s d dmin)
  (setq segs (fit:chain-segs chain z) mx 0.0)
  (foreach q qs
    (setq dmin nil)
    (foreach s segs
      (setq d (fit:seg-dist q s))
      (if (or (null dmin) (< d dmin)) (setq dmin d)))
    (if (> dmin mx) (setq mx dmin)))
  mx)

;; The run of arcs from A to Z that best answers the ordered points QS.
;; ONE arc if one holds them within TOL - an end that really is one
;; radius stays one radius, and no chain appears.  Once a single arc
;; has failed, though, the run keeps going while each extra arc clearly
;; earns its place: stopping the moment it scrapes inside the tolerance
;; would leave the shell's real shape on the table, and the tangency
;; window is what keeps the result a curve rather than a row of facets.
;; Returns the (point bulge) run from A up to but not including Z.
(defun fit:fit-arc-run (qs a z tol / best worst kmax k trial w done)
  (setq best (list (list a (fit:best-bulge a z qs))))
  (if (null qs)
    best
    (progn
      (setq worst (fit:chain-worst best z qs))
      (if (<= worst tol)
        best                                ; one radius holds them
        (progn
          (setq kmax (max 1 (/ (length qs) fit:*arc-pts-min*))
                k    1
                done nil)
          (while (and (not done) (< k kmax))
            (setq k (1+ k))
            (if (<= worst fit:*on-eps*)
              (setq done T)     ; every point is ON it: nothing left to
              (progn            ; chase but the noise
                (setq trial (fit:arc-chain qs a z k tol)
                      w     (fit:chain-worst trial z qs))
                ;; not a clear enough gain - but a plateau is not the
                ;; end of the curve either, so keep looking
                (if (<= w (* worst fit:*both-edge*))
                  (setq best trial worst w)))))
          best)))))

;; The points sorted along the arc SEG, start to end.
(defun fit:order-along-arc (qs seg / g c a1 ccw keyed q rel)
  (setq g (fit:arc-geom (car seg) (cadr seg) (caddr seg)))
  (if (null g)
    qs
    (progn
      (setq c   (car g)
            a1  (caddr g)
            ccw (> (caddr seg) 0.0)
            keyed nil)
      (foreach q qs
        (setq rel (if ccw
                    (cal:angnorm (- (angle c q) a1))
                    (cal:angnorm (- a1 (angle c q))))
              keyed (cons (cons rel q) keyed)))
      (mapcar 'cdr (fit:sort-asc keyed)))))

;; sort (key . val) pairs ascending by key (insertion sort)
(defun fit:sort-asc (lst / out x)
  (foreach x lst (setq out (fit:ins-asc x out)))
  out)
(defun fit:ins-asc (x lst)
  (cond ((null lst) (list x))
        ((< (car x) (car (car lst))) (cons x lst))
        (T (cons (car lst) (fit:ins-asc x (cdr lst))))))

;; Index of the piece of SEGS that P is nearest to.
(defun fit:nearest-seg (p segs / best bd i s d)
  (setq best 0 bd nil i 0)
  (foreach s segs
    (setq d (fit:seg-dist p s))
    (if (or (null bd) (< d bd)) (setq best i bd d))
    (setq i (1+ i)))
  best)

;; The points whose nearest piece of the outline is segment I.
(defun fit:arc-seg-points (pts segs i / out p)
  (setq out nil)
  (foreach p pts
    (if (= i (fit:nearest-seg p segs)) (setq out (cons p out))))
  (reverse out))

;; ---- the Round pool --------------------------------------------------

(defun fit:fit-round (pts / cx cy r ssum sx sy p d n)
  (setq n  (length pts) sx 0.0 sy 0.0)
  (foreach p pts (setq sx (+ sx (car p)) sy (+ sy (cadr p))))
  (setq cx (/ sx n) cy (/ sy n))
  (repeat fit:*rad-iters*
    (setq ssum 0.0)
    (foreach p pts (setq ssum (+ ssum (cal:dist p (list cx cy)))))
    (setq r (/ ssum n) sx 0.0 sy 0.0)
    (foreach p pts
      (setq d (cal:dist p (list cx cy)))
      (if (< d 1.0e-9)
        (setq sx (+ sx (car p)) sy (+ sy (cadr p)))
        (setq sx (+ sx (- (car p) (* r (/ (- (car p) cx) d))))
              sy (+ sy (- (cadr p) (* r (/ (- (cadr p) cy) d)))))))
    (setq cx (/ sx n) cy (/ sy n)))
  (list (cons 'cx cx) (cons 'cy cy) (cons 'r r)))

;; the circle as two bulge-1 semicircles, as ABHD draws a CIRCLE - or
;; the run of arcs the points asked for, when it caved in
(defun fit:round-verts (prm chain / c r)
  (if chain
    chain
    (progn
      (setq c (list (fit:pget prm 'cx) (fit:pget prm 'cy))
            r (fit:pget prm 'r))
      (list (list (list (+ (car c) r) (cadr c)) 1.0)
            (list (list (- (car c) r) (cadr c)) 1.0)))))

;; ---- one result to rule them all -------------------------------------
;; A fit result is an assoc list keyed by symbols: kind (poly / cap /
;; round), type, angle, mirror, and the kind's own parameters.  The
;; outline always lives under 'verts as a closed (pt bulge) list in
;; FRAME coordinates.

(defun fit:rget (res key) (cdr (assoc key res)))
(defun fit:rput (res key val)
  (if (assoc key res)
    (subst (cons key val) (assoc key res) res)
    (cons (cons key val) res)))

(defun fit:res-fsegs (res) (fit:verts-to-segs (fit:rget res 'verts)))

;; the outline carried into world coordinates, still (pt bulge)
(defun fit:res-world-verts (res / a m out v)
  (setq a (fit:rget res 'angle)
        m (fit:rget res 'mirror)
        out nil)
  (foreach v (fit:rget res 'verts)
    (setq out (cons (list (fit:from-frame (car v) a m)
                          (if m (- (cadr v)) (cadr v)))
                    out)))
  (reverse out))

(defun fit:poly-result (ptype fpts dirs offs0 treat / fitres offs size
                                                      vsize which verts got2)
  (if (= 8 (length dirs))
    (progn
      ;; the cut corners are walls of their own here (Grecian, and a
      ;; Rectangle whose corners are Cut) - one shared face for all 4.
      ;; TREAT is the treatment of the eight VERTICES: a nominal
      ;; grecian is sharp, an as-built may well be rounded, so Radius
      ;; (or Cut) measures a shared easing from the points.
      (setq fitres (fit:fit-polytype fpts dirs offs0 "Square")
            offs   (car fitres)
            size   (fit:grec-face dirs offs)
            got2   (fit:grec-cuts dirs offs size)
            dirs   (car got2)
            offs   (cadr got2)
            vsize  nil)
      (if (member treat '("Radius" "Cut"))
        (setq fitres (fit:fit-vertex-feature fpts dirs offs treat)
              vsize  (car fitres)
              offs   (cadr fitres)
              size   (caddr fitres)))
      (setq which (if vsize T nil)
            verts (fit:build-polygon dirs offs treat vsize which nil))
      (list (cons 'kind 'poly) (cons 'type ptype) (cons 'dirs dirs)
            (cons 'offs offs) (cons 'treat treat) (cons 'size size)
            (cons 'vsize vsize) (cons 'which which) (cons 'verts verts)
            (cons 'bows nil) (cons 'valid (fit:poly-valid dirs offs))))
    (progn
      (setq fitres (fit:fit-polytype fpts dirs offs0 treat)
            offs   (car fitres)
            size   (cadr fitres)
            which  (if (member treat '("Radius" "Cut")) T nil)
            verts  (fit:build-polygon dirs offs treat size which nil))
      (list (cons 'kind 'poly) (cons 'type ptype) (cons 'dirs dirs)
            (cons 'offs offs) (cons 'treat treat) (cons 'size size)
            (cons 'which which) (cons 'verts verts) (cons 'bows nil)
            (cons 'valid (fit:poly-valid dirs offs))))))

(defun fit:cap-result (ptype fpts both oos / prm)
  (setq prm (fit:fit-endcap fpts ptype both oos))
  (list (cons 'kind 'cap) (cons 'type ptype) (cons 'prm prm)
        (cons 'both both) (cons 'valid T) (cons 'bows nil)
        (cons 'chains nil)
        (cons 'verts (fit:endcap-verts prm ptype both nil nil))))

(defun fit:fit-config (ptype fpts treat both oos)
  (cond
    ((= ptype "Rectangle")
     (if (= treat "Cut")
       (fit:poly-result ptype fpts fit:*grec-dirs* (fit:grec-init fpts)
                        "Square")
       (fit:poly-result ptype fpts fit:*rect-dirs* (fit:rect-init fpts)
                        treat)))
    ((= ptype "Grecian")
     (fit:poly-result ptype fpts fit:*grec-dirs* (fit:grec-init fpts)
                      treat))
    ((= ptype "L")
     (fit:poly-result ptype fpts fit:*l-dirs* (fit:l-init fpts nil)
                      treat))
    ((= ptype "LAzyl")
     (fit:poly-result ptype fpts fit:*lazy-dirs* (fit:l-init fpts T)
                      treat))
    (T (fit:cap-result ptype fpts both oos))))

;; (extra-rotation mirror both-ends) candidates per type
(defun fit:configs-for (ptype / q e out k m)
  (setq q (/ pi 2.0))
  (cond
    ((member ptype '("Rectangle" "Grecian")) (list (list 0.0 nil nil)))
    ((member ptype '("ROman" "Oval"))
     (setq out nil k 0)
     (repeat 4
       (setq out (cons (list (* k q) nil nil) out) k (1+ k)))
     (reverse (cons (list q nil T) (cons (list 0.0 nil T) out))))
    ((= ptype "L")
     (setq out nil k 0)
     (repeat 4
       (foreach m '(nil T)
         (setq out (cons (list (* k q) m nil) out)))
       (setq k (1+ k)))
     (reverse out))
    ((= ptype "LAzyl")
     (setq e (/ pi 4.0) out nil k 0)
     (repeat 8
       (foreach m '(nil T)
         (setq out (cons (list (* k e) m nil) out)))
       (setq k (1+ k)))
     (reverse out))
    (T (list (list 0.0 nil nil)))))

;; Order, frame, and try every placement the type allows; the
;; lowest-RMS one wins.  Returns the winning result with its frame
;; recorded; the outline stays in frame coordinates.
;; ---- fitting the frame angle of an arc-ended body --------------------
;; The frame is the body's own axis, and the edge vote cannot find it
;; once the two side walls lean by different amounts: every edge pulls
;; the vote towards its own direction, so the axis lands between the
;; walls and the flat end is drawn crooked.  The walls do not care -
;; each carries its own slope - but the end does, so the angle is
;; fitted too, and kept only if it beats the voted one.

;; One trial: the fit at angle A, as (rms res worst).
(defun fit:cap-at (dpts ptype treat both mirror a / fpts res dev)
  (setq fpts (fit:to-frame dpts a mirror)
        res  (fit:fit-config ptype fpts treat both T)
        dev  (fit:outline-dev fpts (fit:res-fsegs res)))
  (list (cadr dev) res (car dev)))

;; A one-degree sweep to find the basin, then golden section inside it.
(defun fit:refine-cap-angle (dpts ptype treat best / both mirror step n k
                                   a ba got bgot gr lo hi x1 x2 f1 f2 i)
  (setq both   (fit:rget best 'both)
        mirror (fit:rget best 'mirror)
        step   (/ pi 180.0)
        n      (fix (+ 0.5 (/ fit:*cap-oos-max* step)))
        ba     (fit:rget best 'angle)
        bgot   (fit:cap-at dpts ptype treat both mirror ba)
        k      (- n))
  (while (<= k n)
    (if (/= k 0)
      (progn
        (setq a   (+ (fit:rget best 'angle) (* k step))
              got (fit:cap-at dpts ptype treat both mirror a))
        (if (< (car got) (car bgot)) (setq ba a bgot got))))
    (setq k (1+ k)))
  (setq gr 0.6180339887
        lo (- ba step)
        hi (+ ba step)
        x1 (- hi (* gr (- hi lo)))
        x2 (+ lo (* gr (- hi lo)))
        f1 (fit:cap-at dpts ptype treat both mirror x1)
        f2 (fit:cap-at dpts ptype treat both mirror x2)
        i  0)
  (while (< i 16)
    (if (<= (car f1) (car f2))
      (setq hi x2                      ; shrink from the top
            x2 x1
            f2 f1
            x1 (- hi (* gr (- hi lo)))
            f1 (fit:cap-at dpts ptype treat both mirror x1))
      (setq lo x1 x1 x2 f1 f2
            x2 (+ lo (* gr (- hi lo)))
            f2 (fit:cap-at dpts ptype treat both mirror x2)))
    (setq i (1+ i)))
  (setq a   (/ (+ lo hi) 2.0)
        got (fit:cap-at dpts ptype treat both mirror a))
  (if (>= (car got) (car bgot)) (setq a ba got bgot))
  (if (>= (car got) (fit:rget best 'rms))
    best
    (progn
      (setq best (cadr got)
            best (fit:rput best 'angle a)
            best (fit:rput best 'mirror mirror)
            best (fit:rput best 'worst (caddr got))
            best (fit:rput best 'rms (car got)))
      best)))

(defun fit:fit-type (pts ptype treat oos / dpts prm tour a0 best cfg a fpts
                                       res dev worst rms edge)
  (setq dpts (cal:dedupe pts fit:*exact-eps*))
  (if (= ptype "ROUnd")
    (progn
      (setq prm (fit:fit-round dpts))
      (list (cons 'kind 'round) (cons 'type ptype) (cons 'prm prm)
            (cons 'angle 0.0) (cons 'mirror nil) (cons 'valid T)
            (cons 'chain nil)
            (cons 'verts (fit:round-verts prm nil))))
    (progn
      (setq tour (fit:order-points dpts)
            a0   (fit:frame-angle tour (if (= ptype "LAzyl") 8 4))
            best nil)
      (foreach cfg (fit:configs-for ptype)
        (setq a    (+ a0 (car cfg))
              fpts (fit:to-frame dpts a (cadr cfg))
              res  (fit:fit-config ptype fpts treat (caddr cfg) oos))
        (if (fit:rget res 'valid)
          (progn
            (setq dev   (fit:outline-dev fpts (fit:res-fsegs res))
                  worst (car dev)
                  rms   (cadr dev)
                  ;; a both-ends cap has more freedom than a single-
                  ;; ended one, so it only wins with a clear margin - a
                  ;; big flat arc can always shave a little rms off a
                  ;; genuinely square end
                  edge  (if (and (caddr cfg) best
                                 (not (fit:rget best 'both)))
                          fit:*both-edge*
                          1.0))
            (if (or (null best) (< rms (* (fit:rget best 'rms) edge)))
              (setq res  (fit:rput res 'angle a)
                    res  (fit:rput res 'mirror (cadr cfg))
                    res  (fit:rput res 'worst worst)
                    res  (fit:rput res 'rms rms)
                    best res)))))
      ;; a rectangle or grecian fits the same either way around -
      ;; report the long dimension as the length, deterministically
      (if (and best
               (member ptype '("Rectangle" "Grecian"))
               (> (fit:get-dim best 'WID) (fit:get-dim best 'LEN)))
        (progn
          (setq a    (+ (fit:rget best 'angle) (/ pi 2.0))
                fpts (fit:to-frame dpts a nil)
                res  (fit:fit-config ptype fpts treat nil oos)
                dev  (fit:outline-dev fpts (fit:res-fsegs res))
                res  (fit:rput res 'angle a)
                res  (fit:rput res 'mirror nil)
                res  (fit:rput res 'worst (car dev))
                res  (fit:rput res 'rms (cadr dev))
                best res)))
      ;; an arc-ended body whose walls lean unequally needs its frame
      ;; angle fitted as well, or the flat end comes out crooked
      (if (and oos best (eq (fit:rget best 'kind) 'cap))
        (setq best (fit:refine-cap-angle dpts ptype treat best)))
      best)))

;; ---- nice dimensions -------------------------------------------------
;; After the free fit, each headline dimension is snapped to the first
;; friendly increment - whole feet, half feet, inches, half inches -
;; that the points can live with: the snapped outline must stay within
;; the run tolerance (or, when an outlier already sits beyond it, move
;; nothing more than fit:*snap-eps*).  The points outrank pretty
;; numbers.

;; the snapping order per type: overall dims first, features after
(defun fit:dim-keys (res / t2)
  (setq t2 (fit:rget res 'type))
  (cond
    ((= t2 "Rectangle") '(LEN WID SIZE))
    ((= t2 "Grecian")
     (if (fit:rget res 'vsize) '(LEN WID CUT VSIZE) '(LEN WID CUT)))
    ((= t2 "L")         '(LEN WID WINGX WINGY SIZE))
    ((= t2 "LAzyl")     '(SIZE))
    ((= t2 "ROman")     '(WID BLEN RAD))
    ((= t2 "Oval")      '(WID BLEN))
    ((= t2 "ROUnd")     '(RAD))
    (T nil)))

(defun fit:get-dim (res key / t2 offs prm)
  (setq t2 (fit:rget res 'type))
  (cond
    ((eq (fit:rget res 'kind) 'poly)
     (setq offs (fit:rget res 'offs))
     (if (= 8 (length offs))
       (cond
         ((eq key 'LEN) (+ (nth 2 offs) (nth 6 offs)))
         ((eq key 'WID) (+ (nth 4 offs) (nth 0 offs)))
         ((member key '(CUT SIZE)) (fit:rget res 'size))
         ((eq key 'VSIZE) (fit:rget res 'vsize)))
       (cond
         ((eq key 'LEN)
          (+ (nth 1 offs)
             (nth (if (member t2 '("L" "LAzyl")) 5 3) offs)))
         ((eq key 'WID) (+ (nth 2 offs) (nth 0 offs)))
         ((eq key 'WINGX) (+ (nth 1 offs) (nth 3 offs)))
         ((eq key 'WINGY) (- (nth 2 offs) (nth 4 offs)))
         ((eq key 'SIZE) (fit:rget res 'size)))))
    ((eq (fit:rget res 'kind) 'cap)
     (setq prm (fit:rget res 'prm))
     (cond
       ((eq key 'WID) (- (fit:pget prm 'Ty) (fit:pget prm 'By)))
       ((eq key 'BLEN) (- (fit:pget prm 'Re)
                          (if (fit:rget res 'both)
                            (fit:pget prm 'Re2)
                            (fit:pget prm 'Lx))))
       ((eq key 'RAD) (fit:pget prm 'r))))
    ((eq key 'RAD) (fit:pget (fit:rget res 'prm) 'r))))

;; A copy of RES with the dimension forced to V and its outline
;; rebuilt.  Symmetric dims move both walls, keeping the centre.
(defun fit:set-dim (res key v / t2 offs prm d j w got2)
  (setq t2 (fit:rget res 'type))
  (cond
    ((eq (fit:rget res 'kind) 'poly)
     (setq offs (fit:rget res 'offs))
     (if (= 8 (length offs))
       (progn
         (cond
           ((eq key 'LEN)
            (setq d (/ (- v (+ (nth 2 offs) (nth 6 offs))) 2.0)
                  offs (fit:setnth offs 2 (+ (nth 2 offs) d))
                  offs (fit:setnth offs 6 (+ (nth 6 offs) d))))
           ((eq key 'WID)
            (setq d (/ (- v (+ (nth 4 offs) (nth 0 offs))) 2.0)
                  offs (fit:setnth offs 4 (+ (nth 4 offs) d))
                  offs (fit:setnth offs 0 (+ (nth 0 offs) d))))
           ((member key '(CUT SIZE))
            (setq res (fit:rput res 'size v)))
           ((eq key 'VSIZE)
            (setq res (fit:rput res 'vsize v))))
         (setq got2 (fit:grec-cuts (fit:rget res 'dirs) offs
                                   (fit:rget res 'size))
               res  (fit:rput res 'dirs (car got2))
               offs (cadr got2)))
       (cond
         ((eq key 'LEN)
          (setq j (if (member t2 '("L" "LAzyl")) 5 3)
                d (/ (- v (+ (nth 1 offs) (nth j offs))) 2.0)
                offs (fit:setnth offs 1 (+ (nth 1 offs) d))
                offs (fit:setnth offs j (+ (nth j offs) d)))
          (if (= t2 "L")                ; the wing dims ride on Rx
            (setq offs (fit:setnth offs 3 (- (nth 3 offs) d)))))
         ((eq key 'WID)
          (setq d (/ (- v (+ (nth 2 offs) (nth 0 offs))) 2.0)
                offs (fit:setnth offs 2 (+ (nth 2 offs) d))
                offs (fit:setnth offs 0 (+ (nth 0 offs) d)))
          (if (= t2 "L")
            (setq offs (fit:setnth offs 4 (+ (nth 4 offs) d)))))
         ((eq key 'WINGX)
          (setq offs (fit:setnth offs 3 (- v (nth 1 offs)))))
         ((eq key 'WINGY)
          (setq offs (fit:setnth offs 4 (- (nth 2 offs) v))))
         ((eq key 'SIZE)
          (setq res (fit:rput res 'size v)))))
     (setq res (fit:rput res 'offs offs))
     (fit:rput res 'verts
               (fit:build-polygon (fit:rget res 'dirs) offs
                                  (fit:rget res 'treat)
                                  (if (= 8 (length offs))
                                    (fit:rget res 'vsize)
                                    (fit:rget res 'size))
                                  (fit:rget res 'which)
                                  (fit:rget res 'bows))))
    ((eq (fit:rget res 'kind) 'cap)
     (setq prm (fit:rget res 'prm))
     (cond
       ((eq key 'WID)
        (setq w   (- (fit:pget prm 'Ty) (fit:pget prm 'By))
              d   (/ (- v w) 2.0)
              prm (fit:pput prm 'Ty (+ (fit:pget prm 'Ty) d))
              prm (fit:pput prm 'By (- (fit:pget prm 'By) d)))
        (if (= t2 "Oval")
          (progn
            (setq prm (fit:pput prm 'r (/ v 2.0)))
            (if (fit:rget res 'both)
              (setq prm (fit:pput prm 'r2 (/ v 2.0)))))))
       ((eq key 'BLEN)
        (if (fit:rget res 'both)
          (setq d   (/ (- v (- (fit:pget prm 'Re) (fit:pget prm 'Re2)))
                       2.0)
                prm (fit:pput prm 'Re (+ (fit:pget prm 'Re) d))
                prm (fit:pput prm 'cx (+ (fit:pget prm 'cx) d))
                prm (fit:pput prm 'Re2 (- (fit:pget prm 'Re2) d))
                prm (fit:pput prm 'cx2 (- (fit:pget prm 'cx2) d)))
          (setq prm (fit:pput prm 'Lx (- (fit:pget prm 'Re) v)))))
       ((eq key 'RAD)
        (setq prm (fit:pput prm 'r v))
        (if (fit:rget res 'both) (setq prm (fit:pput prm 'r2 v)))))
     (setq res (fit:rput res 'prm prm))
     (fit:rput res 'verts
               (fit:endcap-verts prm t2 (fit:rget res 'both)
                                 (fit:rget res 'bows)
                                 (fit:rget res 'chains))))
    (T
     (setq prm (fit:pput (fit:rget res 'prm) 'r v)
           res (fit:rput res 'prm prm))
     (fit:rput res 'verts (fit:round-verts prm
                                            (fit:rget res 'chain))))))

;; Snap each headline dimension to the first friendly increment the
;; points allow; the free value stays when none do.  Whole dimensions
;; may spend the run tolerance, but a MEASURED feature - a corner
;; radius, a cut face, a roman end radius - may only grow the worst
;; deviation by fit:*feat-snap*: an 8-inch as-built corner must not
;; become a foot just because the tolerance would absorb it.  On each
;; tier the two neighbouring multiples are both tried and the one
;; that fits the points better wins.
(defun fit:snap-result (res fpts tol allow / key v feature spend before
                                             after inc lo v2 trial w done
                                             bw bt)
  (foreach key (fit:dim-keys res)
    (setq v (fit:get-dim res key))
    (if (and v (> v 0.0))
      (progn
        (setq feature (member key '(SIZE VSIZE CUT RAD))
              spend   (if feature 0 allow)
              before  (fit:outline-dists fpts (fit:res-fsegs res))
              done    nil)
        (foreach inc fit:*nice-dims*
          (if (not done)
            (progn
              (setq lo (* inc (fix (/ v inc)))
                    bw nil bt nil)
              (foreach v2 (list lo (+ lo inc))
                (if (> v2 0.0)
                  (progn
                    (setq trial (fit:set-dim res key v2)
                          after (fit:outline-dists
                                  fpts (fit:res-fsegs trial)))
                    (if (fit:snap-ok before after tol allow feature)
                      (progn
                        (setq w (fit:held-worst after spend))
                        (if (or (null bw) (< w bw))
                          (setq bw w bt trial)))))))
              (if bt (setq res bt done T))))))))
  res)

;; How far from a corner a point belongs to the corner feature rather
;; than to a wall.
(defun fit:corner-zone-of (res)
  (cond
    ((fit:rget res 'vsize)
     (+ (* 1.2 (fit:rget res 'vsize) (cal:tan (/ pi 8.0)))
        fit:*zone-pad*))
    ;; on an eight-wall template the cut corners ARE walls, and "size"
    ;; is their face length - not a corner feature at all
    ((= 8 (length (fit:rget res 'offs))) 0.0)
    ((fit:rget res 'size) (+ (* 1.2 (fit:rget res 'size))
                             fit:*zone-pad*))
    ((member (fit:rget res 'treat) '("Radius" "Cut")) fit:*corner-zone*)
    (T 0.0)))

;; Refine the placement that already WON: let the walls answer to the
;; points.  A refinement is never a competitor in the search - the
;; extra freedom would let a wrong rotation bend its way to a good
;; score - so it runs once, on the winner.
(defun fit:apply-refinement (res fpts oos bowed / got dirs offs bows
                                                 swung prm a b)
  (cond
    ((eq (fit:rget res 'kind) 'poly)
     (setq got  (fit:refine-walls fpts (fit:rget res 'dirs)
                                  (fit:rget res 'offs)
                                  (fit:corner-zone-of res) oos bowed)
           dirs (car got)
           offs (cadr got)
           bows (caddr got)
           swung nil)
     (setq a (fit:rget res 'dirs) b dirs)
     (while a
       (if (> (abs (cal:signed-dang (car a) (car b))) 1.0e-9)
         (setq swung T))
       (setq a (cdr a) b (cdr b)))
     (if (and (null swung) (null bows))
       res
       (progn
         (setq res (fit:rput res 'dirs dirs)
               res (fit:rput res 'offs offs)
               res (fit:rput res 'bows bows)
               res (fit:rput res 'swung swung))
         (if (= 8 (length offs))
           (setq res (fit:rput res 'size (fit:grec-face dirs offs))))
         (fit:rput res 'verts
                   (fit:build-polygon dirs offs (fit:rget res 'treat)
                                      (if (= 8 (length offs))
                                        (fit:rget res 'vsize)
                                        (fit:rget res 'size))
                                      (fit:rget res 'which) bows)))))
    ((and (eq (fit:rget res 'kind) 'cap) bowed)
     ;; the SWING of these walls is fitted inside fit:fit-endcap, with
     ;; the caps answering to it each round; only the bow is left to do
     (setq got  (fit:fit-cap-bows fpts (fit:rget res 'prm)
                                  (fit:rget res 'both))
           prm  (car got)
           bows (cadr got))
     (if (null (fit:any-bow bows))
       res
       (progn
         (setq res (fit:rput res 'prm prm)
               res (fit:rput res 'bows bows))
         (fit:rput res 'verts
                   (fit:endcap-verts prm (fit:rget res 'type)
                                     (fit:rget res 'both) bows
                                     (fit:rget res 'chains))))))
    (T res)))                             ; a round pool has no walls

;; T when any wall of BOWS came out bowed.
(defun fit:any-bow (bows / found b)
  (foreach b bows
    (if (and b (not (equal b 0.0 1.0e-12))) (setq found T)))
  found)

;; Rebuild any arc a single radius cannot hold as a run of arcs
;; through the points.  This runs LAST, after the dimensions are
;; settled: a chain changes no dimension, it just stops the outline
;; lying about where the shell actually went.  The joints sit on
;; survey points and stay inside the tangency window, so the run is
;; both a real measurement and a smooth curve.

;; The whole outline of a Round pool as one closed run of K arcs, the
;; joints spaced evenly round the (already rotated) survey.
(defun fit:round-chain-of (qs n k tol / trial i lo hi a nxt sub bl te
                                       ts0)
  (setq trial nil i 0)
  (while (< i k)
    (setq trial (cons (list (nth (/ (* i n) k) qs) 0.0) trial)
          i     (1+ i)))
  (setq trial (reverse trial) i 0 te nil ts0 nil)
  (while (< i k)
    (setq lo  (/ (* i n) k)
          hi  (if (= i (1- k)) n (/ (* (1+ i) n) k))
          a   (car (nth i trial))
          nxt (car (nth (rem (1+ i) k) trial))
          sub (fit:sublist qs lo (- hi lo)))
    (if (null te)
      (setq bl  (fit:best-bulge a nxt sub)
            ts0 (fit:start-tangent a nxt bl))
      (setq bl (fit:smooth-bulge te a nxt sub tol
                                 (if (= i (1- k)) ts0))))
    (setq trial (fit:setnth trial i (list a bl))
          te    (fit:end-tangent a nxt bl)
          i     (1+ i)))
  trial)

(defun fit:round-chain (res fpts segs tol / qs n c keyed q best worst
                                           kmax k trial w done tw tc off)
  (setq qs (mapcar 'cal:2d fpts) n (length qs))
  (if (< n (* 2 fit:*arc-pts-min*))
    res
    (progn
      (setq c     (list (fit:pget (fit:rget res 'prm) 'cx)
                        (fit:pget (fit:rget res 'prm) 'cy))
            keyed nil)
      (foreach q qs (setq keyed (cons (cons (angle c q) q) keyed)))
      (setq qs    (mapcar 'cdr (fit:sort-asc keyed))
            worst (fit:outline-worst qs segs)
            best  nil
            kmax  (/ n fit:*arc-pts-min*)
            k     2
            done  nil)
      ;; the ring only STARTS breaking up when one circle misses; from
      ;; there it keeps going while each extra arc earns its place,
      ;; exactly as an end cap's run does
      (if (<= worst tol) (setq done T))
      (while (and (not done) (< k kmax))
        (setq k  (1+ k)
              tw nil tc nil)
        (if (<= worst fit:*on-eps*)
          (setq done T)                     ; every point is ON it
          (progn
            ;; a closed ring has no natural first joint, and where the
            ;; joints land decides how well they bracket the cave-in,
            ;; so try the aligned run and one shifted half a span
            (foreach off (list 0 (/ n (* 2 k)))
              (setq trial (fit:round-chain-of
                            (append (fit:sublist qs off (- n off))
                                    (fit:sublist qs 0 off))
                            n k tol)
                    w     (fit:chain-worst trial (car (car trial)) qs))
              (if (or (null tw) (< w tw)) (setq tw w tc trial)))
            (if (<= tw (* worst fit:*both-edge*))
              (setq best tc worst tw)))))
      (if (null best)
        res
        (progn
          (setq res (fit:rput res 'chain best)
                res (fit:rput res 'kink
                              (fit:chain-kink best (car (car best)) T)))
          (fit:rput res 'verts
                    (fit:round-verts (fit:rget res 'prm) best)))))))

(defun fit:cap-chains (res fpts segs bulged tol / chains kinks side i s
                                                 qs run)
  (setq chains (list nil nil) kinks (list 0.0 0.0) side 0)
  (foreach i bulged
    (if (< side 2)
      (progn
        (setq s  (nth i segs)
              qs (fit:order-along-arc (fit:arc-seg-points fpts segs i) s))
        (if (>= (length qs) (* 2 fit:*arc-pts-min*))
          (progn
            (setq run (fit:fit-arc-run qs (car s) (cadr s) tol))
            (if (> (length run) 1)
              (setq chains (fit:setnth chains side run)
                    kinks  (fit:setnth kinks side
                                       (fit:chain-kink run (cadr s) nil))))))
        (setq side (1+ side)))))
  (if (or (car chains) (cadr chains))
    (progn
      (setq res (fit:rput res 'chains chains)
            res (fit:rput res 'kinks kinks))
      (fit:rput res 'verts
                (fit:endcap-verts (fit:rget res 'prm)
                                  (fit:rget res 'type)
                                  (fit:rget res 'both)
                                  (fit:rget res 'bows) chains)))
    res))

;; ---- the same rule on a polygon's own curves -------------------------
;; A corner fillet and a bowed wall are drawn as ONE arc for the same
;; reason an oval's end is: that is how the shape is described, not how
;; it was built.  Anything the outline draws as a single R may become a
;; run of arcs under exactly the rules the ends follow - it only starts
;; when one arc cannot hold the points within the typed tolerance, the
;; joints sit on survey points, every joint stays inside the tangency
;; window, each extra arc has to earn its place, and a curve carrying N
;; points may become at most N/3 arcs.  A straight wall has no bulge to
;; break up, so nothing happens to one.

;; Which vert each wall leaves from, and which vert each corner's own
;; curve starts at - the same walk fit:build-polygon does, so a run can
;; say WHICH corner or wall it rebuilt.  Returns (leaves starts).
(defun fit:poly-vert-map (dirs offs treat size which / corners n leaves
                                                      starts i cf k m)
  (setq corners (fit:poly-corners dirs offs)
        n       (length corners)
        leaves  nil
        starts  nil
        k       0
        i       0)
  (while (< i n)
    (setq cf (fit:corner-frame dirs i)
          m  (if which
               (length (fit:corner-verts
                         (nth (rem (+ i n -1) n) corners)
                         (nth i corners)
                         (nth (rem (1+ i) n) corners)
                         (car cf) treat size))
               1)
          starts (cons k starts)             ; the corner's own curve
          k      (+ k m)
          leaves (cons (1- k) leaves)        ; wall i leaves here
          i      (1+ i)))
  (list (reverse leaves) (reverse starts)))

;; Splice the run RUN in for vert K: the run's arcs replace the single
;; one, and every vert after it shifts along.
(defun fit:splice-run (verts k run / out i n v)
  (setq out nil i 0 n (length verts))
  (while (< i n)
    (if (= i k)
      (foreach v run (setq out (cons v out)))
      (setq out (cons (nth i verts) out)))
    (setq i (1+ i)))
  (reverse out))

;; Rebuild every curve of a polygon outline that one arc cannot hold.
;; Works back to front so an earlier splice cannot move a later index.
(defun fit:poly-chains (res fpts segs bulged tol / verts map leaves
                                                  starts runs k s qs run
                                                  nm j rest)
  (setq verts (fit:rget res 'verts)
        map   (fit:poly-vert-map (fit:rget res 'dirs) (fit:rget res 'offs)
                                 (fit:rget res 'treat)
                                 (if (= 8 (length (fit:rget res 'offs)))
                                   (fit:rget res 'vsize)
                                   (fit:rget res 'size))
                                 (fit:rget res 'which))
        leaves (car map)
        starts (cadr map)
        runs   nil)
  (foreach k (reverse bulged)
    (setq s  (nth k segs)
          qs (fit:order-along-arc (fit:arc-seg-points fpts segs k) s))
    (if (>= (length qs) (* 2 fit:*arc-pts-min*))
      (progn
        (setq run (fit:fit-arc-run qs (car s) (cadr s) tol))
        (if (> (length run) 1)
          (progn
            ;; name it before the splice moves anything
            (setq j  (fit:index-of k leaves)
                  nm (if j
                       (cons 'wall j)
                       (cons 'corner (fit:index-of k starts))))
            (setq runs (cons (list nm (length run)
                                   (fit:chain-kink run (cadr s) nil)
                                   (fit:chain-segs run (cadr s)))
                             runs)
                  verts (fit:splice-run verts k run)))))))
  (if (null runs)
    res
    (progn
      (setq res (fit:rput res 'runs runs))
      (fit:rput res 'verts verts))))

;; Where VAL sits in LST, or nil.
(defun fit:index-of (val lst / i out x)
  (setq i 0)
  (foreach x lst
    (if (and (null out) (= x val)) (setq out i))
    (setq i (1+ i)))
  out)

(defun fit:apply-arc-chains (res fpts tol / segs bulged i s)
  (if (not (member (fit:rget res 'kind) '(cap round poly)))
    res
    (progn
      (setq segs (fit:res-fsegs res) bulged nil i 0)
      (foreach s segs
        (if (> (abs (caddr s)) 1.0e-9) (setq bulged (cons i bulged)))
        (setq i (1+ i)))
      (setq bulged (reverse bulged))
      (cond
        ((null bulged) res)
        ((eq (fit:rget res 'kind) 'round)
         (fit:round-chain res fpts segs tol))
        ((eq (fit:rget res 'kind) 'poly)
         (fit:poly-chains res fpts segs bulged tol))
        (T (fit:cap-chains res fpts segs bulged tol))))))

;; worst distance from QS to a whole outline
(defun fit:outline-worst (qs segs / mx q s d dmin)
  (setq mx 0.0)
  (foreach q qs
    (setq dmin nil)
    (foreach s segs
      (setq d (fit:seg-dist q s))
      (if (or (null dmin) (< d dmin)) (setq dmin d)))
    (if (> dmin mx) (setq mx dmin)))
  mx)

;; The whole engine: configuration search, the bow refinement when the
;; walls may be bowed, then nice-dim snapping against the share of the
;; points the user allows beyond the distance, then the final figures.  The outline stays in frame
;; coordinates under 'verts; fit:res-world-verts carries it out.
(defun fit:fit-and-snap (pts ptype treat tol pct oos bowed / dpts allow
                                                            res fpts dev)
  (setq dpts  (cal:dedupe pts fit:*exact-eps*)
        allow (cal:ceil (* pct (length dpts)))
        res   (fit:fit-type dpts ptype treat oos))
  (if (eq (fit:rget res 'kind) 'round)
    (setq fpts dpts)
    (setq fpts (fit:to-frame dpts (fit:rget res 'angle)
                             (fit:rget res 'mirror))))
  (if (or oos bowed)
    (setq res (fit:apply-refinement res fpts oos bowed)))
  (setq res (fit:snap-result res fpts tol allow)
        res (fit:apply-arc-chains res fpts tol)
        dev (fit:outline-dev fpts (fit:res-fsegs res))
        res (fit:rput res 'worst (car dev))
        res (fit:rput res 'rms (cadr dev))
        res (fit:rput res 'allow allow))
  res)

;; ---- entity creation and "this one is mine" stamping -----------------
;; FITABHD writes onto layers the drawing may already use - FGStep in
;; particular - so everything it creates carries a small piece of
;; extended data naming this command, and only stamped objects are
;; ever erased again.

(defun fit:tag-mine (en / ed)
  (if en
    (progn
      (regapp "FITABHD")
      (setq ed (entget en))
      (entmod (append ed (list (list -3 (list "FITABHD"
                                              (cons 1000 "FITABHD"))))))))
  en)

;; Erase only FITABHD's own objects on a layer.  Returns how many went.
(defun fit:purge-mine (name / ss i n en)
  (setq n 0)
  (if (tblsearch "LAYER" name)
    (progn
      (setq ss (ssget "_X" (list (cons 8 name))))
      (if ss
        (progn
          (setq i 0)
          (repeat (sslength ss)
            (setq en (ssname ss i))
            (if (assoc -3 (entget en '("FITABHD")))
              (progn (entdel en) (setq n (1+ n))))
            (setq i (1+ i)))))))
  n)

;; verts: list of (pt bulge) in order, closed.  COL is an AutoCAD
;; colour index, or nil for BYLAYER.
(defun fit:make-pline (verts layer col / dxf v)
  (setq dxf (list '(0 . "LWPOLYLINE") '(100 . "AcDbEntity")
                  (cons 8 layer)))
  (if col (setq dxf (append dxf (list (cons 62 col)))))
  (setq dxf (append dxf (list '(100 . "AcDbPolyline")
                              (cons 90 (length verts)) '(70 . 1))))
  (foreach v verts
    (setq dxf (append dxf (list (cons 10 (car v)) (cons 42 (cadr v))))))
  (entmakex dxf))

;; The kept fit joins the POOL layer in ByLayer colour.
(defun fit:set-bylayer (en / ed)
  (cal:ensure-layer fit:*pool-layer* 4)
  (setq ed (entget en)
        ed (subst (cons 8 fit:*pool-layer*) (assoc 8 ed) ed))
  (if (assoc 62 ed) (setq ed (subst '(62 . 256) (assoc 62 ed) ed)))
  (entmod ed))

;; A LINE on the pool layer with linetype LTYP (nil = ByLayer).
(defun fit:make-line (p1 p2 ltyp / dxf)
  (setq dxf (list '(0 . "LINE") '(100 . "AcDbEntity")
                  (cons 8 fit:*pool-layer*)))
  (if ltyp (setq dxf (append dxf (list (cons 6 ltyp)))))
  (entmakex (append dxf
                    (list '(100 . "AcDbLine")
                          (cons 10 (list (car p1) (cadr p1) 0.0))
                          (cons 11 (list (car p2) (cadr p2) 0.0))))))

;; A CIRCLE on LAYER (the Round hopper ring and the miss rings).
(defun fit:make-circle (c r layer)
  (entmakex (list '(0 . "CIRCLE") '(100 . "AcDbEntity")
                  (cons 8 layer) '(100 . "AcDbCircle")
                  (cons 10 (list (car c) (cadr c) 0.0))
                  (cons 40 r))))

;; Make sure the DASHED2 linetype (the half-size dashes marking the
;; underwater break stubs) exists - pure entmake, no command calls.
(defun fit:ensure-dashed2 ()
  (if (not (tblsearch "LTYPE" "DASHED2"))
    (entmake (list '(0 . "LTYPE") '(100 . "AcDbSymbolTableRecord")
                   '(100 . "AcDbLinetypeTableRecord")
                   '(2 . "DASHED2") '(70 . 0)
                   '(3 . "Dashed (.5x) _ _ _ _ _")
                   '(72 . 65) '(73 . 2) '(40 . 9.0)
                   '(49 . 6.0) '(74 . 0)
                   '(49 . -3.0) '(74 . 0)))))

;; An aligned dimension measuring PA to PB in the current style, its
;; dimension line through PDL - or right on the measured stretch when
;; PDL is nil.  nil comes back when the drawing cannot take one.
(defun fit:make-dim (pa pb pdl / m)
  (setq m (if pdl pdl (cal:mid pa pb)))
  (entmakex (list '(0 . "DIMENSION") '(100 . "AcDbEntity")
                  (cons 8 fit:*pool-layer*)
                  '(100 . "AcDbDimension")
                  (cons 3 (getvar "DIMSTYLE"))
                  (cons 10 (list (car m) (cadr m) 0.0))
                  '(70 . 33)                     ; aligned + block flag
                  '(1 . "")                      ; text = the measurement
                  '(100 . "AcDbAlignedDimension")
                  (cons 13 (list (car pa) (cadr pa) 0.0))
                  (cons 14 (list (car pb) (cadr pb) 0.0)))))

;; ---- reading the selection -------------------------------------------
;; Same classifier as ABHD's: ab_pt blocks are points on any layer,
;; POINT entities and other blocks count on the POINTS layer.  The
;; run-scoped fit-pts / fit-npt / fit-ptnames are bound by the command.

(defun fit:add-point (p nm)
  (setq fit-npt     (1+ fit-npt)
        fit-pts     (cons p fit-pts)
        fit-ptnames (cons (cons p (if (and nm (/= nm "")) nm
                                    (itoa fit-npt)))
                          fit-ptnames)))

;; What to call the surveyed point at Q.
(defun fit:pt-name (q / nm p)
  (setq nm nil)
  (foreach p fit-ptnames
    (if (and (null nm) (< (cal:dist (car p) q) fit:*exact-eps*))
      (setq nm (cdr p))))
  (if nm nm "?"))

;; Sort the selection into survey points; anything else is counted and
;; ignored - the TYPE is the guide here, not drawn geometry.
(defun fit:gather (ss / i en ed lay typ nskip)
  (setq i 0 nskip 0)
  (while (< i (sslength ss))
    (setq en  (ssname ss i)
          ed  (entget en)
          lay (strcase (cdr (assoc 8 ed)))
          typ (cdr (assoc 0 ed))
          i   (1+ i))
    (cond
      ((and (= typ "INSERT")
            (= (strcase (cdr (assoc 2 ed))) (strcase fit:*point-block*)))
       (fit:add-point (cal:2d (cdr (assoc 10 ed)))
                      (cal:block-number en fit:*pt-tag*)))
      ((and (= lay (strcase fit:*point-layer*)) (= typ "POINT"))
       (fit:add-point (cal:2d (cdr (assoc 10 ed))) nil))
      ((and (= typ "INSERT") (= lay (strcase fit:*point-layer*)))
       (fit:add-point (cal:2d (cdr (assoc 10 ed))
                      )
                      (cal:block-number en fit:*pt-tag*)))
      (T (setq nskip (1+ nskip)))))
  (if (> nskip 0)
    (princ (strcat "\nFITABHD: " (itoa nskip)
                   " selected object(s) that are not survey points"
                   " were ignored - the pool TYPE is the guide here,"
                   " not drawn geometry.")))
  (length fit-pts))

;; ---- the report ------------------------------------------------------

;; a length in feet-and-inches, the way the sheets read
(defun fit:ftin (v) (rtos v 4 4))

;; The fitted dimensions, one line per figure, per type.
(defun fit:dims-lines (res / t2 out prm w co n i names size)
  (setq t2 (fit:rget res 'type) out nil)
  (cond
    ((eq (fit:rget res 'kind) 'poly)
     (if (member t2 '("L" "LAzyl"))
       (progn
         (setq co    (fit:poly-corners (fit:rget res 'dirs)
                                       (fit:rget res 'offs))
               n     (length co)
               names '("A-B" "B-C" "C-D" "D-E" "E-F" "F-A")
               i     0)
         (while (< i n)
           (setq out (cons (cons (strcat "Side " (nth i names))
                                 (fit:ftin (cal:dist
                                             (nth i co)
                                             (nth (rem (1+ i) n) co))))
                           out)
                 i   (1+ i))))
       (setq out (list (cons "Width" (fit:ftin (fit:get-dim res 'WID)))
                       (cons "Length" (fit:ftin (fit:get-dim res 'LEN))))))
     (setq size (fit:rget res 'size))
     (if (fit:rget res 'vsize)
       (setq out (cons (cons (if (= (fit:rget res 'treat) "Cut")
                               "Corner easing (cut)"
                               "Corner easing radius")
                             (fit:ftin (fit:rget res 'vsize)))
                       out)))
     (cond
       ((and (= 8 (length (fit:rget res 'offs))) size (> size 0.01))
        (if (and (member (fit:rget res 'treat) '("Radius" "Cut"))
                 (null (fit:rget res 'vsize)))
          (setq out (cons (cons "Corner easing"
                                "none measurable - drawn sharp")
                          out)))
        (setq out (cons (cons "Corner cut face" (fit:ftin size)) out)))
       ((and size (= (fit:rget res 'treat) "Radius"))
        (setq out (cons (cons "Corner radius" (fit:ftin size)) out)))
       ((and size (= (fit:rget res 'treat) "Cut"))
        (setq out (cons (cons "Corner cut face" (fit:ftin size)) out)))
       ((= (fit:rget res 'treat) "NotGiven")
        (setq out (cons (cons "Corners" "Not Given - drawn square")
                        out)))))
    ((eq (fit:rget res 'kind) 'cap)
     (setq prm (fit:rget res 'prm)
           w   (fit:get-dim res 'WID))
     (setq out (list (cons (if (= t2 "ROman") "Roman end(s)"
                             "Radius end(s)")
                           (if (fit:rget res 'both) "both ends"
                             "one end"))
                     (cons "End radius" (fit:ftin (fit:pget prm 'r)))
                     (cons "Straight length"
                           (fit:ftin (fit:get-dim res 'BLEN)))
                     (cons "Width" (fit:ftin w))))
     (if (= t2 "ROman")
       (setq out (cons (cons "Roman stub (S1)"
                             (fit:ftin (- (/ w 2.0)
                                          (fit:endcap-h
                                            (fit:pget prm 'Re)
                                            (fit:pget prm 'cx)
                                            (fit:pget prm 'r)
                                            (fit:pget prm 'By)
                                            (fit:pget prm 'Ty)))))
                       (cons (cons "Roman bulge (S)"
                                   (fit:ftin (- (+ (fit:pget prm 'cx)
                                                   (fit:pget prm 'r))
                                                (fit:pget prm 'Re))))
                             out)))))
    (T
     (setq out (list (cons "Diameter"
                           (fit:ftin (* 2.0 (fit:pget
                                              (fit:rget res 'prm) 'r))))))))
  (reverse out))

;; "A-B", "B-C", ... for wall I of an N-wall ring.
(defun fit:wall-name (i n)
  (strcat (chr (+ 65 i)) "-" (chr (+ 65 (rem (1+ i) n)))))

;; The radius a bow of sagitta S over a chord of C implies - the
;; "extremely high R" a wall drawn dead straight really has on site.
(defun fit:bow-radius (s c)
  (+ (/ (* c c) (* 8.0 (abs s))) (/ (abs s) 2.0)))

;; The lines an OUT-OF-SQUARE fit needs: every side by name, the
;; diagonals that pin the shape down (POOL's cross dims), and how far
;; off square the worst wall came out.  A pool held square needs none
;; of this - its sides are its two dimensions.
(defun fit:square-lines (res / dirs offs corners n i j out worst sw base
                               names prm xl xr)
  (if (eq (fit:rget res 'kind) 'cap)
    (progn
      (setq prm (fit:rget res 'prm)
            xr  (fit:pget prm 'Re)
            xl  (if (fit:rget res 'both)
                  (fit:pget prm 'Re2)
                  (fit:pget prm 'Lx)))
      (if (< (abs (- (fit:cap-half prm xr) (fit:cap-half prm xl))) 0.25)
        nil
        (list (cons "Width at one end"
                    (fit:ftin (* 2.0 (fit:cap-half prm xr))))
              (cons "Width at the other"
                    (fit:ftin (* 2.0 (fit:cap-half prm xl))))
              (cons "Out of square by"
                    (strcat (fit:ftin (abs (* 2.0
                                              (- (fit:cap-half prm xr)
                                                 (fit:cap-half prm xl)))))
                            " wider at one end"))
              (cons "Side walls off parallel"
                    (strcat (rtos (abs (/ (* 180.0
                                             (fit:cap-divergence prm))
                                          pi))
                                  2 2)
                            " deg")))))
    (fit:square-lines-poly res)))

(defun fit:square-lines-poly (res / dirs offs corners n i j out worst sw
                                   base names)
  (setq dirs (fit:rget res 'dirs)
        offs (fit:rget res 'offs)
        out  nil)
  (if (or (null dirs) (null (fit:rget res 'swung)))
    nil
    (progn
      (setq corners (fit:poly-corners dirs offs)
            n       (length corners)
            base    (fit:template-dirs (fit:rget res 'type)
                                       (fit:rget res 'treat) n)
            worst   0.0
            i       0)
      (while (< i n)
        (setq sw (abs (cal:signed-dang (nth i base) (nth i dirs))))
        (if (> sw worst) (setq worst sw))
        (setq out (cons (cons (strcat "Side " (fit:wall-name i n))
                              (fit:ftin (cal:dist
                                          (nth i corners)
                                          (nth (rem (1+ i) n) corners))))
                        out)
              i   (1+ i)))
      ;; the diagonals: every corner to the one opposite it
      (setq i 0)
      (while (< i (/ n 2))
        (setq j (rem (+ i (/ n 2)) n)
              out (cons (cons (strcat "Diagonal "
                                      (chr (+ 65 i)) "-" (chr (+ 65 j)))
                              (fit:ftin (cal:dist (nth i corners)
                                                  (nth j corners))))
                        out)
              i   (1+ i)))
      (setq out (cons (cons "Out of square by"
                            (strcat (rtos (/ (* 180.0 worst) pi) 2 2)
                                    " deg at the worst wall"))
                      out))
      (reverse out))))

;; The template directions a type started from, for measuring how far
;; a wall has swung.
(defun fit:template-dirs (ptype treat n)
  (cond
    ((= n 8) fit:*grec-dirs*)
    ((= ptype "L") fit:*l-dirs*)
    ((= ptype "LAzyl") fit:*lazy-dirs*)
    (T fit:*rect-dirs*)))

;; A line for any arc the fit had to rebuild as a run of arcs: how
;; many, and the radius of each - the shape a shell that caved in
;; actually took, instead of the one clean radius it was drawn with.
;; How smooth a run came out, for the report.  A joint is never
;; perfectly tangent - the arcs stay ON the survey points instead -
;; but it is always inside the window, and that is worth printing.
(defun fit:kink-text (k)
  (if (or (null k) (< k 1.0e-9))
    ""
    (strcat "  (joints smooth to "
            (rtos (/ (* 180.0 k) pi) 2 1) " deg)")))

(defun fit:chain-lines (res / out chains chain z segs s txt r r2 i nm)
  (setq out nil)
  (cond
    ((and (eq (fit:rget res 'kind) 'poly) (fit:rget res 'runs))
     (foreach r (fit:rget res 'runs)
       (setq segs (cadddr r) txt "")
       (foreach s segs
         (setq r2  (fit:bulge-radius (car s) (cadr s) (caddr s))
               txt (strcat txt (if (= txt "") "" " / ")
                           (if r2 (fit:ftin r2) "straight"))))
       (setq nm  (if (eq (car (car r)) 'wall)
                   (strcat "Wall "
                           (fit:wall-name (cdr (car r))
                                          (length (fit:rget res 'dirs))))
                   (strcat "Corner "
                           (chr (+ 65 (cdr (car r))))))
             out (cons (cons (strcat nm " is a run of")
                             (strcat (itoa (cadr r)) " arcs  R " txt
                                     (fit:kink-text (caddr r))))
                       out))))
    ((eq (fit:rget res 'kind) 'cap)
     (setq chains (fit:rget res 'chains) i 0)
     (foreach chain chains
       (if (and chain (> (length chain) 1))
         (progn
           (setq z    (fit:chain-close res i)
                 segs (fit:chain-segs chain z)
                 txt  "")
           (foreach s segs
             (setq r   (fit:bulge-radius (car s) (cadr s) (caddr s))
                   txt (strcat txt (if (= txt "") "" " / ")
                               (if r (fit:ftin r) "straight"))))
           (setq nm  (if (= i 0) "A" "B")
                 out (cons (cons (strcat "End " nm " is a run of")
                                 (strcat (itoa (length segs))
                                         " arcs  R " txt
                                         (fit:kink-text
                                           (nth i (fit:rget res 'kinks)))))
                           out))))
       (setq i (1+ i))))
    ((and (eq (fit:rget res 'kind) 'round) (fit:rget res 'chain))
     (setq chain (fit:rget res 'chain)
           segs  (fit:chain-segs chain (car (car chain)))
           txt   "")
     (foreach s segs
       (setq r   (fit:bulge-radius (car s) (cadr s) (caddr s))
             txt (strcat txt (if (= txt "") "" " / ")
                         (if r (fit:ftin r) "straight"))))
     (setq out (list (cons "Outline is a run of"
                           (strcat (itoa (length segs))
                                   " arcs  R " txt
                                   (fit:kink-text
                                     (fit:rget res 'kink))))))))
  (reverse out))

;; Where a cap's run of arcs lands: the far spring point of that end.
(defun fit:chain-close (res i / verts chain n j k)
  (setq verts (fit:rget res 'verts)
        chain (nth i (fit:rget res 'chains))
        n     (length verts)
        j     0 k nil)
  ;; the vertex after the run's last one closes it
  (while (< j n)
    (if (equal (car (nth j verts)) (car (last chain)) 1.0e-9)
      (setq k (rem (1+ j) n)))
    (setq j (1+ j)))
  (if k (car (nth k verts)) (car (car chain))))

;; Radius of the arc (A B bulge); nil when the segment is straight.
(defun fit:bulge-radius (a b bl / h)
  (if (< (abs bl) 1.0e-9)
    nil
    (progn
      (setq h (/ (cal:dist a b) 2.0))
      (/ (* h (1+ (* bl bl))) (* 2.0 (abs bl))))))

;; One report line per wall the fit found bowed.
(defun fit:bow-lines (res / bows out i n corners s c span nm)
  (setq bows (fit:rget res 'bows) out nil)
  (if bows
    (if (eq (fit:rget res 'kind) 'poly)
      (progn
        (setq corners (fit:poly-corners (fit:rget res 'dirs)
                                        (fit:rget res 'offs))
              n       (length corners)
              i       0)
        (while (< i n)
          (setq s (nth i bows))
          (if (and s (not (equal s 0.0 1.0e-12)))
            (setq c   (cal:dist (nth i corners)
                                (nth (rem (1+ i) n) corners))
                  out (cons (cons (strcat "Wall " (fit:wall-name i n)
                                          " bowed")
                                  (strcat (fit:ftin (abs s))
                                          (if (> s 0.0) " out" " in")
                                          "  (R "
                                          (fit:ftin (fit:bow-radius s c))
                                          ")"))
                            out)))
          (setq i (1+ i))))
      (progn
        (setq span (fit:cap-wall-span (fit:rget res 'prm)
                                      (fit:rget res 'both))
              c    (abs (- (cadr span) (car span)))
              i    0)
        (foreach s bows
          (if (and s (not (equal s 0.0 1.0e-12)))
            (setq nm  (if (= i 0) "A" "B")
                  out (cons (cons (strcat "Side wall " nm " bowed")
                                  (strcat (fit:ftin (abs s))
                                          (if (> s 0.0) " out" " in")
                                          "  (R "
                                          (fit:ftin (fit:bow-radius s c))
                                          ")"))
                            out)))
          (setq i (1+ i))))))
  (reverse out))

;; Ring every point beyond the tolerance on the miss layer (stamped, so
;; only FITABHD's own rings are ever swept) and print the hit report.
(defun fit:report (res dpts tol allow / segs non noff nbad q d dmin s
                                        keyed pr worst line)
  (setq segs (fit:verts-to-segs (fit:res-world-verts res))
        non 0 noff 0 nbad 0 keyed nil worst 0.0)
  (foreach q dpts
    (setq dmin nil)
    (foreach s segs
      (setq d (fit:seg-dist q s))
      (if (or (null dmin) (< d dmin)) (setq dmin d)))
    (if (> dmin worst) (setq worst dmin))
    (cond
      ((<= dmin fit:*on-eps*) (setq non (1+ non)))
      ((<= dmin tol) (setq noff (1+ noff)))
      (T (setq nbad (1+ nbad)
               keyed (cons (cons dmin q) keyed)))))
  (princ (strcat "\n\nFITABHD: " (fit:rget res 'type)
                 " template fitted at "
                 (rtos (rem (/ (* 180.0 (fit:rget res 'angle)) pi) 180.0)
                       2 2)
                 " degrees."))
  (foreach pr (append (fit:dims-lines res) (fit:square-lines res)
                      (fit:bow-lines res) (fit:chain-lines res))
    (setq line (car pr))
    (while (< (strlen line) 18) (setq line (strcat line " ")))
    (princ (strcat "\n  " line (cdr pr))))
  (princ (strcat "\n  Points on the outline:        " (itoa non)))
  (princ (strcat "\n  Points off within tolerance:  " (itoa noff)))
  (princ (strcat "\n  Points beyond tolerance:      " (itoa nbad)
                 "  (allowance " (itoa allow) ")"))
  (princ (strcat "\n  Worst point deviation:        " (rtos worst 2 3)))
  (if (> nbad allow)
    (princ (strcat "\n  MORE POINTS ARE BEYOND THE DISTANCE THAN YOU"
                   " ALLOWED (" (itoa nbad) " of " (itoa (length dpts))
                   ")."
                   "\n  Redo with a looser distance or a bigger"
                   " percentage, leave the strays out,"
                   "\n  or the survey may not be a " (fit:rget res 'type)
                   " at all.")))
  ;; rings from an earlier run describe a fit that no longer exists
  (fit:purge-mine fit:*miss-layer*)
  (if keyed
    (progn
      (cal:ensure-layer fit:*miss-layer* 1)
      (princ (strcat "\n  POINTS OFF THE FIT (" (itoa nbad)
                     "), ringed on " fit:*miss-layer* ", worst first:"))
      ;; insertion sort, worst first
      (setq keyed (fit:sort-desc keyed))
      (foreach pr keyed
        (fit:tag-mine (fit:make-circle (cdr pr) fit:*miss-radius*
                                       fit:*miss-layer*))
        (princ (strcat "\n    Pt." (fit:pt-name (cdr pr))
                       "   off by " (rtos (car pr) 4 4))))
      (princ (strcat "\n  A stray this far off is usually a mis-shot, a"
                     "\n  duplicate, or a feature the chosen type cannot"
                     "\n  say - ABHD traces those."))))
  nbad)

;; sort (key . val) pairs descending by key (insertion sort)
(defun fit:sort-desc (lst / out x)
  (foreach x lst (setq out (fit:ins-desc x out)))
  out)
(defun fit:ins-desc (x lst)
  (cond ((null lst) (list x))
        ((> (car x) (car (car lst))) (cons x lst))
        (T (cons (car lst) (fit:ins-desc x (cdr lst))))))

;; ---- the standard-hopper bottom --------------------------------------
;; The bottom is GENERATED, not traced: the type gave us the pool's own
;; frame, so the breaks run dead square across the chosen leg, the
;; hopper is the offset rectangle every standard order sheet means, and
;; the slopes are straight lines.  Anything fancier is ABHD/ADAB's job.

;; T when a typed string means "go back a step"
(defun fit:back-word (s)
  (member (strcase s) '("B" "BACK" "U" "UNDO")))

;; Show an offset the way it was typed: architectural when it came in
;; as feet-and-inches, plain inches otherwise.  DEF is (value . ftin).
(defun fit:fmt-off (def)
  (if (cdr def) (rtos (car def) 4 4) (rtos (car def) 2 2)))

;; Read a distance, remembering HOW it was typed - as feet-and-inches
;; (3'6) or plain inches (42).  Returns (value . ftin); Enter takes
;; DEF, a pair from the previous entry.  Typing B goes back (CAL-BACK)
;; when BACK is on.
(defun fit:get-off (msg def back / s v res)
  (setq res nil)
  (while (null res)
    (setq s (getstring T (strcat "\n" msg " <" (fit:fmt-off def) ">"
                                 (if back " [Back]" "") ": ")))
    (cond
      ((= s "") (setq res def))
      ((and back (fit:back-word s)) (setq res 'CAL-BACK))
      (T
       (setq v (distof s 4))
       (cond
         ((null v)
          (princ "\n  (that is not a distance - type inches like 42, or feet and inches like 3'6)"))
         ((<= v 0.0)
          (princ "\n  (the distance must be positive)"))
         (T (setq res (cons v (if (wcmatch s "*'*") T nil))))))))
  res)

;; The standard hopper in LEG coordinates: x = distance into the pool
;; from the deep end wall, y = across, side walls at S1 < S2.  DB/SB =
;; the two break stations, SO/BO the side and back offsets.  Returns
;; (pts lines): pts = (W1 W2 H1 H2 B1 B2 P1 P2), lines = (pa pb dashed).
(defun fit:hopper-layout (db sb s1 s2 so bo / w1 w2 h1 h2 b1 b2 p1 p2)
  (setq w1 (list db s1) w2 (list db s2)
        h1 (list db (+ s1 so)) h2 (list db (- s2 so))
        b1 (list bo (+ s1 so)) b2 (list bo (- s2 so))
        p1 (list sb s1) p2 (list sb s2))
  (list (list w1 w2 h1 h2 b1 b2 p1 p2)
        (list (list w1 h1 T) (list h2 w2 T)     ; deep-break stubs
              (list h1 h2 nil)                  ; deep break, solid run
              (list h1 b1 nil) (list b1 b2 nil) (list b2 h2 nil)
              (list h1 p1 nil) (list h2 p2 nil) ; straight slope lines
              (list p1 p2 nil))))               ; shallow break

;; direction frame->world (no translation)
(defun fit:ffd (v a mirror)
  (fit:rot (if mirror (list (car v) (- (cadr v))) v) a))

;; The pool's candidate deep ends, one leg per end wall the type has:
;; ((origin u v s1 s2) ...) in WORLD coordinates - origin ON the end
;; wall at its middle, u pointing INTO the pool, v across, the side
;; walls at v-coordinates s1 < s2 relative to the origin.
(defun fit:legs (res / t2 a m dirs offs corners ends e n c1 c2 o u v s1
                       s2 out prm)
  (setq t2 (fit:rget res 'type)
        a  (fit:rget res 'angle)
        m  (fit:rget res 'mirror)
        out nil)
  (if (eq (fit:rget res 'kind) 'poly)
    (progn
      (setq dirs    (fit:rget res 'dirs)
            offs    (fit:rget res 'offs)
            corners (fit:poly-corners dirs offs)
            n       (length dirs)
            ends    (cond ((= t2 "L") '(1 5))
                          ((= t2 "LAzyl") '(2 5))
                          ((= 8 n) '(2 6))
                          (T '(1 3))))
      (foreach e ends
        (setq c1 (nth e corners)
              c2 (nth (rem (1+ e) n) corners)
              o  (cal:mid c1 c2)
              u  (cal:v* (fit:wall-normal (nth e dirs)) -1.0)
              v  (cal:perp u)
              s1 (cal:dot v (cal:v- c1 o))
              s2 (cal:dot v (cal:v- c2 o)))
        (if (> s1 s2) (setq c1 s1 s1 s2 s2 c1))
        (setq out (cons (list (fit:from-frame o a m)
                              (fit:ffd u a m) (fit:ffd v a m) s1 s2)
                        out))))
    (progn                                ; cap types: end lines
      ;; each leg takes its cross extent from the walls AT ITS OWN END,
      ;; so a pool built wider at one end gets a hopper square to the
      ;; wall that is really there
      (setq prm (fit:rget res 'prm))
      (setq out (list (list (fit:from-frame
                              (list (fit:pget prm 'Re)
                                    (fit:cap-cy prm (fit:pget prm 'Re)))
                              a m)
                            (fit:ffd '(-1.0 0.0) a m)
                            (fit:ffd '(0.0 1.0) a m)
                            (- (fit:cap-half prm (fit:pget prm 'Re)))
                            (fit:cap-half prm (fit:pget prm 'Re)))))
      (if (fit:rget res 'both)
        (setq out (cons (list (fit:from-frame
                                (list (fit:pget prm 'Re2)
                                      (fit:cap-cy prm (fit:pget prm 'Re2)))
                                a m)
                              (fit:ffd '(1.0 0.0) a m)
                              (fit:ffd '(0.0 1.0) a m)
                              (- (fit:cap-half prm (fit:pget prm 'Re2)))
                              (fit:cap-half prm (fit:pget prm 'Re2)))
                        out))
        (setq out (cons (list (fit:from-frame
                                (list (fit:pget prm 'Lx)
                                      (fit:cap-cy prm (fit:pget prm 'Lx)))
                                a m)
                              (fit:ffd '(1.0 0.0) a m)
                              (fit:ffd '(0.0 1.0) a m)
                              (- (fit:cap-half prm (fit:pget prm 'Lx)))
                              (fit:cap-half prm (fit:pget prm 'Lx)))
                        out)))))
  out)

;; leg point -> world
(defun fit:leg-pt (leg p)
  (cal:v+ (car leg)
          (cal:v+ (cal:v* (cadr leg) (car p))
                  (cal:v* (caddr leg) (cadr p)))))

;; The standard-hopper flow over a kept fit.  Asks which end is deep,
;; the two break stations and the two offsets (Back steps backwards),
;; then draws the whole bottom square to the leg's own frame.
(defun fit:bottom (res / legs pick leg best bd lg d step go db sb so bo
                        v w lay pts lines ln p1w p2w h1 h2 w1 w2 mid)
  (setq legs (fit:legs res))
  (setq pick (getpoint "\nPick a point at the DEEP end of the pool: "))
  (if (null pick)
    (princ "\nFITABHD: no deep end picked - no bottom drawn.")
    (progn
      (setq best nil bd nil)
      (foreach lg legs
        (setq d (cal:dist (cal:2d pick) (car lg)))
        (if (or (null bd) (< d bd)) (setq best lg bd d)))
      (setq leg best
            w   (- (nth 4 leg) (nth 3 leg))
            step 1 go T)
      (while (and go (<= step 4))
        (cond
          ((= step 1)
           (setq v (fit:get-off
                     "Deep break - how far from the deep end wall?"
                     fit:*brk-deep* nil))
           (setq fit:*brk-deep* v db (car v) step 2))
          ((= step 2)
           (setq v (fit:get-off
                     "Shallow break - how far from the deep end wall?"
                     fit:*brk-shal* T))
           (cond
             ((eq v 'CAL-BACK)
              (princ "\nStepping back one step.")
              (setq step 1))
             ((<= (car v) (+ db 6.0))
              (princ "\n  (the shallow break must sit past the deep break - at least 6\" further from the deep end)"))
             (T (setq fit:*brk-shal* v sb (car v) step 3))))
          ((= step 3)
           (setq v (fit:get-off
                     "Hopper offset in from each side wall"
                     fit:*hop-side* T))
           (cond
             ((eq v 'CAL-BACK)
              (princ "\nStepping back one step.")
              (setq step 2))
             ((>= (* 2.0 (car v)) (- w 2.0))
              (princ (strcat "\n  (twice that offset leaves no hopper - the pool is only "
                             (fit:ftin w) " wide here)")))
             (T (setq fit:*hop-side* v so (car v) step 4))))
          ((= step 4)
           (setq v (fit:get-off
                     "Hopper offset in from the deep end wall"
                     fit:*hop-back* T))
           (cond
             ((eq v 'CAL-BACK)
              (princ "\nStepping back one step.")
              (setq step 3))
             ((>= (car v) (- db 1.0))
              (princ "\n  (the back offset must stay short of the deep break)"))
             (T (setq fit:*hop-back* v bo (car v) step 5))))))
      (if (> step 4)
        (progn
          (cal:ensure-layer fit:*pool-layer* 4)
          (fit:ensure-dashed2)
          (setq lay  (fit:hopper-layout db sb (nth 3 leg) (nth 4 leg)
                                        so bo)
                pts  (car lay)
                lines (cadr lay))
          (foreach ln lines
            (setq p1w (fit:leg-pt leg (car ln))
                  p2w (fit:leg-pt leg (cadr ln)))
            (fit:tag-mine
              (fit:make-line p1w p2w (if (caddr ln) "DASHED2" nil))))
          ;; the K/L/M string a foot off the deep break, shallow side
          (setq w1 (nth 0 pts) w2 (nth 1 pts)
                h1 (nth 2 pts) h2 (nth 3 pts)
                mid (+ db fit:*dim-off*))
          (foreach ln (list (list w1 h1) (list h1 h2) (list h2 w2))
            (fit:tag-mine
              (fit:make-dim (fit:leg-pt leg (car ln))
                            (fit:leg-pt leg (cadr ln))
                            (fit:leg-pt leg
                                        (list mid
                                              (/ (+ (cadr (car ln))
                                                    (cadr (cadr ln)))
                                                 2.0))))))
          ;; and one on the back offset, on the hopper's centreline
          (fit:tag-mine
            (fit:make-dim (fit:leg-pt leg (list 0.0 0.0))
                          (fit:leg-pt leg (list bo 0.0))
                          nil))
          (princ (strcat "\nFITABHD: standard hopper drawn on layer "
                         fit:*pool-layer* " - breaks at "
                         (fit:ftin db) " and " (fit:ftin sb)
                         " from the deep end, hopper "
                         (fit:ftin (- (- (nth 4 leg) so)
                                      (+ (nth 3 leg) so)))
                         " wide."))
          (princ "\nDeep-break stubs are dashed; the K/L/M string reads from the shallow side."))))))

;; A Round pool's bottom is a concentric hopper ring.
(defun fit:round-bottom (res / prm r v off c)
  (setq prm (fit:rget res 'prm)
        r   (fit:pget prm 'r)
        v   (fit:get-off "Hopper offset in from the wall"
                         fit:*hop-back* nil))
  (setq off (car v))
  (if (>= off (- r 1.0))
    (princ "\n  (that offset leaves no hopper - nothing drawn)")
    (progn
      (setq fit:*hop-back* v
            c (fit:from-frame (list (fit:pget prm 'cx)
                                    (fit:pget prm 'cy))
                              (fit:rget res 'angle)
                              (fit:rget res 'mirror)))
      (cal:ensure-layer fit:*pool-layer* 4)
      (fit:tag-mine (fit:make-circle c (- r off) fit:*pool-layer*))
      (fit:tag-mine (fit:make-dim c (cal:v+ c (list (- r off) 0.0)) nil))
      (princ (strcat "\nFITABHD: hopper ring drawn at "
                     (fit:ftin off) " in from the wall.")))))

;; ---- the questions ---------------------------------------------------
;; All five in one place, with Back stepping backwards through them,
;; so a Redo can re-open exactly the same questions without asking for
;; the selection again.  DEF is the current (ptype treat tol pct
;; bowed); Enter keeps each answer.  TOTAL is how many steps the run
;; has, so the labels read true on a first run (6, the selection last)
;; and on a Redo (5, the points already in hand).
(defun fit:ask-settings (def total / step ptype treat tol pct oos bowed v
                                    n)
  (setq ptype (nth 0 def)
        treat (nth 1 def)
        tol   (nth 2 def)
        pct   (nth 3 def)
        oos   (nth 4 def)
        bowed (nth 5 def)
        n     (itoa total)
        step  1)
  (while (<= step 6)
    (cond
      ((= step 1)
       (setq v (cal:askkw (strcat "\n  Step 1 of " n
                                  " - what type of pool is this?\nPool type")
                          fit:*types*
                          "Rectangle/Grecian/ROman/Oval/L/LAzyl/ROUnd"
                          ptype nil))
       (setq ptype v fit:*ptype* v step 2))
      ((= step 2)
       ;; the corner question - for a Grecian it asks about the eight
       ;; CUT-corner vertices: the nominal drawing is sharp, but an
       ;; as-built may well ease them, and Radius measures that easing
       ;; from the points (a fit too small to believe stays sharp).
       ;; The arc-ended and round templates keep their corners square.
       (cond
         ((member ptype '("Rectangle" "L" "LAzyl"))
          (princ (strcat "\n\n  Step 2 of " n
                         " - the pool corners.  The SIZE is not asked:"))
          (princ "\n  the radius or cut face is measured from the points.")
          (setq v (cal:asktreat "the pool corners"
                                (if fit:*treat* fit:*treat* "Radius") T)))
         ((= ptype "Grecian")
          (princ (strcat "\n\n  Step 2 of " n
                         " - the cut corners.  Nominal grecians are sharp,"))
          (princ "\n  but an as-built may ease them - Radius measures that easing")
          (princ "\n  from the points (too small to believe stays sharp).")
          (setq v (cal:asktreat "the cut corners"
                                (if fit:*gtreat* fit:*gtreat* "Radius") T)))
         (T (setq v "Square")))
       (if (eq v 'CAL-BACK)
         (progn (princ "\nStepping back one step.")
                (setq step 1))
         (progn
           (setq treat v)
           (if (member ptype '("Rectangle" "L" "LAzyl"))
             (setq fit:*treat* v))
           (if (= ptype "Grecian") (setq fit:*gtreat* v))
           (setq step 3))))
      ((= step 3)
       (princ (strcat "\n\n  Step 3 of " n
                      " - how far may the fitted outline sit from a"))
       (princ "\n  survey point?  Smaller hugs the survey; bigger lets the")
       (princ "\n  nice whole-foot dimensions win more often.")
       (initget 6 "Back Undo")
       (setq v (getdist (strcat "\nMaximum distance from a point <"
                                (rtos tol 2 3) "> [Back]: ")))
       (cond
         ((and (= (type v) 'STR) (member v '("Back" "Undo")))
          (princ "\nStepping back one step.")
          (setq step 2))
         (T
          (if (null v) (setq v tol))
          (if (> v fit:*tol-max*)
            (progn
              (princ (strcat "\n  (pulled back to "
                             (rtos fit:*tol-max* 2 1)
                             " - further than that and the fit is no"
                             " longer a trace of the points)"))
              (setq v fit:*tol-max*)))
          (setq tol v fit:*tol* v step 4))))
      ((= step 4)
       (princ (strcat "\n\n  Step 4 of " n
                      " - what percent of the points may sit BEYOND"))
       (princ "\n  that distance?  That slack is what buys whole-foot")
       (princ "\n  dimensions: a snap is kept when only this share of the")
       (princ "\n  points object to it.")
       (initget 6 "Back Undo")
       (setq v (getint (strcat "\nPercent of points allowed beyond <"
                               (itoa (fix (+ 0.5 (* 100.0 pct))))
                               "> [Back]: ")))
       (cond
         ((and (= (type v) 'STR) (member v '("Back" "Undo")))
          (princ "\nStepping back one step.")
          (setq step 3))
         ((null v) (setq step 5))
         ((> v 100)
          (princ "\n  (more than 100 makes no sense - using 100)")
          (setq pct 1.0 step 5))
         (T (setq pct (/ v 100.0) step 5))))
      ((= step 5)
       ;; POOL asks the same question of the same pools, in the same
       ;; words: an AB pool is built, not drawn, and almost none of
       ;; them come out true.  Outofsquare lets each wall swing a
       ;; little to answer its own points - and a pool that really is
       ;; square still comes out square, because a swing is kept only
       ;; where the points prove it.
       (if (= ptype "ROUnd")
         (setq v nil)                      ; a circle has no walls
         (progn
           (princ (strcat "\n\n  Step 5 of " n
                          " - is the pool in-square, or out of square?"))
           (princ "\n  Outofsquare lets each wall swing a little to honour the")
           (princ "\n  points; Insquare holds the template true and shows you")
           (princ "\n  the error instead.  A Roman or Oval's two side walls")
           (princ "\n  are not held parallel at all: a shell slumps as it")
           (princ "\n  cures, so one very often slants away from the other.")
           (setq v (cal:askkw "Is the pool in-square or out-of-square?"
                              "Insquare Outofsquare"
                              "Insquare/Outofsquare"
                              (if oos "Outofsquare" "Insquare") T))
           (if (not (eq v 'CAL-BACK)) (setq v (= v "Outofsquare")))))
       (if (eq v 'CAL-BACK)
         (progn (princ "\nStepping back one step.")
                (setq step 4))
         (setq oos v step 6)))
      ((= step 6)
       (if (= ptype "ROUnd")
         (setq v nil)                      ; a round pool has no walls
         (progn
           (princ (strcat "\n\n  Step 6 of " n
                          " - may the straight walls be bowed?"))
           (princ "\n  A wall drawn dead straight is very often a very long")
           (princ "\n  radius on site.  Yes measures a bow on every wall from")
           (princ "\n  the points and keeps it only where they prove one - a")
           (princ "\n  wall that really is straight stays straight, and no bow")
           (princ "\n  ever moves a corner.  No is the answer for a drawing that")
           (princ "\n  has to show clean straight walls whatever the site did.")
           (setq v (cal:askyn "Any bowed walls?"
                              (if bowed "Yes" "No") T))))
       (if (eq v 'CAL-BACK)
         (progn (princ "\nStepping back one step.")
                (setq step 5))
         (setq bowed v step 7)))))
  (setq fit:*oos* oos fit:*bowed* bowed)
  (list ptype treat tol pct oos bowed))

;; ---- leaving points out ----------------------------------------------
;; A fit that came out wrong is usually one bad shot dragging a wall.
;; On a Redo the user can set those points aside - and pick a ringed
;; one again to put it back.

;; T when Q is one of the points currently set aside.
(defun fit:omitted-p (q / found x)
  (foreach x fit-omit
    (if (< (cal:dist (car x) q) fit:*exact-eps*) (setq found T)))
  found)

;; The points the fit may use: everything gathered, less the ones set
;; aside.
(defun fit:active ( / out q)
  (setq out nil)
  (foreach q fit-pts
    (if (not (fit:omitted-p q)) (setq out (cons q out))))
  (reverse out))

;; The dashed ring marking a point left out of the fit.
(defun fit:omit-ring (p)
  (fit:ensure-dashed2)
  (cal:ensure-layer fit:*out-layer* 2)
  (fit:tag-mine
    (entmakex (list '(0 . "CIRCLE") '(100 . "AcDbEntity")
                    (cons 8 fit:*out-layer*) '(6 . "DASHED2")
                    (cons 62 1) '(100 . "AcDbCircle")
                    (cons 10 (list (car p) (cadr p) 0.0))
                    (cons 40 fit:*miss-radius*)))))

;; Which way a pick goes: (RESTORE . pt) when it lands nearer a point
;; already set aside, (OMIT . pt) when it lands nearer one still in the
;; fit, nil when it lands near neither.  Every pick is a toggle.
(defun fit:omit-choose (wp / w1 w2)
  (setq w1 (fit:nearest wp (fit:active))
        w2 (fit:nearest wp (mapcar 'car fit-omit)))
  (cond
    ((and w2 (or (null w1) (<= (cal:dist wp w2) (cal:dist wp w1))))
     (cons 'RESTORE w2))
    (w1 (cons 'OMIT w1))))

;; fit-omit without the entry for point Q (and its ring erased).
(defun fit:omit-drop (q / out x)
  (setq out nil)
  (foreach x fit-omit
    (if (< (cal:dist (car x) q) fit:*exact-eps*)
      (if (and (cadr x) (entget (cadr x))) (entdel (cadr x)))
      (setq out (cons x out))))
  (reverse out))

;; The omit/restore loop.  Each pick toggles: a point in the fit goes
;; out and gets a ring, a ringed one comes back in and loses it.
(defun fit:omit-loop ( / wp pick)
  (princ "\n\n  Any points to leave out this time?")
  (princ "\n  Pick each one (Enter for none) - mis-shots, duplicates, or")
  (princ "\n  anything the outline should not chase; each gets a dashed ring.")
  (if fit-omit
    (princ (strcat "\n  " (itoa (length fit-omit))
                   " point(s) are already out - picking one of those puts"
                   " it BACK IN.")))
  (while (setq wp (getpoint "\n  Point to leave out - or a ringed one to restore (Enter when done): "))
    (setq pick (fit:omit-choose (cal:2d wp)))
    (cond
      ((null pick) (princ "  - (no survey point near that pick)"))
      ((eq (car pick) 'RESTORE)
       (setq fit-omit (fit:omit-drop (cdr pick)))
       (princ (strcat "  - Pt." (fit:pt-name (cdr pick)) " back in")))
      (T
       (setq fit-omit (cons (list (cdr pick) (fit:omit-ring (cdr pick)))
                            fit-omit))
       (princ (strcat "  - leaving out Pt."
                      (fit:pt-name (cdr pick))))))))

;; Erase the omission rings; they are scaffolding, not a result.
(defun fit:omit-clear ( / x)
  (foreach x fit-omit
    (if (and (cadr x) (entget (cadr x))) (entdel (cadr x))))
  (princ))

;; ---- the commands ----------------------------------------------------

(defun c:FITABHDVER ()
  (princ (strcat "\nFITABHD " *fitabhd-version* " loaded."))
  (princ))

(defun c:FITABHD ( / *error* undo-open set ptype treat tol pct oos bowed
                    ss n res verts en swept ans again dpts
                    fit-pts fit-npt fit-ptnames fit-omit)
  (defun *error* (msg)
    ;; user settings come back FIRST so nothing below can skip them
    (cal:sysrestore)
    (if undo-open (command "_.UNDO" "_End"))
    (if (and msg (not (wcmatch (strcase msg)
                               "*BREAK*,*CANCEL*,*QUIT*,*EXIT*")))
      (princ (strcat "\nFITABHD error: " msg)))
    ;; cover mode lasts one run: leaked, it would quietly cost the next
    ;; FITABHD its bottom
    (setq fit:*nobottom* nil)
    (princ))
  (cal:syssave '("OSMODE" "CMDECHO" "CLAYER"))
  (setvar "CMDECHO" 0)
  (command "_.UNDO" "_Begin")
  (setq undo-open T)
  ;; a preview a dead run left behind describes nothing - sweep it
  (setq swept (fit:purge-mine fit:*out-layer*))
  (if (> swept 0)
    (princ (strcat "\nFITABHD: swept " (itoa swept)
                   " leftover preview outline(s) from an earlier run.")))
  (princ "\n\nFITABHD - fit a typical pool's template through the survey points.")
  (setq fit-pts nil fit-npt 0 fit-ptnames nil fit-omit nil
        set (fit:ask-settings (list fit:*ptype* "Square" fit:*tol*
                                    fit:*miss-pct* fit:*oos* fit:*bowed*)
                              7)
        ptype (nth 0 set))
  (princ (strcat "\n\n  Step 7 of 7 - select the survey points (POINTS layer or"
                 "\n  " fit:*point-block* " blocks)."))
  (princ "\n  Select objects: ")
  (setq ss (ssget '((0 . "POINT,INSERT"))))
  (cond
    ((null ss)
     (princ (strcat "\nNothing usable selected (POINT entities on layer "
                    fit:*point-layer* " or \"" fit:*point-block*
                    "\" block insertions).")))
    ((< (setq n (fit:gather ss)) (if (= ptype "ROUnd") 3 6))
     (princ (strcat "\nOnly " (itoa n) " survey point(s) found - a "
                    ptype " template needs at least "
                    (itoa (if (= ptype "ROUnd") 3 6)) ".")))
    (T
     (if (> n 150)
       (princ (strcat "\nFITABHD: " (itoa n)
                      " points - ordering and fitting will take a"
                      " little while, please wait...")))
     (setq again T)
     (while again
       (setq again nil
             ptype (nth 0 set) treat (nth 1 set) tol (nth 2 set)
             pct   (nth 3 set) oos   (nth 4 set) bowed (nth 5 set)
             dpts  (cal:dedupe (fit:active) fit:*exact-eps*))
       (if (< (length dpts) (if (= ptype "ROUnd") 3 6))
         (princ (strcat "\nToo few points left in the fit ("
                        (itoa (length dpts))
                        ") - put some back on the next Redo."))
         (progn
           (princ (strcat "\nFitting the " ptype
                          " template every way it can sit, keeping the"
                          " best..."))
           (setq res   (fit:fit-and-snap dpts ptype treat tol pct oos
                                         bowed)
                 verts (fit:res-world-verts res))
           (cal:ensure-layer fit:*out-layer* 2)
           (setq en (fit:tag-mine (fit:make-pline verts fit:*out-layer* 2)))
           (fit:report res dpts tol (fit:rget res 'allow))))
       (setq ans (cal:askkw "\nKeep this fit, or Redo it?"
                         "Keep Redo Erase" "Keep/Redo/Erase"
                         (if res "Keep" "Redo") nil))
       (cond
         ((= ans "Redo")
          ;; the preview and its rings describe a fit that is about to
          ;; stop existing
          (if (and en (entget en)) (entdel en))
          (fit:purge-mine fit:*miss-layer*)
          (setq en nil res nil)
          (princ "\n\nRedoing the fit - the same points, new settings.")
          (fit:omit-loop)
          (setq set   (fit:ask-settings set 6)
                again T))
         ((and (= ans "Keep") res)
          (fit:omit-clear)
          (fit:set-bylayer en)
          (princ (strcat "\nKept - the outline moved to layer "
                         fit:*pool-layer* " in ByLayer colour."))
          ;; cover mode answers this No without asking: a cover sheet
          ;; is the perimeter and nothing below it
          (if (and (not fit:*nobottom*)
                   (cal:askyn (if (= ptype "ROUnd")
                                "Add the bottom of the pool (hopper ring)?"
                                "Add the bottom of the pool (standard hopper)?")
                              "No" nil))
            (if (= ptype "ROUnd")
              (fit:round-bottom res)
              (fit:bottom res))
            (if fit:*nobottom*
              (princ "\nCover sheet - the pool bottom was skipped."))))
         (T
          (fit:omit-clear)
          (if (and en (entget en)) (entdel en))
          (fit:purge-mine fit:*miss-layer*)
          (princ "\nNothing kept - the drawing is unchanged."))))))
  (command "_.UNDO" "_End")
  (setq undo-open nil)
  (cal:sysrestore)
  (setq fit:*nobottom* nil)
  (princ))

;; FITABHD for a cover sheet: the same template fit, with the
;; pool-bottom question answered No before it is asked.  A command of
;; its own rather than a mode, so a button runs exactly what it names;
;; c:FITABHD clears the flag on both exits so it cannot leak.
(defun c:FITABHDCOVER ()
  (setq fit:*nobottom* t)
  (princ "\nFITABHDCOVER: cover sheet - the pool bottom will be skipped.")
  (c:FITABHD)
  (princ))

;; ----------------------------------------------------------------------
(princ (strcat "\nFITABHD " *fitabhd-version*
               " loaded.  Type FITABHD to run (FITABHDVER for the"
               " version)."))
(princ)


;;; ======================================================================
;;; >>> lhd.lsp
;;; ======================================================================

;;; ===================================================================
;;; LHD.LSP  --  Fit a top-down outline through laser-scanned points
;;; -------------------------------------------------------------------
;;; For AutoCAD 2018 and later (plain AutoLISP, no external libraries).
;;;
;;; Command:  LHD - fit an outline (closed or open) through the points
;;;
;;; SHARED BUILD: requires CALOFIN-LIB.lsp (load via CALOFIN-LOADER.lsp).
;;; Generic helpers live there under cal: - see STANDARDS.md.
;;;
;;; The laser-point sibling of ABHD.  ABHD fits a pool perimeter
;;; through ab_pt survey blocks; LHD fits the same kind of arcs-on-the-
;;; points outline through points that came off a laser scan of an
;;; uneven surface.  The fit itself is a flat TOP-DOWN PROJECTION:
;;; every coordinate is flattened to the XY plane before anything is
;;; fitted, exactly as ABHD does.  What the elevations DO decide -
;;; when the points carry any - is the single height the finished
;;; outline is drawn at: the command asks whether that should be the
;;; TOPMOST point, the BOTTOMMOST, the AVERAGE of them all, or zero.
;;;
;;; WHAT COUNTS AS A LASER POINT - the classifier is deliberately
;;; looser than ABHD's, because scan exports land in many shapes:
;;;   * an INSERT of the survey point block ("ab_pt"), on any layer;
;;;     its number attribute names the point in reports
;;;   * a plain POINT entity on ANY layer (ABHD insists on the POINTS
;;;     layer; laser exports rarely land there) - its Z, when nonzero,
;;;     is that point's elevation
;;;   * any other INSERT sitting on the POINTS layer
;;;   * a TEXT entity whose value reads as a number and that sits
;;;     within *LH-TEXT-EPS* of a point names that point's elevation
;;;     (the DRONE convention: elevation labels share the point's spot)
;;;
;;; CLOSED OR OPEN - asked per run.  Closed is ABHD's loop engine
;;; unchanged: nearest-neighbour tour + 2-opt, arcs grown span by span
;;; inside the tangent window, the seam held closed.  Open drops the
;;; loop: the two ends of the run are the farthest-apart pair of
;;; points (or two points you pick on a Redo), the ordering keeps both
;;; ends fixed, and the fitter walks the path once with no seam - the
;;; first span starts free and the last simply ends.
;;;
;;; HELD POINTS: the user may declare points that must be held
;;; ABSOLUTELY - control shots, tie-ins, anything scanned as an exact
;;; position.  A held point is never buried inside a span, so every
;;; span ends ON it and the fitted line passes through it exactly, in
;;; every candidate; it costs nothing from the miss allowance and the
;;; tangency window still applies at its joint (it is not a corner).
;;;
;;; Everything else is ABHD's behaviour, kept on purpose: the miss
;;; allowance, declared straight stretches and sharp corners, the
;;; curve cap with its relaxing refit, nice radii, and the three
;;; candidates (tight / as asked / few) drawn side by side to pick
;;; from.  A lines-only sketch on the POOL layer orders the points
;;; when the automatic order goes wrong; the kept outline lands on the
;;; POOL layer like ABHD's, so the rest of the toolset can read it.
;;; ===================================================================

;; ---- configuration -------------------------------------------------
(setq *lh-version*      "v1.3")     ; announced on load; release_lisp.py
                                    ; reads this banner and stamps the
                                    ; dated twin in releases/ from it
(setq *LH-POOL-LAYER*   "POOL")     ; layer of the ordering sketch, and
                                    ; where the kept outline ends up
(setq *LH-POINT-LAYER*  "POINTS")   ; layer whose POINTs/INSERTs are
                                    ; always points
(setq *LH-POINT-BLOCK*  "ab_pt")    ; block name whose INSERTs mark
                                    ; points wherever they sit
(setq *LH-OUT-LAYER*    "LHD-FIT")  ; layer the candidate fits go on
(setq *LH-MISS-LAYER*   "FGStep")   ; layer the "could not hold this
                                    ; point" rings go on; LHD stamps
                                    ; its objects and only erases its
                                    ; own (see lh:tag-mine)
(setq *LH-MISS-RADIUS*  4.0)        ; radius of those rings (4 inches)
(setq *LH-PT-TAG*       "number")   ; attribute tag on the point block
                                    ; naming the point, as in "Pt.17"
(setq *LH-WALL-LAYER*   "POOL-WALLS") ; layer for the dashed markers of
                                    ; declared straight stretches
(setq *LH-TOL-MAX*      2.0)        ; hard ceiling on the max-distance
                                    ; prompt (2 inches)
(setq *LH-TEXT-EPS*     6.0)        ; a numeric TEXT within this of a
                                    ; point is that point's elevation
                                    ; label (6 in; labels sit right on
                                    ; their points, so keep it small -
                                    ; a mispair would only nudge the
                                    ; output height, never the shape)
(setq *LH-COMPARE*                  ; the three candidate fits offered:
  '(("tight" 1 "red"    "most curves - least error")
    ("asked" 2 "yellow" "as asked")
    ("few"   4 "cyan"   "fewest curves - still within the distance")))
                                    ; same three aims as ABHD: "tight"
                                    ; fits to *LH-TIGHT-TOL* with no
                                    ; miss allowance and no cap;
                                    ; "asked" is the settings as
                                    ; typed; "few" lifts the miss
                                    ; allowance so arcs run as long as
                                    ; the typed distance permits
(setq *LH-TIGHT-TOL*    0.01)       ; the "tight" candidate's accuracy
                                    ; target (units)
(setq *LH-EXACT-EPS*    0.001)      ; "exactly on" threshold (units)
(setq *LH-FIT-EPS*      0.01)       ; an arc through an interior point
                                    ; must pass within twice this of it
                                    ; to count as anchored
(setq *LH-ON-EPS*       0.25)       ; a point within this of the result
                                    ; counts as ON it; only points off
                                    ; by more eat into the allowance
(setq *LH-MISS-PCT*     0.15)       ; share of the points (rounded UP)
                                    ; that may sit off the result by up
                                    ; to the tolerance
(setq *LH-CORNER-ANG*   (/ pi 4.0)) ; a point that turns more than this
                                    ; (45 deg) is a sharp corner: it
                                    ; may start or end a span but never
                                    ; gets buried inside one
(setq *LH-NICE-RADII* '(12.0 6.0 1.0)) ; preferred arc-radius tiers,
                                    ; tried in order: whole feet, half
                                    ; feet, whole inches
(setq *LH-TANG-TOL* (/ pi 22.5))    ; wiggle room from perfect tangency
                                    ; at each joint (8 degrees)
(setq *LH-TANG-STEPS* '(1.0 1.25 1.5)) ; when nothing fits inside the
                                    ; tangent window, stretch it by
                                    ; these multiples before falling
                                    ; back to a one-point stub
(setq *LH-SNAP-EPS*     0.02)       ; a nice-radius snap may move the
                                    ; covered points at most this far
                                    ; beyond where they already sat
(setq *LH-CHAIN-FUZZ*   1.0e-4)     ; endpoint-matching fuzz for
                                    ; chaining sketch segments
(if (null *LH-TOL*)   (setq *LH-TOL* 1.0))      ; default tolerance
(if (null *LH-SHAPE*) (setq *LH-SHAPE* "Closed")) ; closed or open,
                                    ; remembered per session
(if (null *LH-ZMODE*) (setq *LH-ZMODE* "Average")) ; where the outline
                                    ; sits in Z when the points carry
                                    ; elevations: Top / Bottom /
                                    ; Average / Zero, remembered
;; *LH-MAX-ARCS* : cap on the number of curved segments in the output;
;; nil = no cap.  Prompted for and remembered per session, like
;; *LH-TOL*.

;; ---- circle / arc geometry -----------------------------------------

;; Circumcenter of three points, nil when (nearly) collinear.
(defun lh:circumcenter (pa pb pc / x1 y1 x2 y2 x3 y3 d s1 s2 s3)
  (setq x1 (car pa) y1 (cadr pa)
        x2 (car pb) y2 (cadr pb)
        x3 (car pc) y3 (cadr pc)
        d  (* 2.0 (+ (* x1 (- y2 y3)) (* x2 (- y3 y1)) (* x3 (- y1 y2)))))
  (if (< (abs d) 1.0e-10)
    nil
    (progn
      (setq s1 (+ (* x1 x1) (* y1 y1))
            s2 (+ (* x2 x2) (* y2 y2))
            s3 (+ (* x3 x3) (* y3 y3)))
      (list (/ (+ (* s1 (- y2 y3)) (* s2 (- y3 y1)) (* s3 (- y1 y2))) d)
            (/ (+ (* s1 (- x3 x2)) (* s2 (- x1 x3)) (* s3 (- x2 x1))) d)))))

;; Bulge of the unique circular arc that starts at P1, ends at P2 and
;; passes through Q.  0.0 when collinear or a (near) full circle.
(defun lh:bulge-3pt (p1 q p2 / c a1 a2 aq dccw dq)
  (setq p1 (cal:2d p1) q (cal:2d q) p2 (cal:2d p2)
        c  (lh:circumcenter p1 q p2))
  (if (null c)
    0.0
    (progn
      (setq a1   (angle c p1)
            a2   (angle c p2)
            aq   (angle c q)
            dccw (cal:angnorm (- a2 a1))
            dq   (cal:angnorm (- aq a1)))
      (cond
        ((< dccw 1.0e-9) 0.0)                       ; degenerate sweep
        ((> dccw (- (* 2.0 pi) 1.0e-9)) 0.0)        ; degenerate sweep
        ((<= dq dccw) (cal:tan (/ dccw 4.0)))        ; CCW arc through Q
        (T (- (cal:tan (/ (- (* 2.0 pi) dccw) 4.0)))))))) ; CW through Q

;; Arc geometry of a bulged segment: (center radius angStart angEnd).
;; nil for a straight segment.
(defun lh:arc-geom (p1 p2 b / ch dir apex c)
  (if (< (abs b) 1.0e-9)
    nil
    (progn
      (setq p1   (cal:2d p1)
            p2   (cal:2d p2)
            ch   (cal:dist p1 p2)
            dir  (cal:v* (cal:v- p2 p1) (/ 1.0 ch))
            apex (cal:v+ (cal:mid p1 p2)
                         (cal:v* (cal:perp dir) (* -0.5 ch b)))
            c    (lh:circumcenter p1 apex p2))
      (if (null c)
        nil
        (list c (cal:dist c p1) (angle c p1) (angle c p2))))))

;; Distance from point P to segment (p1 p2 bulge).
(defun lh:seg-dist (p seg / p1 p2 b v w len2 t2 g c r a1 a2 ap sweep rel)
  (setq p  (cal:2d p)
        p1 (cal:2d (car seg))
        p2 (cal:2d (cadr seg))
        b  (caddr seg))
  (if (< (abs b) 1.0e-9)
    (progn
      (setq v    (cal:v- p2 p1)
            w    (cal:v- p p1)
            len2 (cal:dot v v))
      (if (< len2 1.0e-20)
        (cal:dist p p1)
        (progn
          (setq t2 (/ (cal:dot w v) len2))
          (if (< t2 0.0) (setq t2 0.0))
          (if (> t2 1.0) (setq t2 1.0))
          (cal:dist p (cal:v+ p1 (cal:v* v t2))))))
    (progn
      (setq g (lh:arc-geom p1 p2 b))
      (if (null g)
        (min (cal:dist p p1) (cal:dist p p2))
        (progn
          (setq c  (car g)  r (cadr g)
                a1 (caddr g) a2 (cadddr g)
                ap (angle c p))
          (if (> b 0.0)
            (setq sweep (cal:angnorm (- a2 a1)) rel (cal:angnorm (- ap a1)))
            (setq sweep (cal:angnorm (- a1 a2)) rel (cal:angnorm (- ap a2))))
          (if (<= rel sweep)
            (abs (- (cal:dist p c) r))
            (min (cal:dist p p1) (cal:dist p p2))))))))

;; Bulge of the arc that starts at A with tangent direction TANG
;; (radians) and ends at B.
(defun lh:tangent-bulge (a tang b / phi)
  (setq phi (cal:signed-dang tang (angle (cal:2d a) (cal:2d b))))
  (cal:tan (/ phi 2.0)))

;; Position of P along segment (p1 p2 bulge) as a 0..1 parameter,
;; used only to ORDER candidate points along the segment.
(defun lh:seg-param (p seg / p1 p2 b v w len2 g c a1 a2 ap sweep rel)
  (setq p  (cal:2d p)
        p1 (cal:2d (car seg))
        p2 (cal:2d (cadr seg))
        b  (caddr seg))
  (if (< (abs b) 1.0e-9)
    (progn
      (setq v (cal:v- p2 p1) w (cal:v- p p1) len2 (cal:dot v v))
      (if (< len2 1.0e-20) 0.0 (/ (cal:dot w v) len2)))
    (progn
      (setq g (lh:arc-geom p1 p2 b))
      (if (null g)
        0.0
        (progn
          (setq c (car g) a1 (caddr g) a2 (cadddr g) ap (angle c p))
          (if (> b 0.0)
            (setq sweep (cal:angnorm (- a2 a1))
                  rel   (cal:angnorm (- ap a1)))
            (setq sweep (cal:angnorm (- a1 a2))
                  rel   (- (cal:angnorm (- a1 a2))
                           (cal:angnorm (- ap a2)))))
          (if (< sweep 1.0e-10) 0.0 (/ rel sweep)))))))

;; ---- entity -> segment extraction ----------------------------------
;; A segment is (startPt endPt bulge), 2D points.

(defun lh:lw-segs (ed / pts bls item segs n closed)
  (setq pts nil bls nil)
  (foreach item ed
    (cond
      ((= (car item) 10)
       (setq pts (cons (cal:2d (cdr item)) pts)
             bls (cons 0.0 bls)))
      ((and (= (car item) 42) bls)
       (setq bls (cons (cdr item) (cdr bls))))))
  (setq pts (reverse pts) bls (reverse bls)
        closed (= 1 (logand 1 (cdr (assoc 70 ed))))
        segs nil n 0)
  (while (< n (1- (length pts)))
    (setq segs (cons (list (nth n pts) (nth (1+ n) pts) (nth n bls)) segs)
          n    (1+ n)))
  (if (and (> (length pts) 2)
           (or closed
               (< (cal:dist (last pts) (car pts)) *LH-CHAIN-FUZZ*)))
    (if (>= (cal:dist (last pts) (car pts)) *LH-CHAIN-FUZZ*)
      (setq segs (cons (list (last pts) (car pts) (last bls)) segs))))
  (reverse segs))

(defun lh:pl-segs (en / ed sub pts bls segs n closed)
  ;; heavy (old-style) 2D POLYLINE: walk its VERTEX sub-entities
  (setq ed (entget en)
        closed (= 1 (logand 1 (cdr (assoc 70 ed))))
        pts nil bls nil
        sub (entnext en))
  (while (and sub (= "VERTEX" (cdr (assoc 0 (setq ed (entget sub))))))
    (if (= 0 (logand 17 (cond ((cdr (assoc 70 ed))) (0))))
      (setq pts (cons (cal:2d (cdr (assoc 10 ed))) pts)
            bls (cons (cond ((cdr (assoc 42 ed))) (0.0)) bls)))
    (setq sub (entnext sub)))
  (setq pts (reverse pts) bls (reverse bls) segs nil n 0)
  (while (< n (1- (length pts)))
    (setq segs (cons (list (nth n pts) (nth (1+ n) pts) (nth n bls)) segs)
          n    (1+ n)))
  (if (and closed (> (length pts) 2))
    (setq segs (cons (list (last pts) (car pts) (last bls)) segs)))
  (reverse segs))

(defun lh:ent-segs (en / ed typ c r a1 a2 delta)
  (setq ed  (entget en)
        typ (cdr (assoc 0 ed)))
  (cond
    ((= typ "LINE")
     (list (list (cal:2d (cdr (assoc 10 ed)))
                 (cal:2d (cdr (assoc 11 ed)))
                 0.0)))
    ((= typ "ARC")
     (setq c  (cal:2d (cdr (assoc 10 ed)))
           r  (cdr (assoc 40 ed))
           a1 (cdr (assoc 50 ed))
           a2 (cdr (assoc 51 ed))
           delta (cal:angnorm (- a2 a1)))
     (if (< delta 1.0e-10) (setq delta (* 2.0 pi)))
     ;; a full-circle arc cannot be one bulged segment: two semis
     (if (> delta (- (* 2.0 pi) 1.0e-9))
       (list (list (polar c a1 r) (polar c (+ a1 pi) r) 1.0)
             (list (polar c (+ a1 pi) r) (polar c a1 r) 1.0))
       (list (list (polar c a1 r) (polar c a2 r) (cal:tan (/ delta 4.0))))))
    ((= typ "CIRCLE")
     (setq c (cal:2d (cdr (assoc 10 ed)))
           r (cdr (assoc 40 ed)))
     (list (list (polar c 0.0 r) (polar c pi r) 1.0)
           (list (polar c pi r) (polar c 0.0 r) 1.0)))
    ((= typ "LWPOLYLINE") (lh:lw-segs ed))
    ((= typ "POLYLINE") (lh:pl-segs en))
    (T nil)))

;; ---- chain loose sketch segments into one run ------------------------
;; The chain of SEGS in forward order, reversed segment by segment.
(defun lh:rev-segs (segs)
  (mapcar '(lambda (s) (list (cadr s) (car s) (- (caddr s)))) (reverse segs)))

;; Chain loose segments into one run, closed or open.  Unlike ABHD's
;; chainer this one accepts a chain that does not close: when nothing
;; joins the growing end any more, the chain is turned around once and
;; grown from its other end (an open sketch has two).  Returns
;; (closedflag . orderedSegs), or nil for an empty input; pieces that
;; join neither end are reported and ignored.
(defun lh:chain (segs / fwd start end found s rest flipped go)
  (if (null segs)
    nil
    (progn
      (setq fwd     (list (car segs))
            start   (car (car segs))
            end     (cadr (car segs))
            segs    (cdr segs)
            flipped nil
            go      T)
      (while (and go segs (>= (cal:dist end start) *LH-CHAIN-FUZZ*))
        (setq found nil rest nil)
        (foreach s segs
          (cond
            (found (setq rest (cons s rest)))
            ((< (cal:dist end (car s)) *LH-CHAIN-FUZZ*)
             (setq found s))
            ((< (cal:dist end (cadr s)) *LH-CHAIN-FUZZ*)
             (setq found (list (cadr s) (car s) (- (caddr s)))))
            (T (setq rest (cons s rest)))))
        (cond
          (found
           (setq fwd  (append fwd (list found))
                 end  (cadr found)
                 segs (reverse rest)))
          ((not flipped)
           (setq fwd     (lh:rev-segs fwd)
                 start   (car (car fwd))
                 end     (cadr (last fwd))
                 flipped T))
          (T (setq go nil))))
      (if segs
        (princ (strcat "\nLHD: warning - " (itoa (length segs))
                       " sketch segment(s) that join neither end of the"
                       " chain were ignored.")))
      (cons (< (cal:dist (cadr (last fwd)) (car (car fwd))) *LH-CHAIN-FUZZ*)
            fwd))))

;; ---- span fitting helpers --------------------------------------------
;; A "span" is one candidate segment from A to B judged against QS, the
;; scanned points it is supposed to represent.

;; Worst distance from any of QS to the segment (A B bulge).
(defun lh:span-dev (a b bul qs / seg mx d q)
  (setq seg (list a b bul) mx 0.0)
  (foreach q qs
    (setq d (lh:seg-dist q seg))
    (if (> d mx) (setq mx d)))
  mx)

;; The miss percentage in force for the current run.
(defun lh:misspct ()
  (if lh-miss-pct lh-miss-pct *LH-MISS-PCT*))

;; The "on the shape" threshold in force for the current run; scales
;; with the tolerance (a quarter of it, never below *LH-ON-EPS*).
;; lh-on-eps is bound per pass by lh:fit-pass / lh:fit-pass-open.
(defun lh:oneps ()
  (if lh-on-eps lh-on-eps *LH-ON-EPS*))

;; How many of QS sit farther than the on-the-shape threshold from the
;; segment - the points that would eat into the miss allowance.
(defun lh:span-misses (a b bul qs / seg c q lim)
  (setq seg (list a b bul) c 0 lim (lh:oneps))
  (foreach q qs
    (if (> (lh:seg-dist q seg) lim) (setq c (1+ c))))
  c)

;; Radius of the arc (A B bulge); nil for a straight segment.
(defun lh:bulge-radius (a b bl / h)
  (if (< (abs bl) 1.0e-9)
    nil
    (progn
      (setq h (/ (cal:dist a b) 2.0))
      (/ (* h (1+ (* bl bl))) (* 2.0 (abs bl))))))

;; Bulge of the arc from A to B with radius R, on the same side and
;; with the same minor/major-arc character as reference bulge BREF.
(defun lh:radius-bulge (a b r bref / h s bl)
  (setq h (/ (cal:dist a b) 2.0))
  (if (or (< r h) (< h 1.0e-9))
    nil
    (progn
      (setq s  (sqrt (- (* r r) (* h h)))
            bl (if (> (abs bref) 1.0)
                 (/ (+ r s) h)              ; major arc
                 (/ (- r s) h)))            ; minor arc
      (if (< bref 0.0) (- bl) bl))))

;; Try to snap the arc A->B (free-fit bulge BL over points QS) to a
;; nice radius, keeping every point within TOL and at most LEFT of
;; them off by more than the on-the-shape threshold.  When WIN (a
;; bulge interval) is given the snapped bulge must stay inside it.
;; Returns (bulge . misses) of the snapped arc, or nil.
(defun lh:snap-arc (a b bl qs tol left win / r0 h best tier lo hi
                                              cands r bl2 mis)
  (setq r0   (lh:bulge-radius a b bl)
        h    (/ (cal:dist a b) 2.0)
        best nil)
  (if (and r0 (< r0 1.0e6))       ; a huge radius is basically straight
    (foreach tier *LH-NICE-RADII*
      (if (null best)
        (progn
          (setq lo    (* tier (fix (/ r0 tier)))
                hi    (+ lo tier)
                cands (if (< (- r0 lo) (- hi r0))
                        (list lo hi)
                        (list hi lo)))
          (foreach r cands
            (if (and (null best) (>= r h) (> r 0.0))
              (progn
                (setq bl2 (lh:radius-bulge a b r bl))
                (if (and bl2
                         (or (null win)
                             (and (>= bl2 (car win)) (<= bl2 (cdr win))))
                         (<= (lh:span-dev a b bl2 qs) tol)
                         (<= (setq mis (lh:span-misses a b bl2 qs))
                             left))
                  (setq best (cons bl2 mis))))))))))
  best)

;; ---- point ordering and naming ---------------------------------------

;; Remove every element equal (within fuzz) to VAL from LST.
(defun lh:remove (val lst / out x)
  (foreach x lst
    (if (not (equal x val 1.0e-9)) (setq out (cons x out))))
  (reverse out))

;; Insert (key . val) pair X into the already-sorted list LST.
(defun lh:ins-car (x lst)
  (cond ((null lst) (list x))
        ((< (car x) (car (car lst))) (cons x lst))
        (T (cons (car lst) (lh:ins-car x (cdr lst))))))

;; Insertion-sort a list of (key . val) pairs ascending by key.
(defun lh:sort-car (lst / out x)
  (foreach x lst (setq out (lh:ins-car x out)))
  out)

;; T when the chained sketch contains at least one curved segment.
(defun lh:has-arcs (loop / r)
  (foreach s loop (if (>= (abs (caddr s)) 1.0e-9) (setq r T)))
  r)

;; Order points into a closed tour: nearest-neighbour walk from the
;; leftmost point, then 2-opt passes to remove crossings.  (ABHD's
;; closed-mode ordering, unchanged.)
(defun lh:order-points (pts / start cur tour rest best bd q d n i j k
                              pass improved ti ti1 tj tj1 delta head midl
                              taill)
  (setq start (car pts))
  (foreach q (cdr pts)
    (if (or (< (car q) (car start))
            (and (= (car q) (car start)) (< (cadr q) (cadr start))))
      (setq start q)))
  (setq cur  start
        rest (lh:remove start pts)
        tour (list start))
  (while rest
    (setq best nil bd nil)
    (foreach q rest
      (setq d (cal:dist cur q))
      (if (or (null bd) (< d bd)) (setq best q bd d)))
    (setq tour (cons best tour)
          cur  best
          rest (lh:remove best rest)))
  (setq tour (reverse tour)
        n    (length tour)
        pass 0
        improved T)
  (while (and improved (< pass 40))
    (setq improved nil pass (1+ pass) i 0)
    (while (< i (1- n))
      (setq j (1+ i))
      (while (< j n)
        (if (not (and (= i 0) (= j (1- n))))
          (progn
            (setq ti    (nth i tour)
                  ti1   (nth (1+ i) tour)
                  tj    (nth j tour)
                  tj1   (nth (rem (1+ j) n) tour)
                  delta (- (+ (cal:dist ti tj) (cal:dist ti1 tj1))
                           (+ (cal:dist ti ti1) (cal:dist tj tj1))))
            (if (< delta -1.0e-9)
              (progn                    ; reverse tour[i+1 .. j]
                (setq head nil midl nil taill nil k 0)
                (foreach q tour
                  (cond ((<= k i) (setq head (cons q head)))
                        ((<= k j) (setq midl (cons q midl)))
                        (T        (setq taill (cons q taill))))
                  (setq k (1+ k)))
                (setq tour     (append (reverse head) midl (reverse taill))
                      improved T)))))
        (setq j (1+ j)))
      (setq i (1+ i))))
  tour)

;; The farthest-apart pair of points, as (a b) - the automatic choice
;; of ends for an open run.
(defun lh:far-pair (pts / a b best q r d)
  (setq best -1.0 a nil b nil)
  (foreach q pts
    (foreach r pts
      (setq d (cal:dist q r))
      (if (> d best) (setq best d a q b r))))
  (list a b))

;; Order points into an OPEN run from E1 to E2 (nil = pick the
;; farthest-apart pair automatically): nearest-neighbour walk from E1,
;; E2 forced last, then 2-opt with BOTH ENDS FIXED.  Reversing
;; tour[i+1..j] changes only the edges (i,i+1) and (j,j+1); with j
;; capped at n-2 the index j+1 always exists, so there is no
;; wraparound and no closing edge to price - the closed 2-opt's delta
;; would charge for an edge an open run does not have.
(defun lh:order-points-open (pts e1 e2 / pr cur tour rest best bd q d n
                                          i j k ti ti1 tj tj1 delta head
                                          midl taill pass improved)
  (if (null e1)
    (progn
      (setq pr (lh:far-pair pts)
            e1 (car pr)
            e2 (cadr pr))))
  (setq cur  e1
        rest (lh:remove e2 (lh:remove e1 pts))
        tour (list e1))
  (while rest
    (setq best nil bd nil)
    (foreach q rest
      (setq d (cal:dist cur q))
      (if (or (null bd) (< d bd)) (setq best q bd d)))
    (setq tour (cons best tour)
          cur  best
          rest (lh:remove best rest)))
  (setq tour (reverse (cons e2 tour))
        n    (length tour)
        pass 0
        improved T)
  (while (and improved (< pass 40))
    (setq improved nil pass (1+ pass) i 0)
    (while (< i (- n 2))
      (setq j (1+ i))
      (while (< j (1- n))
        (setq ti    (nth i tour)
              ti1   (nth (1+ i) tour)
              tj    (nth j tour)
              tj1   (nth (1+ j) tour)
              delta (- (+ (cal:dist ti tj) (cal:dist ti1 tj1))
                       (+ (cal:dist ti ti1) (cal:dist tj tj1))))
        (if (< delta -1.0e-9)
          (progn                        ; reverse tour[i+1 .. j]
            (setq head nil midl nil taill nil k 0)
            (foreach q tour
              (cond ((<= k i) (setq head (cons q head)))
                    ((<= k j) (setq midl (cons q midl)))
                    (T        (setq taill (cons q taill))))
              (setq k (1+ k)))
            (setq tour     (append (reverse head) midl (reverse taill))
                  improved T)))
        (setq j (1+ j)))
      (setq i (1+ i))))
  tour)

;; Order points by their position along a chained ordering sketch:
;; each point keys on segment-index + parameter.
(defun lh:loop-order (loop pts / keyed q best bd d i s tp)
  (foreach q pts
    (setq best 0 bd nil i 0)
    (foreach s loop
      (setq d (lh:seg-dist q s))
      (if (or (null bd) (< d bd)) (setq bd d best i))
      (setq i (1+ i)))
    (setq tp (lh:seg-param q (nth best loop)))
    (if (< tp 0.0) (setq tp 0.0))
    (if (> tp 1.0) (setq tp 1.0))
    (setq keyed (cons (cons (+ best tp) q) keyed)))
  (mapcar 'cdr (lh:sort-car keyed)))

;; Remember a point, what to call it, and - when it has one - its
;; elevation, so a miss reports as "Pt.17" and the output height can
;; be taken from the points.  Points with no name get the next count.
(defun lh:add-point (p nm z)
  (setq npt        (1+ npt)
        pts        (cons p pts)
        lh-ptnames (cons (cons p (if (and nm (/= nm "")) nm (itoa npt)))
                         lh-ptnames))
  (if (and z (> (abs z) 1.0e-9))
    (setq lh-zvals (cons (cons p z) lh-zvals))))

;; What to call the scanned point at Q.
(defun lh:pt-name (q / nm p)
  (setq nm nil)
  (foreach p lh-ptnames
    (if (and (null nm) (< (cal:dist (car p) q) *LH-EXACT-EPS*))
      (setq nm (cdr p))))
  (if nm nm "?"))

;; The member of LST nearest to P.
(defun lh:nearest (p lst / best bd q d)
  (setq best nil bd nil)
  (foreach q lst
    (setq d (cal:dist p q))
    (if (or (null bd) (< d bd)) (setq best q bd d)))
  best)

;; Index of point P in TOUR (exact-point fuzz), or nil.
(defun lh:tour-index (p tour / i k q)
  (setq i nil k 0)
  (foreach q tour
    (if (and (null i) (< (cal:dist p q) *LH-EXACT-EPS*)) (setq i k))
    (setq k (1+ k)))
  i)

;; Rotate the closed TOUR so it starts at point P.
(defun lh:rotate-to-point (tour p / i)
  (setq i (lh:tour-index p tour))
  (if (and i (> i 0))
    (append (cal:nthcdr i tour) (cal:sublist tour 0 i))
    tour))

;; Rotate the closed TOUR so it starts at its sharpest turn.
(defun lh:rotate-to-corner (tour / n i prev cur next turn best bi)
  (setq n (length tour) i 0 best -1.0 bi 0)
  (repeat n
    (setq prev (nth (rem (+ i n -1) n) tour)
          cur  (nth i tour)
          next (nth (rem (1+ i) n) tour)
          turn (abs (cal:signed-dang (angle prev cur) (angle cur next))))
    (if (> turn best) (setq best turn bi i))
    (setq i (1+ i)))
  (append (cal:nthcdr bi tour) (cal:sublist tour 0 bi)))

;; Number of curved segments in a span list.
(defun lh:arc-count (spans / c sp)
  (setq c 0)
  (foreach sp spans (if (>= (abs (caddr sp)) 1.0e-9) (setq c (1+ c))))
  c)

;; ---- near-tangent span fitting ---------------------------------------
;; Arcs sit ON the scanned points: every span runs from tour point to
;; tour point and its interior is fitted through the points with exact
;; 3-point arcs.  Tangency is a WINDOW: at each joint the new arc's
;; start tangent may differ from the previous arc's end tangent by at
;; most *LH-TANG-TOL*.  A bulge window is a cons (lo . hi); nil means
;; unconstrained.

;; Allowed bulge interval for the span A->B whose START tangent must
;; lie within *LH-TANG-TOL* (times WF) of the incoming tangent TE.
(defun lh:tang-window (te a b wf / tt phi alo ahi lo hi)
  (setq tt  (* *LH-TANG-TOL* wf)
        phi (cal:signed-dang te (angle a b))
        alo (max (min (/ (- phi tt) 2.0) 1.373) -1.373)
        ahi (max (min (/ (+ phi tt) 2.0) 1.373) -1.373)
        lo  (cal:tan alo)
        hi  (cal:tan ahi))
  (if (<= lo hi) (cons lo hi) (cons hi lo)))

;; Allowed bulge interval for the CLOSING span A->B whose END tangent
;; must lie within *LH-TANG-TOL* (times WF) of the loop's start
;; tangent TS0.  Closed mode only - an open run has no closing span.
(defun lh:end-window (ts0 a b wf / tt psi alo ahi lo hi)
  (setq tt  (* *LH-TANG-TOL* wf)
        psi (cal:signed-dang (angle a b) ts0)
        alo (max (min (/ (- psi tt) 2.0) 1.373) -1.373)
        ahi (max (min (/ (+ psi tt) 2.0) 1.373) -1.373)
        lo  (cal:tan alo)
        hi  (cal:tan ahi))
  (if (<= lo hi) (cons lo hi) (cons hi lo)))

;; Intersect two bulge windows; when they don't overlap, split the
;; difference so the leftover kink shares across the two joints.
(defun lh:merge-windows (win win2 / lo hi)
  (cond
    ((null win) win2)
    ((null win2) win)
    (T
     (setq lo (max (car win) (car win2))
           hi (min (cdr win) (cdr win2)))
     (if (<= lo hi)
       (cons lo hi)
       (progn
         (setq lo (if (< (cdr win) (car win2))
                    (/ (+ (cdr win) (car win2)) 2.0)
                    (/ (+ (cdr win2) (car win)) 2.0)))
         (cons lo lo))))))

;; Clamp bulge B into window WIN (nil = unconstrained).
(defun lh:clamp-b (b win)
  (cond ((null win) b)
        ((< b (car win)) (car win))
        ((> b (cdr win)) (cdr win))
        (T b)))

;; Closest any of QS comes to the segment (A B bulge).
(defun lh:span-min (a b bul qs / seg mn d q)
  (setq seg (list a b bul) mn nil)
  (foreach q qs
    (setq d (lh:seg-dist q seg))
    (if (or (null mn) (< d mn)) (setq mn d)))
  mn)

;; Best bulge for the span A->B over interior points QS, restricted to
;; the tangent window WIN (nil = free).  Exact 3-point arcs come
;; first; compromise bulges only when no exact arc works.  Returns
;; (bulge dev misses exactflag).
(defun lh:span-fit (a b qs win tol left / bls m sum bl cands best d mis)
  (setq bls  (mapcar '(lambda (q) (lh:bulge-3pt a q b)) qs)
        m    (length qs)
        best nil)
  (foreach bl bls
    (if (or (null win)
            (and (>= bl (car win)) (<= bl (cdr win))))
      (progn
        (setq d (lh:span-dev a b bl qs))
        (if (and (<= d tol)
                 (or (null best) (< d (cadr best))))
          (progn
            (setq mis (lh:span-misses a b bl qs))
            (if (<= mis left)
              (setq best (list bl d mis T))))))))
  (if (null best)
    (progn
      (setq sum 0.0)
      (foreach bl bls (setq sum (+ sum bl)))
      (setq cands (list (/ sum m) (nth (/ m 2) bls)))
      (if (>= m 4)
        (setq cands (append cands (list (nth (/ m 4) bls)
                                        (nth (/ (* 3 m) 4) bls)))))
      (if win
        (setq cands (append (mapcar '(lambda (bl) (lh:clamp-b bl win))
                                    cands)
                            (list (car win) (cdr win)
                                  (/ (+ (car win) (cdr win)) 2.0)))))
      (foreach bl cands
        (setq d (lh:span-dev a b bl qs))
        (if (or (null best) (< d (cadr best)))
          (setq best (list bl d (lh:span-misses a b bl qs) nil))))))
  best)

;; Cover the rotated CLOSED tour with arcs whose endpoints sit ON the
;; tour points.  ABHD's loop walker, unchanged: modular indices, the
;; seam held inside the tangent window, TE0 seeding the first span to
;; close the seam on a re-run.
(defun lh:span-loop (tour tol left te0 pro / n sharp i prev cur next
                                             turn strtshp segs pos te
                                             ts0 lim a best bstx len go
                                             bnd win qs fr bl mis sn
                                             dev0 anch steps wf lm
                                             walls w i1 i2 fwd nogrow f
                                             wrec)
  (setq n (length tour))
  ;; sharp corners: intentional kinks, window resets
  (setq sharp nil i 0)
  (repeat n
    (setq prev (nth (rem (+ i n -1) n) tour)
          cur  (nth i tour)
          next (nth (rem (1+ i) n) tour)
          turn (abs (cal:signed-dang (angle prev cur) (angle cur next))))
    (setq sharp (cons (or (> turn *LH-CORNER-ANG*)
                          (lh:memb cur lh-corners))
                      sharp)
          i     (1+ i)))
  (setq sharp (reverse sharp))
  ;; declared straight stretches onto tour indices, short way around
  (setq walls nil)
  (foreach w lh-walls
    (setq i1 (lh:tour-index (car w) tour)
          i2 (lh:tour-index (cadr w) tour))
    (if (and i1 i2 (/= i1 i2))
      (progn
        (setq fwd (rem (+ (- i2 i1) n) n))
        (if (> (* 2 fwd) n)
          (setq i1 i2 fwd (- n fwd)))
        (if (<= (+ i1 fwd) n)
          (setq walls (cons (list i1 (+ i1 fwd)) walls))))))
  ;; indices ordinary spans may not swallow - including every HELD
  ;; point: a span may end on one (landing exactly) but never bury it
  (setq nogrow nil i 0)
  (repeat n
    (setq f (nth i sharp))
    (foreach w walls
      (if (and (>= i (car w)) (<= i (cadr w))) (setq f T))
      (if (and (= (cadr w) n) (= i 0)) (setq f T)))
    (if (lh:memb (nth i tour) lh-holds) (setq f T))
    (setq nogrow (cons f nogrow)
          i      (1+ i)))
  (setq nogrow  (reverse nogrow)
        strtshp (car sharp)
        segs    nil
        pos     0
        te      (if strtshp nil te0)
        ts0     nil)
  (while (< pos n)
    (setq a    (nth pos tour)
          wrec (assoc pos walls))
    (if wrec
      ;; ---- a declared straight stretch starts here: emit verbatim --
      (progn
        (setq len  (- (cadr wrec) pos)
              bnd  (nth (rem (cadr wrec) n) tour)
              qs   (cal:sublist tour (1+ pos) (1- len))
              mis  (lh:span-misses a bnd 0.0 qs)
              segs (cons (list a bnd 0.0) segs)
              left (max 0 (- left mis)))
        (if (and (null ts0) (not strtshp))
          (setq ts0 (angle a bnd)))
        (setq pos (cadr wrec)
              te  (if (and (< pos n) (nth (rem pos n) sharp))
                    nil
                    (angle a bnd))))
      ;; ---- an ordinary span --------------------------------------
      (progn
    ;; the first span stops one point short so the result always has
    ;; at least two real segments
    (setq lim  (if (= pos 0) (1- (- n pos)) (- n pos))
          best nil                   ; longest feasible span of any kind
          bstx nil                   ; longest span through an interior point
          steps *LH-TANG-STEPS*)
    (while (and (null best) steps)
      (setq wf    (car steps)
            steps (cdr steps)
            len   2
            go    T)
      (while (and go (<= len lim))
        (if (nth (rem (+ pos len -1) n) nogrow)
          (setq go nil)         ; never bury a corner or a wall point
          (progn
            (setq bnd (nth (rem (+ pos len) n) tour)
                  win (if te (lh:tang-window te a bnd wf)))
            ;; the span that closes the loop must also end within the
            ;; tangent window of the loop's start
            (if (and (= (+ pos len) n) (not strtshp) ts0)
              (setq win (lh:merge-windows win
                                          (lh:end-window ts0 a bnd wf))))
            (setq qs (cal:sublist tour (1+ pos) (1- len))
                  lm (if pro
                       (min left (cal:ceil (* (lh:misspct) len)))
                       left)
                  fr (lh:span-fit a bnd qs win tol lm))
            (if (and (<= (cadr fr) tol) (<= (caddr fr) lm))
              (progn
                (setq best (list len (car fr) (caddr fr) win))
                (if (cadddr fr) (setq bstx best))
                (setq len (1+ len)))
              (setq go nil))))))
    ;; a floating arc must cover at least 2 more points than the
    ;; longest arc through an interior point to be chosen
    (if (and bstx best (< (car best) (+ (car bstx) 2)))
      (setq best bstx))
    (if (null best)
      ;; stub to the very next point: continue the incoming tangent
      (progn
        (setq bnd (nth (rem (1+ pos) n) tour))
        (if te
          (progn
            (setq bl (lh:tangent-bulge a te bnd))
            (if (and (= (1+ pos) n) (not strtshp) ts0)
              ;; closing stub: split the kink between both joints
              (setq bl (/ (+ bl (cal:tan (/ (cal:signed-dang (angle a bnd)
                                                           ts0)
                                           2.0)))
                          2.0)))
            (if (> bl 1.0) (setq bl 1.0))
            (if (< bl -1.0) (setq bl -1.0)))
          (setq bl 0.0))
        (setq best (list 1 bl 0 nil)))
      ;; nice-radius snap inside the same tangent window
      (progn
        (setq len  (car best)
              bl   (cadr best)
              win  (cadddr best)
              bnd  (nth (rem (+ pos len) n) tour)
              qs   (cal:sublist tour (1+ pos) (1- len))
              dev0 (lh:span-dev a bnd bl qs)
              anch (<= (lh:span-min a bnd bl qs) (* 2.0 *LH-FIT-EPS*))
              sn   (lh:snap-arc a bnd bl qs
                                (max dev0 *LH-SNAP-EPS*) left win))
        (if (and sn
                 (or (not anch)
                     (<= (lh:span-min a bnd (car sn) qs)
                         (* 2.0 *LH-FIT-EPS*))))
          (setq best (list len (car sn) (cdr sn) win)))))
    (setq len  (car best)
          bl   (cadr best)
          mis  (caddr best)
          bnd  (nth (rem (+ pos len) n) tour)
          segs (cons (list a bnd bl) segs)
          left (- left mis))
    (if (and (null ts0) (not strtshp))
      (setq ts0 (- (angle a bnd) (* 2.0 (atan bl)))))
    (setq pos (+ pos len)
          te  (if (nth (rem pos n) sharp)
                nil
                (+ (angle a bnd) (* 2.0 (atan bl))))))))
  (reverse segs))

;; Cover the OPEN tour with arcs, walking it once from end to end.
;; This is lh:span-loop rebuilt with LINEAR indices - not a stripped
;; copy, because the loop walker's modular arithmetic (rem ... n) is
;; exactly what an open run must not do: there is no seam, no closing
;; span, no start-tangent seeding, and the last span simply ends at
;; the final point.  The two path ends are free kinks by construction;
;; sharp corners are flagged on interior points only.  Everything else
;; - the window widening, exact-arc preference, floating-arc rule and
;; nice-radius snap - is the loop walker's, unchanged.
(defun lh:span-path (tour tol left pro / n sharp i prev cur next turn
                                         segs pos te lim a best bstx
                                         len go bnd win qs fr bl mis sn
                                         dev0 anch steps wf lm walls w
                                         i1 i2 nogrow f wrec)
  (setq n (length tour))
  ;; sharp corners: interior points only - the ends have no joint
  (setq sharp nil i 0)
  (repeat n
    (if (or (= i 0) (= i (1- n)))
      (setq sharp (cons nil sharp))
      (progn
        (setq prev (nth (1- i) tour)
              cur  (nth i tour)
              next (nth (1+ i) tour)
              turn (abs (cal:signed-dang (angle prev cur)
                                        (angle cur next))))
        (setq sharp (cons (or (> turn *LH-CORNER-ANG*)
                              (lh:memb cur lh-corners))
                          sharp))))
    (setq i (1+ i)))
  (setq sharp (reverse sharp))
  ;; declared straight stretches map straight onto linear indices -
  ;; no short-way-around: an open run has only one way between them
  (setq walls nil)
  (foreach w lh-walls
    (setq i1 (lh:tour-index (car w) tour)
          i2 (lh:tour-index (cadr w) tour))
    (if (and i1 i2 (/= i1 i2))
      (progn
        (if (> i1 i2) (setq f i1 i1 i2 i2 f))
        (setq walls (cons (list i1 i2) walls)))))
  ;; indices ordinary spans may not swallow - including every HELD
  ;; point: a span may end on one (landing exactly) but never bury it
  (setq nogrow nil i 0)
  (repeat n
    (setq f (nth i sharp))
    (foreach w walls
      (if (and (>= i (car w)) (<= i (cadr w))) (setq f T)))
    (if (lh:memb (nth i tour) lh-holds) (setq f T))
    (setq nogrow (cons f nogrow)
          i      (1+ i)))
  (setq nogrow (reverse nogrow)
        segs   nil
        pos    0
        te     nil)
  (while (< pos (1- n))
    (setq a    (nth pos tour)
          wrec (assoc pos walls))
    (if wrec
      ;; ---- a declared straight stretch starts here: emit verbatim --
      (progn
        (setq len  (- (cadr wrec) pos)
              bnd  (nth (cadr wrec) tour)
              qs   (cal:sublist tour (1+ pos) (1- len))
              mis  (lh:span-misses a bnd 0.0 qs)
              segs (cons (list a bnd 0.0) segs)
              left (max 0 (- left mis))
              pos  (cadr wrec)
              te   (if (and (< pos (1- n)) (nth pos sharp))
                     nil
                     (angle a bnd))))
      ;; ---- an ordinary span --------------------------------------
      (progn
    ;; a span may reach the last point and no further; one arc over
    ;; the whole open run is legitimate, so no stop-short rule here
    (setq lim  (- (1- n) pos)
          best nil                   ; longest feasible span of any kind
          bstx nil                   ; longest span through an interior point
          steps *LH-TANG-STEPS*)
    (while (and (null best) steps)
      (setq wf    (car steps)
            steps (cdr steps)
            len   2
            go    T)
      (while (and go (<= len lim))
        (if (nth (+ pos len -1) nogrow)
          (setq go nil)         ; never bury a corner or a wall point
          (progn
            (setq bnd (nth (+ pos len) tour)
                  win (if te (lh:tang-window te a bnd wf))
                  qs  (cal:sublist tour (1+ pos) (1- len))
                  lm  (if pro
                        (min left (cal:ceil (* (lh:misspct) len)))
                        left)
                  fr  (lh:span-fit a bnd qs win tol lm))
            (if (and (<= (cadr fr) tol) (<= (caddr fr) lm))
              (progn
                (setq best (list len (car fr) (caddr fr) win))
                (if (cadddr fr) (setq bstx best))
                (setq len (1+ len)))
              (setq go nil))))))
    ;; a floating arc must cover at least 2 more points than the
    ;; longest arc through an interior point to be chosen
    (if (and bstx best (< (car best) (+ (car bstx) 2)))
      (setq best bstx))
    (if (null best)
      ;; stub to the very next point: continue the incoming tangent
      (progn
        (setq bnd (nth (1+ pos) tour))
        (if te
          (progn
            (setq bl (lh:tangent-bulge a te bnd))
            (if (> bl 1.0) (setq bl 1.0))
            (if (< bl -1.0) (setq bl -1.0)))
          (setq bl 0.0))
        (setq best (list 1 bl 0 nil)))
      ;; nice-radius snap inside the same tangent window
      (progn
        (setq len  (car best)
              bl   (cadr best)
              win  (cadddr best)
              bnd  (nth (+ pos len) tour)
              qs   (cal:sublist tour (1+ pos) (1- len))
              dev0 (lh:span-dev a bnd bl qs)
              anch (<= (lh:span-min a bnd bl qs) (* 2.0 *LH-FIT-EPS*))
              sn   (lh:snap-arc a bnd bl qs
                                (max dev0 *LH-SNAP-EPS*) left win))
        (if (and sn
                 (or (not anch)
                     (<= (lh:span-min a bnd (car sn) qs)
                         (* 2.0 *LH-FIT-EPS*))))
          (setq best (list len (car sn) (cdr sn) win)))))
    (setq len  (car best)
          bl   (cadr best)
          mis  (caddr best)
          bnd  (nth (+ pos len) tour)
          segs (cons (list a bnd bl) segs)
          left (- left mis)
          pos  (+ pos len)
          te   (if (and (< pos (1- n)) (nth pos sharp))
                 nil
                 (+ (angle a bnd) (* 2.0 (atan bl))))))))
  (reverse segs))

;; Tangent mismatch at the loop's closing joint (radians).
(defun lh:seam-kink (segs / sl sf te ts)
  (setq sl (last segs)
        sf (car segs)
        te (+ (angle (car sl) (cadr sl)) (* 2.0 (atan (caddr sl))))
        ts (- (angle (car sf) (cadr sf)) (* 2.0 (atan (caddr sf)))))
  (abs (cal:signed-dang te ts)))

;; One full CLOSED fit; when the seam closes with more than
;; *LH-TANG-TOL* of kink, refit once seeding the first span's window
;; with the arrival tangent and keep whichever seam is straighter.
(defun lh:fit-pass (tour tol left pro / segs k1 sl te0 segs2 lh-on-eps)
  (setq lh-on-eps (max *LH-ON-EPS* (* 0.25 tol))
        segs      (lh:span-loop tour tol left nil pro)
        k1        (lh:seam-kink segs))
  (if (> k1 (+ *LH-TANG-TOL* 0.001))
    (progn
      (setq sl    (last segs)
            te0   (+ (angle (car sl) (cadr sl))
                     (* 2.0 (atan (caddr sl))))
            segs2 (lh:span-loop tour tol left te0 pro))
      (if (< (lh:seam-kink segs2) k1) (setq segs segs2))))
  segs)

;; One full OPEN fit.  A single walk is the whole job: there is no
;; seam to close, so the seam-kink re-run has nothing to do here.
(defun lh:fit-pass-open (tour tol left pro / lh-on-eps)
  (setq lh-on-eps (max *LH-ON-EPS* (* 0.25 tol)))
  (lh:span-path tour tol left pro))

;; Closed points-driven fit with the curve cap: refit the whole loop
;; with a progressively relaxed tolerance until the cap holds, keeping
;; the fewest-curves result seen.  (ABHD's, unchanged.)
(defun lh:coarse-loop (tour tol maxarcs left pro / segs segs2 tol2 tries)
  ;; start the walk at a declared stretch or corner when there is one;
  ;; otherwise at the sharpest turn
  (setq tour (cond
               (lh-walls   (lh:rotate-to-point tour (car (car lh-walls))))
               (lh-corners (lh:rotate-to-point tour (car lh-corners)))
               (T          (lh:rotate-to-corner tour)))
        segs (lh:fit-pass tour tol left pro))
  (if maxarcs
    (progn
      (setq tol2 tol tries 0)
      (while (and (> (lh:arc-count segs) maxarcs) (< tries 40))
        (setq tol2  (* tol2 1.4)
              tries (1+ tries)
              segs2 (lh:fit-pass tour tol2 1000000 nil))
        (if (< (lh:arc-count segs2) (lh:arc-count segs))
          (setq segs segs2)))))
  segs)

;; The open counterpart: same relaxing cap loop, but the tour is NOT
;; rotated - an open run's start and end are its endpoints, and
;; rotating them away would corrupt the path.
(defun lh:coarse-path (tour tol maxarcs left pro / segs segs2 tol2 tries)
  (setq segs (lh:fit-pass-open tour tol left pro))
  (if maxarcs
    (progn
      (setq tol2 tol tries 0)
      (while (and (> (lh:arc-count segs) maxarcs) (< tries 40))
        (setq tol2  (* tol2 1.4)
              tries (1+ tries)
              segs2 (lh:fit-pass-open tour tol2 1000000 nil))
        (if (< (lh:arc-count segs2) (lh:arc-count segs))
          (setq segs segs2)))))
  segs)

;; ---- self-intersection check -----------------------------------------

;; Cross product of (P-O) x (Q-O); its sign says which side Q is on.
(defun lh:cross3 (o p q)
  (- (* (- (car p) (car o)) (- (cadr q) (cadr o)))
     (* (- (cadr p) (cadr o)) (- (car q) (car o)))))

;; T when segments A-B and C-D properly cross.
(defun lh:segs-cross (a b c d / d1 d2 d3 d4)
  (setq d1 (lh:cross3 a b c) d2 (lh:cross3 a b d)
        d3 (lh:cross3 c d a) d4 (lh:cross3 c d b))
  (and (< (* d1 d2) 0.0) (< (* d3 d4) 0.0)))

;; Sample the fitted chain into a point list; arcs get intermediate
;; points so a bulging arc's real path is tested, not just its chord.
(defun lh:loop-pts (segs / out s g c r a1 a2 sweep k j aa)
  (setq out nil)
  (foreach s segs
    (setq out (cons (cal:2d (car s)) out))
    (if (>= (abs (caddr s)) 1.0e-9)
      (progn
        (setq g (lh:arc-geom (car s) (cadr s) (caddr s)))
        (if g
          (progn
            (setq c  (car g)   r  (cadr g)
                  a1 (caddr g) a2 (cadddr g))
            (if (> (caddr s) 0.0)
              (setq sweep (cal:angnorm (- a2 a1)))
              (setq sweep (- (cal:angnorm (- a1 a2)))))
            (setq k 4 j 1)
            (while (< j k)
              (setq aa  (+ a1 (* sweep (/ (float j) (float k))))
                    out (cons (list (+ (car c) (* r (cos aa)))
                                    (+ (cadr c) (* r (sin aa))))
                              out)
                    j   (1+ j))))))))
  (reverse out))

;; T when the fitted result crosses itself.  Closed results test the
;; ring of chords with the first/last pair exempt (they legitimately
;; share a vertex); open results test the open chain, whose real end
;; point is appended instead of the ring-closing repeat.
(defun lh:self-crosses (segs closed / p n found ti tj i j a b c d)
  (setq p (lh:loop-pts segs))
  (if closed
    (setq p (append p (list (car p))))
    (setq p (append p (list (cal:2d (cadr (last segs)))))))
  (if (< (length p) 4)
    nil
    (progn
      (setq n     (1- (length p))            ; number of chords
            found nil
            ti    p
            i     0)
      (while (and (not found) (< i (- n 2)))
        (setq a  (car ti)
              b  (cadr ti)
              tj (cddr ti)
              j  (+ i 2))
        (while (and (not found) (< j n))
          (setq c (car tj) d (cadr tj))
          (if (not (and closed (= i 0) (= j (1- n))))
            (if (lh:segs-cross a b c d) (setq found T)))
          (setq tj (cdr tj) j (1+ j)))
        (setq ti (cdr ti) i (1+ i)))
      found)))

;; ---- output helpers --------------------------------------------------

;; How many fitted polylines are already on the output layer.
(defun lh:prior-fits (/ ss)
  (setq ss (ssget "_X" (list (cons 8 *LH-OUT-LAYER*)
                             '(0 . "LWPOLYLINE"))))
  (if ss (sslength ss) 0))

;; T when R is a whole multiple of one of the *LH-NICE-RADII* tiers.
(defun lh:nice-radius-p (r / found tier q)
  (setq found nil)
  (if (and r (< r 1.0e6))
    (foreach tier *LH-NICE-RADII*
      (setq q (/ r tier))
      (if (< (abs (- q (fix (+ q 0.5)))) 1.0e-6) (setq found T))))
  found)

;; VERTS: list of (pt bulge) in order.  For a CLOSED polyline the last
;; vertex's bulge curves back to the first; an OPEN polyline needs the
;; final end point as one more vertex (bulge 0) or its last segment
;; silently vanishes - the callers append it.  ELEV is the single
;; height the whole polyline sits at (LWPOLYLINE group 38); COL is an
;; AutoCAD colour index, or nil for BYLAYER.
(defun lh:make-pline (verts layer col closed elev / dxf v)
  (setq dxf (list '(0 . "LWPOLYLINE") '(100 . "AcDbEntity")
                  (cons 8 layer)))
  (if col (setq dxf (append dxf (list (cons 62 col)))))
  (setq dxf (append dxf (list '(100 . "AcDbPolyline")
                              (cons 90 (length verts))
                              (cons 70 (if closed 1 0))
                              (cons 38 elev))))
  (foreach v verts
    (setq dxf (append dxf (list (cons 10 (car v)) (cons 42 (cadr v))))))
  (entmakex dxf))

;; The kept fit joins the POOL layer in ByLayer colour: the preview
;; colour and layer belonged to the comparison - the result belongs
;; with the rest of the drawing.
(defun lh:set-bylayer (en / ed)
  (cal:ensure-layer *LH-POOL-LAYER* 4)
  (setq ed (entget en)
        ed (subst (cons 8 *LH-POOL-LAYER*) (assoc 8 ed) ed))
  (if (assoc 62 ed) (setq ed (subst '(62 . 256) (assoc 62 ed) ed)))
  (entmod ed))

;; The points SEGS fails to hold within TOL.
(defun lh:unheld (segs pts tol / out q s d dmin)
  (setq out nil)
  (foreach q pts
    (setq dmin nil)
    (foreach s segs
      (setq d (lh:seg-dist q s))
      (if (or (null dmin) (< d dmin)) (setq dmin d)))
    (if (> dmin tol) (setq out (cons q out))))
  (reverse out))

;; List membership by position, within the exact-point fuzz.
(defun lh:memb (q lst / found p)
  (setq found nil)
  (foreach p lst
    (if (< (cal:dist p q) *LH-EXACT-EPS*) (setq found T)))
  found)

(defun lh:isect (a b / out q)
  (setq out nil)
  (foreach q a
    (if (lh:memb q b) (setq out (cons q out))))
  (reverse out))

;; ---- temporary preview geometry --------------------------------------
;; Every piece of scaffolding - dashed markers, candidate outlines,
;; labels - registers here as it is created and is swept away when the
;; command ends, however it ends.  Whatever the user keeps is dropped
;; from the list first.

(defun lh:temp-add (en)
  (if en (setq lh-temp (cons en lh-temp)))
  en)

(defun lh:temp-drop (en / out x)
  (setq out nil)
  (foreach x lh-temp
    (if (not (eq x en)) (setq out (cons x out))))
  (setq lh-temp (reverse out))
  en)

(defun lh:temp-clear ( / en)
  (foreach en lh-temp
    (if (and en (entget en)) (entdel en)))
  (setq lh-temp nil))

;; ---- "this one is mine" stamping -------------------------------------
;; LHD writes onto layers the drawing may already be using, so it must
;; never clear a layer wholesale: everything it creates carries xdata
;; naming this command, and only stamped objects are ever erased.

(defun lh:tag-mine (en / ed)
  (if en
    (progn
      (regapp "LHD")
      (setq ed (entget en))
      (entmod (append ed (list (list -3 (list "LHD" (cons 1000 "LHD"))))))))
  en)

;; Erase only LHD's own objects on a layer.  Returns how many went.
(defun lh:purge-mine (name / ss i n en)
  (setq n 0)
  (if (tblsearch "LAYER" name)
    (progn
      (setq ss (ssget "_X" (list (cons 8 name))))
      (if ss
        (progn
          (setq i 0)
          (repeat (sslength ss)
            (setq en (ssname ss i))
            (if (assoc -3 (entget en '("LHD")))
              (progn (entdel en) (setq n (1+ n))))
            (setq i (1+ i)))))))
  n)

;; Make sure the DASHED linetype exists (pure entmake).
(defun lh:ensure-dashed ()
  (if (not (tblsearch "LTYPE" "DASHED"))
    (entmake (list '(0 . "LTYPE") '(100 . "AcDbSymbolTableRecord")
                   '(100 . "AcDbLinetypeTableRecord")
                   '(2 . "DASHED") '(70 . 0)
                   '(3 . "Dashed __ __ __ __ __")
                   '(72 . 65) '(73 . 2) '(40 . 18.0)
                   '(49 . 12.0) '(74 . 0)
                   '(49 . -6.0) '(74 . 0)))))

;; Draw the dashed ring marking a declared sharp corner.
(defun lh:draw-corner-marker (p)
  (lh:ensure-dashed)
  (cal:ensure-layer *LH-WALL-LAYER* 8)
  (entmakex (list '(0 . "CIRCLE") '(100 . "AcDbEntity")
                  (cons 8 *LH-WALL-LAYER*) '(6 . "DASHED")
                  '(100 . "AcDbCircle")
                  (cons 10 (list (car p) (cadr p) 0.0))
                  (cons 40 *LH-MISS-RADIUS*))))

;; Draw the marker for a declared HELD point: a dashed ring at half
;; the miss-ring radius, so it reads apart from corner rings.
(defun lh:draw-hold-marker (p)
  (lh:ensure-dashed)
  (cal:ensure-layer *LH-WALL-LAYER* 8)
  (entmakex (list '(0 . "CIRCLE") '(100 . "AcDbEntity")
                  (cons 8 *LH-WALL-LAYER*) '(6 . "DASHED")
                  '(100 . "AcDbCircle")
                  (cons 10 (list (car p) (cadr p) 0.0))
                  (cons 40 (* 0.5 *LH-MISS-RADIUS*)))))

;; Draw the dashed marker for a declared straight stretch.
(defun lh:draw-wall-marker (p1 p2)
  (lh:ensure-dashed)
  (cal:ensure-layer *LH-WALL-LAYER* 8)
  (entmakex (list '(0 . "LINE") '(100 . "AcDbEntity")
                  (cons 8 *LH-WALL-LAYER*) '(6 . "DASHED")
                  '(100 . "AcDbLine")
                  (cons 10 (list (car p1) (cadr p1) 0.0))
                  (cons 11 (list (car p2) (cadr p2) 0.0)))))

;; Bounding box of a point list, as (minx miny maxx maxy).
(defun lh:bbox (pts / x0 y0 x1 y1 q)
  (foreach q pts
    (if (null x0)
      (setq x0 (car q) x1 (car q) y0 (cadr q) y1 (cadr q))
      (setq x0 (min x0 (car q)) x1 (max x1 (car q))
            y0 (min y0 (cadr q)) y1 (max y1 (cadr q)))))
  (list x0 y0 x1 y1))

;; Draw "1", "2", "3" beside each candidate, in that candidate's own
;; colour, with that fit's numbers spelled out beside it.
(defun lh:label (num colour bb hgt row top bot / x y out e pr)
  (setq x   (+ (caddr bb) (* 0.6 hgt))
        y   (- (cadddr bb) (* row hgt 2.1))
        out nil)
  (setq e (entmakex (list '(0 . "TEXT") '(100 . "AcDbEntity")
                          (cons 8 *LH-OUT-LAYER*) (cons 62 colour)
                          '(100 . "AcDbText")
                          (cons 10 (list x y 0.0))
                          (cons 40 hgt)
                          (cons 1 num))))
  (if e (setq out (cons e out)))
  (foreach pr (list (cons top (* 0.55 hgt)) (cons bot (* -0.05 hgt)))
    (setq e (entmakex (list '(0 . "TEXT") '(100 . "AcDbEntity")
                            (cons 8 *LH-OUT-LAYER*) (cons 62 colour)
                            '(100 . "AcDbText")
                            (cons 10 (list (+ x (* 1.4 hgt))
                                           (+ y (cdr pr))
                                           0.0))
                            (cons 40 (* 0.42 hgt))
                            (cons 1 (car pr)))))
    (if e (setq out (cons e out))))
  (reverse out))

;; Ring every point the chosen fit could not hold and list them beside
;; the shape, worst first.
(defun lh:mark-unheld (bad segs bb hgt / q d s dmin keyed pair th x y
                                         line)
  (lh:purge-mine *LH-MISS-LAYER*)
  (if bad
    (progn
      (cal:ensure-layer *LH-MISS-LAYER* 1)
      (foreach q bad
        (lh:tag-mine
          (entmakex (list '(0 . "CIRCLE") '(100 . "AcDbEntity")
                          (cons 8 *LH-MISS-LAYER*) '(100 . "AcDbCircle")
                          (cons 10 (list (car q) (cadr q) 0.0))
                          (cons 40 *LH-MISS-RADIUS*)))))
      (setq keyed nil)
      (foreach q bad
        (setq dmin nil)
        (foreach s segs
          (setq d (lh:seg-dist q s))
          (if (or (null dmin) (< d dmin)) (setq dmin d)))
        (setq keyed (cons (cons dmin q) keyed)))
      (setq keyed (reverse (lh:sort-car keyed))
            th    (* 0.5 hgt)
            x     (+ (caddr bb) (* 0.6 hgt))
            y     (cadddr bb))
      (lh:tag-mine
        (entmakex (list '(0 . "TEXT") '(100 . "AcDbEntity")
                        (cons 8 *LH-MISS-LAYER*) '(100 . "AcDbText")
                        (cons 10 (list x y 0.0))
                        (cons 40 th)
                        (cons 1 (strcat "POINTS OFF THE LINE ("
                                        (itoa (length bad)) ")")))))
      (foreach pair keyed
        (setq y    (- y (* th 1.6))
              line (strcat "Pt." (lh:pt-name (cdr pair))
                           "   off by " (rtos (car pair) 4 4)))
        (lh:tag-mine
          (entmakex (list '(0 . "TEXT") '(100 . "AcDbEntity")
                          (cons 8 *LH-MISS-LAYER*) '(100 . "AcDbText")
                          (cons 10 (list x y 0.0))
                          (cons 40 th)
                          (cons 1 line)))))))
  keyed)

;; Print the hit report for the fit the user kept.  ALLOW is the run's
;; miss allowance; CLOSED says which joint the chain has none of.
(defun lh:report (newsegs pts tol allow prior closed
                  / nl na hiton hitok miss q s s2 d dmin worst sum
                    sumo no nice onpt inner ns nj i te ts kk mk nk
                    hw hq lh-on-eps)
  ;; report against the same on-the-shape threshold the fit used
  (setq lh-on-eps (max *LH-ON-EPS* (* 0.25 tol)))
  (progn
      ;; -- segment mix, nice radii, arcs anchored on a point --------
      (setq nl 0 na 0 nice 0 onpt 0)
      (foreach s newsegs
        (if (< (abs (caddr s)) 1.0e-9)
          (setq nl (1+ nl))
          (progn
            (setq na (1+ na))
            (if (lh:nice-radius-p
                  (lh:bulge-radius (car s) (cadr s) (caddr s)))
              (setq nice (1+ nice)))
            (setq inner nil)
            (foreach q pts
              (if (and (> (cal:dist q (car s)) *LH-EXACT-EPS*)
                       (> (cal:dist q (cadr s)) *LH-EXACT-EPS*)
                       (<= (lh:seg-dist q s) (* 2.0 *LH-FIT-EPS*)))
                (setq inner T)))
            (if inner (setq onpt (1+ onpt))))))
      ;; -- how the scanned points landed ------------------------------
      (setq hiton 0 hitok 0 miss 0 worst 0.0 sum 0.0 sumo 0.0 no 0)
      (foreach q pts
        (setq dmin nil)
        (foreach s newsegs
          (setq d (lh:seg-dist q s))
          (if (or (null dmin) (< d dmin)) (setq dmin d)))
        (if (> dmin worst) (setq worst dmin))
        (setq sum (+ sum dmin))
        (if (> dmin (lh:oneps))
          (setq sumo (+ sumo dmin) no (1+ no)))
        (cond
          ((<= dmin (lh:oneps)) (setq hiton (1+ hiton)))
          ((<= dmin tol)        (setq hitok (1+ hitok)))
          (T                    (setq miss  (1+ miss)))))
      ;; -- smoothness: worst kink at a joint that is not a corner ----
      ;; an open chain has one joint fewer - its seam does not exist
      (setq ns (length newsegs)
            nj (if closed ns (1- ns))
            i 0 mk 0.0 nk 0)
      (while (< i nj)
        (setq s  (nth i newsegs)
              s2 (nth (rem (1+ i) ns) newsegs)
              te (+ (angle (car s) (cadr s)) (* 2.0 (atan (caddr s))))
              ts (- (angle (car s2) (cadr s2)) (* 2.0 (atan (caddr s2))))
              kk (abs (cal:signed-dang te ts)))
        (if (<= kk *LH-CORNER-ANG*)     ; bigger = an intentional corner
          (progn
            (if (> kk mk) (setq mk kk))
            (if (> kk (+ *LH-TANG-TOL* 1.0e-6)) (setq nk (1+ nk)))))
        (setq i (1+ i)))
      (princ (strcat "\nLHD: " (itoa ns) " segments ("
                     (itoa nl) " lines + " (itoa na)
                     " curves) written to layer " *LH-POOL-LAYER* "."
                     "\n  Points on the outline:        " (itoa hiton)
                     "\n  Points off within tolerance:  " (itoa hitok)
                     "  (allowance " (itoa allow) ")"
                     "\n  Points beyond tolerance:      " (itoa miss)
                     "\n  Worst point deviation:        " (rtos worst 2 3)
                     "\n  Average off, all points:      "
                     (rtos (if (> (length pts) 0)
                             (/ sum (length pts))
                             0.0)
                           2 3)
                     "\n  Average off, off points only: "
                     (if (> no 0)
                       (strcat (rtos (/ sumo no) 2 3)
                               "  (" (itoa no) " point(s))")
                       "-  (every point is on the line)")
                     "\n  Curves through a point:       " (itoa onpt)
                     " of " (itoa na)
                     "\n  Curves on foot/half/inch radii:" (itoa nice)
                     " of " (itoa na)
                     "\n  Largest joint kink:           "
                     (rtos (* 180.0 (/ mk pi)) 2 1) " deg  (limit "
                     (rtos (* 180.0 (/ *LH-TANG-TOL* pi)) 2 1) ")"))
      (if (> nk 0)
        (princ (strcat "\n  (" (itoa nk)
                       " joint(s) needed more than the tangent limit)")))
      (if lh-walls
        (princ (strcat "\n  (" (itoa (length lh-walls))
                       " declared straight stretch(es) kept dead"
                       " straight)")))
      (if lh-holds
        (progn
          ;; every held point must sit ON the kept fit exactly; one
          ;; that does not means a declared stretch overruled it, and
          ;; that deserves a loud line of its own
          (setq hw 0.0)
          (foreach q lh-holds
            (setq dmin nil)
            (foreach s newsegs
              (setq d (lh:seg-dist q s))
              (if (or (null dmin) (< d dmin)) (setq dmin d)))
            (if (> dmin hw) (setq hw dmin hq q)))
          (if (<= hw *LH-EXACT-EPS*)
            (princ (strcat "\n  (" (itoa (length lh-holds))
                           " held point(s) all landed on the line"
                           " exactly)"))
            (princ (strcat "\n  WARNING: held Pt." (lh:pt-name hq)
                           " is off by " (rtos hw 2 4)
                           " - a declared stretch overruled it.")))))
      (if (and *LH-MAX-ARCS* (> na *LH-MAX-ARCS*))
        (princ (strcat "\n  (the curve cap is " (itoa *LH-MAX-ARCS*)
                       " but " (itoa na) " curves was the fewest"
                       " reachable)")))
      (if (> miss 0)
        (princ "\n  (points beyond tolerance: the curve cap overruled them)"))
      (if (lh:self-crosses newsegs closed)
        (princ (strcat "\n  WARNING: the result crosses itself - the"
                       " automatic point order is probably wrong."
                       "  Draw a rough lines-only sketch on layer "
                       *LH-POOL-LAYER*
                       " through the points in the right order and"
                       " select it too.")))
      (if (> prior 0)
        (princ (strcat "\n  (" (itoa prior)
                       " earlier fit(s) were already on layer "
                       *LH-OUT-LAYER* " - erase them if you only want"
                       " the new one)"))))
  (princ))

;; Build one candidate fit in MODE - "tight", "asked" or "few".  TOL
;; is always the distance the user typed; the mode sets what differs:
;; the fit tolerance, the miss allowance, and whether the curve cap
;; binds (only "asked" honours it).  CLOSED picks the engine.
(defun lh:build (tour tol allow mode closed / ftol left cap)
  (setq ftol (if (= mode "tight") (min tol *LH-TIGHT-TOL*) tol)
        left (cond ((= mode "tight") 0)
                   ((= mode "few")   1000000)
                   (T                allow))
        cap  (if (= mode "asked") *LH-MAX-ARCS*))
  (if closed
    (lh:coarse-loop tour ftol cap left (not (= mode "few")))
    (lh:coarse-path tour ftol cap left (not (= mode "few")))))

;; Deviation summary for SEGS against PTS: (worst avg avg-off).
(defun lh:devstats (segs pts on / w q s d dmin sum n sumo no)
  (setq w 0.0 sum 0.0 n 0 sumo 0.0 no 0)
  (foreach q pts
    (setq dmin nil)
    (foreach s segs
      (setq d (lh:seg-dist q s))
      (if (or (null dmin) (< d dmin)) (setq dmin d)))
    (if (> dmin w) (setq w dmin))
    (setq sum (+ sum dmin) n (1+ n))
    (if (> dmin on) (setq sumo (+ sumo dmin) no (1+ no))))
  (list w
        (if (> n 0) (/ sum n) 0.0)
        (if (> no 0) (/ sumo no) nil)))

;; A deviation for a table cell; "-" when there is nothing to average.
(defun lh:fmt-dev (x)
  (if x (rtos x 2 2) "-"))

;; ---- offer three fits and let the user pick ---------------------------
;; The two ends of the curve-versus-accuracy trade and the middle, all
;; drawn, each in its own colour with what it costs; the one the user
;; points at is kept.  ELEV is the height every candidate is drawn at.
(defun lh:compare (tour pts tol allow closed elev
                   / prior vars v e ent lab st onv segs verts bad allbad
                     first i pick idx keep ce bb hgt sel picked keyed pr
                     res)
  (setq prior (lh:prior-fits))
  (cal:ensure-layer *LH-OUT-LAYER* 3)
  (setq onv (max *LH-ON-EPS* (* 0.25 tol)))
  (setq bb  (lh:bbox pts)
        hgt (/ (max (- (caddr bb) (car bb))
                    (- (cadddr bb) (cadr bb)))
               20.0))
  (if (<= hgt 0.0) (setq hgt 1.0))
  (setq lh-phase "building the three candidate fits"
        vars     nil
        allbad   nil
        first    T
        i        1)
  (foreach v *LH-COMPARE*
    (setq segs  (lh:build tour tol allow (car v) closed)
          verts (mapcar '(lambda (s) (list (car s) (caddr s))) segs))
    ;; an open polyline's last segment needs its end point as one more
    ;; vertex; a closed one curves back to vertex 0 by itself
    (if (not closed)
      (setq verts (append verts (list (list (cadr (last segs)) 0.0)))))
    (setq ent  (lh:temp-add
                 (lh:make-pline verts *LH-OUT-LAYER* (cadr v)
                                closed elev))
          bad  (lh:unheld segs pts tol)
          st   (lh:devstats segs pts onv)
          lab  (lh:label
                 (itoa i) (cadr v) bb hgt i
                 (strcat (itoa (length segs)) " segs    "
                         (itoa (lh:arc-count segs)) " curves    "
                         (itoa (length bad)) " not held    "
                         (cadddr v))
                 (strcat "worst " (lh:fmt-dev (car st))
                         "    avg all " (lh:fmt-dev (cadr st))
                         "    avg off " (lh:fmt-dev (caddr st))))
          vars (cons (list segs ent bad v lab st) vars)
          i    (1+ i))
    (foreach e lab (lh:temp-add e))
    ;; only fits built to the user's distance vote on the "no fit
    ;; could hold these" note - the tight one threads everything
    (if (not (= (car v) "tight"))
      (if first
        (setq allbad bad first nil)
        (setq allbad (lh:isect allbad bad)))))
  (setq vars (reverse vars))
  (if (null (cadr (car vars)))
    (princ "\nLHD: could not draw the result - is the drawing read-only?")
    (progn
      (princ (strcat "\n\nThree candidate fits are now drawn on layer "
                     *LH-OUT-LAYER*
                     ",\neach numbered on screen in its own colour:\n"))
      (princ "\n   #  segs  curves  worst off  avg all  avg off  not held  ")
      (princ "\n   -  ----  ------  ---------  -------  -------  --------  ")
      (setq i 1)
      (foreach v vars
        (setq segs (car v) bad (caddr v) ce (cadddr v) st (nth 5 v))
        (princ (strcat "\n   " (itoa i) "  "
                       (cal:pad (itoa (length segs)) 6)
                       (cal:pad (itoa (lh:arc-count segs)) 8)
                       (cal:pad (lh:fmt-dev (car st)) 11)
                       (cal:pad (lh:fmt-dev (cadr st)) 9)
                       (cal:pad (lh:fmt-dev (caddr st)) 9)
                       (cal:pad (itoa (length bad)) 10)
                       (cadddr ce)))
        (setq i (1+ i)))
      (princ (strcat "\n\n  \"not held\" = points further than "
                     (rtos tol 2 3) " from that fit."
                     "\n  \"avg all\" averages every point; \"avg off\""
                     " averages only the points that are off the line"
                     "\n  (further than " (rtos onv 2 3) " from it)."))
      (princ (strcat "\n  All three are measured against the "
                     (rtos tol 2 3) " you typed, but only one is built"
                     " to it:"
                     "\n  the tight fit spends curves to drive the error"
                     " towards nothing (it"
                     "\n  ignores that distance"
                     (if *LH-MAX-ARCS* " and the curve cap" "")
                     "), the middle one is your settings exactly,"
                     "\n  and the few fit holds the same distance with"
                     " as few curves as it can."))
      (if allbad
        (princ (strcat "\n  NOTE: " (itoa (length allbad))
                       " point(s) could not be held by ANY fit built to"
                       " that distance - likely a mis-shot, a duplicate,"
                       " or a corner that needs more points around it."
                       "\n  (the tight fit threads every point it can"
                       " reach, so it does not get a vote here.)")))
      (setq lh-phase "waiting for the choice of fit")
      (princ "\n\n  Click the outline you want to keep, or type its number.")
      (princ "\n  Redo refits with new settings, and lets you omit points first.")
      (initget "1 2 3 All None Redo")
      (setq pick (getkword
                   "\n  Keep which fit - click one, or [1/2/3/All/None/Redo] <2>: "))
      (if (null pick)
        (progn
          (setq sel (entsel "\n  Pick the outline to keep (or Enter for 2): "))
          (if sel
            (progn
              (setq picked (car sel) i 1)
              (foreach v vars
                (if (or (eq picked (cadr v))
                        (member picked (nth 4 v)))
                  (setq pick (itoa i)))
                (setq i (1+ i)))
              (if (null pick)
                (progn
                  (princ "\n  (that is not one of the three - keeping 2)")
                  (setq pick "2"))))
            (setq pick "2"))))
      (cond
        ((= pick "Redo")
         (foreach v vars
           (if (and (cadr v) (entget (cadr v))) (entdel (cadr v)))
           (foreach e (nth 4 v)
             (if (and e (entget e)) (entdel e))))
         (setq res 'REDO))
        ((= pick "All")
         (foreach v vars
           (lh:temp-drop (cadr v))
           (foreach e (nth 4 v) (lh:temp-drop e)))
         (princ "\nKeeping all three, in their preview colours.")
         (princ "\n  (the number labels are kept too - erase them when done)"))
        ((= pick "None")
         (princ "\nAll three erased - nothing was added to the drawing."))
        (T
         (setq idx (atoi pick) i 1)
         (foreach v vars
           (if (= i idx)
             (setq keep v)
             (if (and (cadr v) (entget (cadr v))) (entdel (cadr v))))
           (setq i (1+ i)))
         (if keep
           (princ (strcat "\n  Keeping fit " pick " - "
                          (cadddr (cadddr keep)) ".")))
         (if (cadr keep)
           (progn
             (lh:temp-drop (cadr keep))
             (lh:set-bylayer (cadr keep))))))
      (if keep
        (progn
          (setq keyed (lh:mark-unheld (caddr keep) (car keep) bb hgt))
          (lh:report (car keep) pts tol allow prior closed)
          (if keyed
            (progn
              (princ (strcat "\n  " (itoa (length keyed))
                             " point(s) beyond the distance are ringed"
                             " on layer " *LH-MISS-LAYER*
                             " and listed beside the shape, worst"
                             " first:"))
              (foreach pr keyed
                (princ (strcat "\n    Pt." (lh:pt-name (cdr pr))
                               "   off by " (rtos (car pr) 4 4))))))))))
  (princ)
  res)

;; ---- the numeric parameters ------------------------------------------

;; Maximum distance from a point; remembered in *LH-TOL*.
(defun lh:ask-tol (/ tol)
  (initget 6)
  (setq tol (getdist (strcat "\n  Maximum distance from a point <"
                             (rtos *LH-TOL* 2 3) ">: ")))
  (if (null tol) (setq tol *LH-TOL*))
  (if (> tol *LH-TOL-MAX*)
    (progn
      (princ (strcat "\n  (more than " (rtos *LH-TOL-MAX* 2 1)
                     " and the line is no longer a trace of the points"
                     " - using " (rtos *LH-TOL-MAX* 2 1) ")"))
      (setq tol *LH-TOL-MAX*)))
  (setq *LH-TOL* tol)
  tol)

;; Share of the points allowed off the line, as a fraction.
(defun lh:ask-pct (def / pct)
  (initget 4)
  (setq pct (getint (strcat "\n  Percent of points allowed off <"
                            (itoa (fix (+ 0.5 (* 100.0 def))))
                            ">: ")))
  (cond
    ((null pct) def)
    ((> pct 100)
     (princ "\n  (more than 100 makes no sense - using 100)")
     1.0)
    (T (/ pct 100.0))))

;; Curve cap; remembered in *LH-MAX-ARCS* (nil = no cap).
(defun lh:ask-cap (/ mx)
  (initget 4 "None")
  (setq mx (getint (strcat "\n  Maximum curves <"
                           (if *LH-MAX-ARCS* (itoa *LH-MAX-ARCS*) "None")
                           ">: ")))
  (cond ((null mx) nil)                            ; Enter: keep as-is
        ((eq 'STR (type mx)) (setq *LH-MAX-ARCS* nil))
        (T (setq *LH-MAX-ARCS* mx)))
  *LH-MAX-ARCS*)

;; Closed outline or open polyline; remembered in *LH-SHAPE*.
;; Returns T for closed.
(defun lh:ask-shape (/ ans)
  (initget "Closed Open")
  (setq ans (getkword (strcat
              "\n  Closed outline or Open polyline? [Closed/Open] <"
              *LH-SHAPE* ">: ")))
  (if ans (setq *LH-SHAPE* ans))
  (= *LH-SHAPE* "Closed"))

;; Which elevation the outline is drawn at; remembered in *LH-ZMODE*.
(defun lh:ask-zmode (/ ans)
  (initget "Top Bottom Average Zero")
  (setq ans (getkword (strcat
              "\n  Draw the outline at which height - [Top/Bottom/Average/Zero] <"
              *LH-ZMODE* ">: ")))
  (if ans (setq *LH-ZMODE* ans))
  *LH-ZMODE*)

;; The output height ZMODE picks from the elevation list ZS.
(defun lh:pick-elev (zmode zs / e z sum)
  (if (null zs)
    0.0
    (progn
      (setq e (car zs) sum 0.0)
      (foreach z zs
        (setq sum (+ sum z))
        (cond ((and (= zmode "Top")    (> z e)) (setq e z))
              ((and (= zmode "Bottom") (< z e)) (setq e z))))
      (cond ((= zmode "Average") (/ sum (length zs)))
            ((= zmode "Zero")    0.0)
            (T                   e)))))

;; The elevations carried by the points still in DPTS.
(defun lh:zs-of (dpts / out pr)
  (setq out nil)
  (foreach pr lh-zvals
    (if (lh:memb (car pr) dpts) (setq out (cons (cdr pr) out))))
  (reverse out))

;; ---- redo-time editing of walls and corners --------------------------

;; Erase this run's scaffolding markers of one entity type on the
;; marker layer, so the set can be redrawn to match an edited list.
(defun lh:sweep-marks (etype / keep en ed)
  (setq keep nil)
  (foreach en lh-temp
    (setq ed (if (and en (entget en)) (entget en)))
    (if (and ed
             (= etype (cdr (assoc 0 ed)))
             (= (strcase *LH-WALL-LAYER*)
                (strcase (cdr (assoc 8 ed)))))
      (entdel en)
      (setq keep (cons en keep))))
  (setq lh-temp (reverse keep)))

;; Snap a picked point onto the nearest scanned point.
(defun lh:snap-break (p dpts / q)
  (setq p (cal:2d p)
        q (lh:nearest p dpts))
  (if (null q)
    p
    (progn
      (if (> (cal:dist p q) (* 3.0 *LH-TOL*))
        (princ "\n  (picked well away from any scanned point - snapped to the nearest one)"))
      q)))

;; Add or remove declared straight stretches.
(defun lh:edit-walls (dpts / ans wp1 wp2 w1 w2 best bd w d)
  (setq ans T)
  (while ans
    (initget "Add Remove Keep")
    (setq ans (getkword (strcat
                "\n  Straight stretches (" (itoa (length lh-walls))
                " declared) - [Add/Remove/Keep] <Keep>: ")))
    (cond
      ((= ans "Add")
       (setq lh-phase "picking a straight stretch"
             wp1      (getpoint "\n  First end of the straight stretch: ")
             wp2      (if wp1 (getpoint wp1 "\n  Second end: ")))
       (if wp2
         (progn
           (setq w1 (lh:snap-break wp1 dpts)
                 w2 (lh:snap-break wp2 dpts))
           (if (< (cal:dist w1 w2) *LH-EXACT-EPS*)
             (princ "\n  (both ends landed on the same scanned point - ignored)")
             (progn
               (setq lh-walls (append lh-walls (list (list w1 w2))))
               (lh:temp-add (lh:tag-mine (lh:draw-wall-marker w1 w2)))
               (princ (strcat "\n  stretch Pt." (lh:pt-name w1)
                              " - Pt." (lh:pt-name w2) " added")))))))
      ((= ans "Remove")
       (if (null lh-walls)
         (princ "\n  (no straight stretches to remove)")
         (progn
           (setq lh-phase "removing a straight stretch"
                 wp1      (getpoint "\n  Pick near the straight stretch to remove: "))
           (if wp1
             (progn
               (setq wp1 (cal:2d wp1) best nil bd nil)
               (foreach w lh-walls
                 (setq d (lh:seg-dist wp1 (list (car w) (cadr w) 0.0)))
                 (if (or (null bd) (< d bd)) (setq best w bd d)))
               (setq lh-walls (lh:remove best lh-walls))
               (lh:sweep-marks "LINE")
               (foreach w lh-walls
                 (lh:temp-add (lh:tag-mine
                   (lh:draw-wall-marker (car w) (cadr w)))))
               (princ (strcat "\n  stretch Pt." (lh:pt-name (car best))
                              " - Pt." (lh:pt-name (cadr best))
                              " removed")))))))
      (T (setq ans nil)))))

;; Add or remove declared sharp corners the same way.
(defun lh:edit-corners (dpts / ans wp1 w1 best bd w)
  (setq ans T)
  (while ans
    (initget "Add Remove Keep")
    (setq ans (getkword (strcat
                "\n  Sharp corners (" (itoa (length lh-corners))
                " declared) - [Add/Remove/Keep] <Keep>: ")))
    (cond
      ((= ans "Add")
       (setq lh-phase "picking a sharp corner"
             wp1      (getpoint "\n  Corner point: "))
       (if wp1
         (progn
           (setq w1 (lh:snap-break wp1 dpts))
           (if (lh:memb w1 lh-corners)
             (princ "\n  (that corner is already declared)")
             (progn
               (setq lh-corners (append lh-corners (list w1)))
               (lh:temp-add (lh:tag-mine (lh:draw-corner-marker w1)))
               (princ (strcat "\n  corner Pt." (lh:pt-name w1)
                              " added")))))))
      ((= ans "Remove")
       (if (null lh-corners)
         (princ "\n  (no declared corners to remove)")
         (progn
           (setq lh-phase "removing a sharp corner"
                 wp1      (getpoint "\n  Pick the declared corner to remove: "))
           (if wp1
             (progn
               (setq wp1 (cal:2d wp1) best nil bd nil)
               (foreach w lh-corners
                 (if (or (null bd) (< (cal:dist wp1 w) bd))
                   (setq best w bd (cal:dist wp1 w))))
               (setq lh-corners (lh:remove best lh-corners))
               (lh:sweep-marks "CIRCLE")
               (foreach w lh-corners
                 (lh:temp-add (lh:tag-mine (lh:draw-corner-marker w))))
               (foreach w lh-holds
                 (lh:temp-add (lh:tag-mine (lh:draw-hold-marker w))))
               (princ (strcat "\n  corner Pt." (lh:pt-name best)
                              " removed")))))))
      (T (setq ans nil)))))

;; Add or remove HELD points the same way.
(defun lh:edit-holds (dpts / ans wp1 w1 best bd w)
  (setq ans T)
  (while ans
    (initget "Add Remove Keep")
    (setq ans (getkword (strcat
                "\n  Held points (" (itoa (length lh-holds))
                " declared) - [Add/Remove/Keep] <Keep>: ")))
    (cond
      ((= ans "Add")
       (setq lh-phase "picking a held point"
             wp1      (getpoint "\n  Point to hold exactly: "))
       (if wp1
         (progn
           (setq w1 (lh:snap-break wp1 dpts))
           (if (lh:memb w1 lh-holds)
             (princ "\n  (that point is already held)")
             (progn
               (setq lh-holds (append lh-holds (list w1)))
               (lh:temp-add (lh:tag-mine (lh:draw-hold-marker w1)))
               (princ (strcat "\n  held Pt." (lh:pt-name w1)
                              " added")))))))
      ((= ans "Remove")
       (if (null lh-holds)
         (princ "\n  (no held points to remove)")
         (progn
           (setq lh-phase "removing a held point"
                 wp1      (getpoint "\n  Pick the held point to release: "))
           (if wp1
             (progn
               (setq wp1 (cal:2d wp1) best nil bd nil)
               (foreach w lh-holds
                 (if (or (null bd) (< (cal:dist wp1 w) bd))
                   (setq best w bd (cal:dist wp1 w))))
               (setq lh-holds (lh:remove best lh-holds))
               ;; redraw the rings to match what is left
               (lh:sweep-marks "CIRCLE")
               (foreach w lh-corners
                 (lh:temp-add (lh:tag-mine (lh:draw-corner-marker w))))
               (foreach w lh-holds
                 (lh:temp-add (lh:tag-mine (lh:draw-hold-marker w))))
               (princ (strcat "\n  held Pt." (lh:pt-name best)
                              " released")))))))
      (T (setq ans nil)))))

;; ---- the command -----------------------------------------------------
(defun c:LHD ( / tol ans go wp1 wp2 rawwalls rawcnrs rawholds w w1 w2
                   ss i en ed lay typ ext nunsup nocs closed
                   segs pts dpts allow tour ok stale npt chn sketch
                   texts tx q v zs elev e1 e2
                   again omits pts2 ent ring lh-omitted
                   lh-miss-pct lh-walls lh-corners lh-holds
                   lh-temp lh-ptnames
                   lh-zvals *error* lh-old-err lh-phase)
  ;; report which step failed if anything goes wrong, sweep away any
  ;; preview geometry drawn so far, then restore the old handler
  (setq lh-temp   nil
        lh-old-err *error*
        *error*
          (lambda (m)
            (if (and m (not (wcmatch (strcase m)
                     "*BREAK*,*CANCEL*,*QUIT*,*EXIT*")))
              (princ (strcat "\nLHD stopped while "
                             (if lh-phase lh-phase "starting up")
                             " -- " m)))
            (lh:temp-clear)
            (setq *error* lh-old-err)
            (princ)))

  ;; sweep leftovers from a run that was interrupted before it could
  ;; tidy up after itself
  (setq stale (lh:purge-mine *LH-WALL-LAYER*))
  (if (> stale 0)
    (princ (strcat "\nLHD: cleared " (itoa stale)
                   " leftover marker(s) from layer " *LH-WALL-LAYER*
                   ".")))

  (princ "\n\nLHD - fit a top-down outline through laser-scanned points.")

  ;; -- step 1: how close must the line stay to the points? ----------
  (setq lh-phase "reading the tolerance")
  (princ "\n\n  Step 1 of 6 - how far may the fitted line sit from a scanned point?")
  (princ "\n  Type a distance in drawing units (1 = one inch, 2 at most), or")
  (princ "\n  pick two points in the drawing to measure one.")
  (princ "\n  Smaller = hugs the points.  Bigger = smoother, with fewer curves.")
  (setq tol (lh:ask-tol))

  ;; -- step 2: how many of the points may sit off the line? ---------
  (setq lh-phase "reading the miss percentage")
  (princ "\n\n  Step 2 of 6 - what percent of the points may sit OFF the line")
  (princ "\n  (off, but still within the distance above)?")
  (princ (strcat "\n  Press Enter for the standard "
                 (itoa (fix (+ 0.5 (* 100.0 *LH-MISS-PCT*))))
                 " percent."))
  (setq lh-miss-pct (lh:ask-pct *LH-MISS-PCT*))

  ;; -- step 3: optional cap on how many curves the result may use ---
  (setq lh-phase "reading the curve limit")
  (princ "\n\n  Step 3 of 6 - limit how many curves the result may use?")
  (princ "\n  Type a whole number, or None for no limit.")
  (lh:ask-cap)

  ;; -- step 4: closed outline or open polyline? ---------------------
  (setq lh-phase "reading the shape kind")
  (princ "\n\n  Step 4 of 6 - should the result close back on itself, or run open")
  (princ "\n  from one end of the scan to the other?")
  (setq closed (lh:ask-shape))

  ;; -- step 5: straight stretches and sharp corners -----------------
  ;; ABHD's steps 4 and 5 folded into one loop: a declared straight
  ;; stretch comes out as a dead-straight LINE between its two points;
  ;; a declared corner is exempt from the tangency rule.
  (setq lh-phase "asking about stretches, corners and held points"
        rawwalls nil
        rawcnrs  nil
        rawholds nil
        go       T)
  (princ "\n\n  Step 5 of 6 - any dead-straight stretches, sharp corners, or points")
  (princ "\n  to hold ABSOLUTELY?  A held point can never be fudged: the line")
  (princ "\n  passes through it exactly, in every candidate.  Each is picked by")
  (princ "\n  its point(s), snapping to the scanned points; dashed markers")
  (princ "\n  confirm them and clear themselves afterwards.")
  (while go
    (initget "Stretch Corner Hold Done")
    (setq ans (getkword
                "\n  Declare a stretch, corner or held point - or Done to fit? [Stretch/Corner/Hold/Done] <Done>: "))
    (cond
      ((= ans "Hold")
       (setq lh-phase "picking a held point"
             wp1      (getpoint "\n  Point to hold exactly: "))
       (if wp1
         (progn
           (setq wp1      (cal:2d wp1)
                 rawholds (cons wp1 rawholds))
           (lh:temp-add (lh:tag-mine (lh:draw-hold-marker wp1))))))
      ((= ans "Stretch")
       (setq lh-phase "picking a straight stretch"
             wp1      (getpoint "\n  First end of the straight stretch: ")
             wp2      (if wp1 (getpoint wp1 "\n  Second end: ")))
       (if wp2
         (progn
           (setq wp1 (cal:2d wp1) wp2 (cal:2d wp2))
           (lh:temp-add (lh:tag-mine (lh:draw-wall-marker wp1 wp2)))
           (setq rawwalls (cons (list wp1 wp2) rawwalls)))))
      ((= ans "Corner")
       (setq lh-phase "picking a sharp corner"
             wp1      (getpoint "\n  Corner point: "))
       (if wp1
         (progn
           (setq wp1     (cal:2d wp1)
                 rawcnrs (cons wp1 rawcnrs))
           (lh:temp-add (lh:tag-mine (lh:draw-corner-marker wp1))))))
      (T (setq go nil))))
  (setq rawwalls (reverse rawwalls)
        rawcnrs  (reverse rawcnrs)
        rawholds (reverse rawholds))
  (if (or rawwalls rawcnrs rawholds)
    (princ (strcat "\n  " (itoa (length rawwalls))
                   " stretch(es), " (itoa (length rawcnrs))
                   " corner(s) and " (itoa (length rawholds))
                   " held point(s) noted - the dashed markers on "
                   *LH-WALL-LAYER*
                   " clear themselves when the command finishes.")))

  ;; -- step 6: the selection ----------------------------------------
  (princ "\n\n  Step 6 of 6 - select the laser points (POINT entities on any layer,")
  (princ (strcat "\n  \"" *LH-POINT-BLOCK* "\" blocks, elevation text) and, if you have one, a rough"))
  (princ (strcat "\n  ordering sketch on layer " *LH-POOL-LAYER* "."))
  (princ "\n  Select objects: ")
  (setq lh-phase "waiting for the selection")
  ;; SPLINE and ELLIPSE are let in on purpose - not to fit them, but
  ;; so the classifier can name them in a useful message; TEXT is let
  ;; in so elevation labels can ride along with their points.
  (setq ss (ssget '((0 . "POINT,INSERT,LINE,ARC,CIRCLE,LWPOLYLINE,POLYLINE,SPLINE,ELLIPSE,TEXT"))))
  (if (null ss)
    (princ "\nNothing usable selected (points, and optionally a sketch on the POOL layer).")
    (progn
      ;; -- sort the selection into points, elevations and sketch -----
      (setq lh-phase "reading the selected entities")
      (setq segs nil pts nil texts nil i 0 nunsup 0 nocs 0
            npt 0 lh-ptnames nil lh-zvals nil)
      (while (< i (sslength ss))
        (setq en  (ssname ss i)
              ed  (entget en)
              lay (strcase (cdr (assoc 8 ed)))
              typ (cdr (assoc 0 ed))
              ext (cdr (assoc 210 ed))
              i   (1+ i))
        ;; geometry drawn in a tilted UCS reads back in its own plane,
        ;; so a flat 2D fit of it would be wrong - count and warn
        (if (and ext (< (abs (caddr ext)) 0.999)) (setq nocs (1+ nocs)))
        (cond
          ;; the survey point block is ALWAYS a point, on any layer
          ((and (= typ "INSERT")
                (= (strcase (cdr (assoc 2 ed))) (strcase *LH-POINT-BLOCK*)))
           (lh:add-point (cal:2d (cdr (assoc 10 ed)))
                         (cal:block-number en *LH-PT-TAG*)
                         (caddr (cdr (assoc 10 ed)))))
          ;; a plain POINT counts on ANY layer - laser exports land
          ;; wherever the converter put them; its Z is its elevation
          ((= typ "POINT")
           (lh:add-point (cal:2d (cdr (assoc 10 ed)))
                         nil
                         (caddr (cdr (assoc 10 ed)))))
          ;; a numeric TEXT may be an elevation label - set aside and
          ;; paired with its nearest point after the pass
          ((= typ "TEXT")
           (setq v (cond ((distof (cdr (assoc 1 ed)) 2))
                         ((distof (cdr (assoc 1 ed)) 4))))
           (if v
             (setq texts (cons (cons v (cal:2d (cdr (assoc 10 ed))))
                               texts))))
          ;; curve types we cannot read, on the sketch layer: count
          ;; them so the user gets told what to do
          ((and (= lay (strcase *LH-POOL-LAYER*))
                (member typ '("SPLINE" "ELLIPSE")))
           (setq nunsup (1+ nunsup)))
          ;; LHD's or ABHD's own output lives on the POOL layer too
          ;; (stamped) - never read it back as a sketch
          ((and (= lay (strcase *LH-POOL-LAYER*))
                (or (assoc -3 (entget en '("LHD")))
                    (assoc -3 (entget en '("ABHD")))))
           nil)
          ;; ordering sketch on the POOL layer
          ((= lay (strcase *LH-POOL-LAYER*))
           (setq segs (append segs (lh:ent-segs en))))
          ;; any other block dropped on the POINTS layer -> a point
          ((and (= typ "INSERT") (= lay (strcase *LH-POINT-LAYER*)))
           (lh:add-point (cal:2d (cdr (assoc 10 ed)))
                         (cal:block-number en *LH-PT-TAG*)
                         (caddr (cdr (assoc 10 ed)))))))
      (if (> nunsup 0)
        (princ (strcat "\nLHD: warning - " (itoa nunsup)
                       " SPLINE/ELLIPSE object(s) on layer "
                       *LH-POOL-LAYER*
                       " were ignored (only lines, arcs, circles and"
                       " polylines can be read - explode or convert"
                       " them first).")))
      (if (> nocs 0)
        (princ (strcat "\nLHD: warning - " (itoa nocs)
                       " selected object(s) are not drawn in the world"
                       " plane; the fit is flat (XY) and may be wrong."
                       "  Set UCS to World and flatten them first.")))
      (setq dpts  (if pts (cal:dedupe pts *LH-EXACT-EPS*))
            allow (cal:ceil (* (lh:misspct) (length dpts))))
      ;; pair the elevation labels with their points: nearest point
      ;; within *LH-TEXT-EPS*, and a point's own Z outranks a label
      (foreach tx texts
        (setq q (lh:nearest (cdr tx) dpts))
        (if (and q
                 (< (cal:dist q (cdr tx)) *LH-TEXT-EPS*)
                 (not (assoc q lh-zvals)))
          (setq lh-zvals (cons (cons q (car tx)) lh-zvals))))
      ;; snap the declared stretch ends and corners onto actual points
      (setq lh-walls nil)
      (foreach w rawwalls
        (setq w1 (lh:nearest (car w) dpts)
              w2 (lh:nearest (cadr w) dpts))
        (cond
          ((or (null w1) (null w2)) nil)
          ((< (cal:dist w1 w2) *LH-EXACT-EPS*)
           (princ "\n  (both ends of a declared stretch landed on the same scanned point - that stretch is ignored)"))
          (T
           (if (or (> (cal:dist (car w) w1) (* 3.0 tol))
                   (> (cal:dist (cadr w) w2) (* 3.0 tol)))
             (princ "\n  (a declared stretch end was picked well away from any scanned point - snapped to the nearest one)"))
           (setq lh-walls (cons (list w1 w2) lh-walls)))))
      (setq lh-walls (reverse lh-walls))
      (setq lh-corners nil)
      (foreach w rawcnrs
        (setq w1 (lh:nearest w dpts))
        (if w1
          (progn
            (if (> (cal:dist w w1) (* 3.0 tol))
              (princ "\n  (a declared corner was picked well away from any scanned point - snapped to the nearest one)"))
            (setq lh-corners (cons w1 lh-corners)))))
      (setq lh-corners (reverse lh-corners))
      ;; held points snap onto scanned points the same way; duplicates
      ;; collapse to one
      (setq lh-holds nil)
      (foreach w rawholds
        (setq w1 (lh:nearest w dpts))
        (if w1
          (progn
            (if (> (cal:dist w w1) (* 3.0 tol))
              (princ "\n  (a held point was picked well away from any scanned point - snapped to the nearest one)"))
            (if (not (lh:memb w1 lh-holds))
              (setq lh-holds (cons w1 lh-holds))))))
      (setq lh-holds (reverse lh-holds))
      (if (> (length dpts) 150)
        (princ (strcat "\nLHD: " (itoa (length dpts))
                       " points - ordering and fitting will take a"
                       " little while, please wait...")))
      (cond
        ((null pts)
         (princ (strcat "\nNo laser points found (looked for POINT"
                        " entities, \"" *LH-POINT-BLOCK*
                        "\" block insertions, and blocks on layer "
                        *LH-POINT-LAYER* ").")))
        ((< (length dpts) (if closed 3 2))
         (princ (strcat "\nAt least "
                        (if closed "3 distinct points are needed for a closed outline."
                                   "2 distinct points are needed for an open run."))))
        (T
         ;; -- order the points ---------------------------------------
         (setq ok T sketch nil e1 nil e2 nil)
         (if segs
           (progn
             (setq chn (lh:chain segs))
             (if chn
               (progn
                 (setq sketch (cdr chn))
                 (if (lh:has-arcs sketch)
                   (princ "\nPOOL sketch found - it only ORDERS the points; the shape comes from the points."))
                 (if (and closed (not (car chn)))
                   (princ "\n  (the sketch does not close - fine for ordering, the fit still closes)"))))))
         (cond
           (sketch
            (setq lh-phase "following the sketch order"
                  tour     (lh:loop-order sketch dpts)))
           (closed
            (princ "\nNo sketch selected - ordering the points into a loop automatically.")
            (setq lh-phase "ordering the points"
                  tour     (lh:order-points dpts)))
           (T
            (princ "\nNo sketch selected - the run's ends are the farthest-apart pair.")
            (princ "\n  (Redo lets you pick the two ends yourself.)")
            (setq lh-phase "ordering the points"
                  tour     (lh:order-points-open dpts nil nil))))
         ;; -- the output height, when the points carry elevations ----
         (setq zs (lh:zs-of dpts))
         (if zs
           (progn
             (setq lh-phase "reading the output height")
             (princ (strcat "\n\n  " (itoa (length zs))
                            " point(s) carry elevations.  The fit is a flat top-down"))
             (princ "\n  projection; the elevations only set the height the outline is")
             (princ "\n  drawn at - the highest point, the lowest, their average, or 0.")
             (setq elev (lh:pick-elev (lh:ask-zmode) zs)))
           (setq elev 0.0))
         (if ok
           (progn
             (setq again T)
             (while again
               (setq again nil)
               (if (eq 'REDO (lh:compare tour pts tol allow closed elev))
                 (progn
                   ;; -- redo: maybe omit points, then re-ask ---------
                   (setq lh-phase "picking points to omit"
                         omits    nil)
                   (princ "\n\nRedoing the fit.  Any points to leave out this time?")
                   (princ "\n  Pick each one (Enter for none) - mis-shots, duplicates, or")
                   (princ "\n  anything the line should not chase; each gets a dashed ring.")
                   (if lh-omitted
                     (princ (strcat "\n  " (itoa (length lh-omitted))
                                    " point(s) are already out -"
                                    " picking one of those puts it"
                                    " BACK IN.")))
                   (while (setq wp1 (getpoint
                                      "\n  Point to omit - or a ringed one to restore (Enter when done): "))
                     (setq wp1 (cal:2d wp1)
                           w1  (lh:nearest wp1 dpts)
                           w2  (lh:nearest wp1 (mapcar 'car lh-omitted)))
                     (cond
                       ((and w2 (or (null w1)
                                    (<= (cal:dist wp1 w2)
                                        (cal:dist wp1 w1))))
                        (setq ent        (assoc w2 lh-omitted)
                              pts        (append pts (cadr ent))
                              dpts       (cal:dedupe pts *LH-EXACT-EPS*)
                              lh-omitted (lh:remove ent lh-omitted)
                              omits      (lh:remove w2 omits))
                        (if (and (caddr ent) (entget (caddr ent)))
                          (progn
                            (lh:temp-drop (caddr ent))
                            (entdel (caddr ent))))
                        (princ (strcat "  - Pt." (lh:pt-name w2)
                                       " back in")))
                       (w1
                        (setq pts2 nil ent nil)
                        (foreach w pts
                          (if (< (cal:dist w w1) *LH-EXACT-EPS*)
                            (setq ent (cons w ent))
                            (setq pts2 (cons w pts2))))
                        (setq pts  (reverse pts2)
                              dpts (cal:dedupe pts *LH-EXACT-EPS*)
                              ring (lh:temp-add (lh:tag-mine
                                     (lh:draw-corner-marker w1)))
                              lh-omitted (cons (list w1 ent ring)
                                               lh-omitted)
                              omits      (cons w1 omits))
                        (princ (strcat "  - omitting Pt."
                                       (lh:pt-name w1))))))
                   (if omits
                     (progn
                       ;; declared stretches and corners anchored on
                       ;; an omitted point make no sense any more
                       (setq pts2 nil)
                       (foreach w lh-walls
                         (if (not (or (lh:memb (car w) omits)
                                      (lh:memb (cadr w) omits)))
                           (setq pts2 (cons w pts2))))
                       (if (< (length pts2) (length lh-walls))
                         (princ "\n  (a declared stretch lost an end and was dropped)"))
                       (setq lh-walls (reverse pts2)
                             pts2     nil)
                       (foreach w lh-corners
                         (if (not (lh:memb w omits))
                           (setq pts2 (cons w pts2))))
                       (setq lh-corners (reverse pts2)
                             pts2       nil)
                       ;; a held point that was just omitted is out of
                       ;; the fit entirely - nothing left to hold
                       (foreach w lh-holds
                         (if (not (lh:memb w omits))
                           (setq pts2 (cons w pts2))))
                       (if (< (length pts2) (length lh-holds))
                         (princ "\n  (an omitted point was held - its hold went with it)"))
                       (setq lh-holds (reverse pts2))))
                   (if lh-omitted
                     (princ (strcat "\n  " (itoa (length lh-omitted))
                                    " point(s) omitted in total - "
                                    (itoa (length dpts))
                                    " in the fit.")))
                   (if (< (length dpts) (if closed 3 2))
                     (princ "\nToo few points remain for a fit - nothing redone.")
                     (progn
                       ;; stretches and corners may change for the retry
                       (princ "\n\n  Straight stretches and sharp corners can change too -")
                       (princ "\n  Enter keeps each list as it is.")
                       (setq lh-phase "editing straight stretches")
                       (lh:edit-walls dpts)
                       (setq lh-phase "editing sharp corners")
                       (lh:edit-corners dpts)
                       (setq lh-phase "editing held points")
                       (lh:edit-holds dpts)
                       ;; an open run's ends can be picked by hand
                       (if (not closed)
                         (progn
                           (setq lh-phase "picking the run's ends")
                           (initget "Yes No")
                           (setq ans (getkword
                                       "\n  Pick the two END points of the open run? [Yes/No] <No>: "))
                           (if (= ans "Yes")
                             (progn
                               (setq wp1 (getpoint "\n  First end: ")
                                     wp2 (if wp1 (getpoint wp1 "\n  Second end: ")))
                               (if wp2
                                 (setq e1 (lh:snap-break wp1 dpts)
                                       e2 (lh:snap-break wp2 dpts)))))))
                       (princ "\n\n  New settings - Enter keeps each one as it is.")
                       (setq lh-phase "reading the tolerance"
                             tol      (lh:ask-tol))
                       (setq lh-phase "reading the miss percentage"
                             lh-miss-pct (lh:ask-pct lh-miss-pct))
                       (setq lh-phase "reading the curve limit")
                       (lh:ask-cap)
                       (setq allow (cal:ceil (* (lh:misspct)
                                               (length dpts))))
                       ;; forced ends that were omitted are forgotten
                       (if (and e1
                                (not (and (lh:memb e1 dpts)
                                          (lh:memb e2 dpts))))
                         (setq e1 nil e2 nil))
                       ;; the point order must forget the omitted ones
                       (setq lh-phase "ordering the points")
                       (cond
                         (sketch (setq tour (lh:loop-order sketch dpts)))
                         (closed (setq tour (lh:order-points dpts)))
                         (T      (setq tour (lh:order-points-open
                                              dpts e1 e2))))
                       ;; the output height follows the surviving points
                       (setq zs   (lh:zs-of dpts)
                             elev (lh:pick-elev *LH-ZMODE* zs))
                       (setq again T))))))))))))
  ;; sweep the dashed markers and any candidate the user did not keep
  (lh:temp-clear)
  (setq *error* lh-old-err)   ; restore the previous error handler
  (princ))

(princ (strcat "\nLHD " *lh-version*
               " loaded.  LHD fits a top-down outline (closed or open)"
               " through laser-scanned points."))
(princ)


;;; ======================================================================
;;; >>> lincheck.lsp
;;; ======================================================================

;;; ===================================================================
;;; LINCHECK.LSP - Liner tech drawing checklist
;;;
;;; Interactive AutoLISP routine that runs down the liner drawing
;;; checklist one item at a time, prompting the tech to complete /
;;; answer each item, then prints a report of everything that was
;;; checked, answered, and noted along the way.
;;;
;;; Every item after the first also offers Back (type B; Undo works
;;; too), which re-asks the previous item and drops what it logged -
;;; a mis-answered question never means Esc and a fresh start.  At the
;;; typed prompts (notes, values, cross dims) Back is typed like a
;;; note: B, BACK, U or UNDO alone, any case.
;;;
;;; Load with APPLOAD (or (load "lincheck.lsp")) and run the
;;; LINCHECK command.
;;; ===================================================================

;;; ------------------------------------------------------------------
;;; Helpers
;;; ------------------------------------------------------------------

;;; SHARED BUILD: requires CALOFIN-LIB.lsp (load via CALOFIN-LOADER.lsp).
;;; Generic helpers live there under cal: - see STANDARDS.md.
;;;

(setq *lincheck-version* "v1.1")   ; announced on load; release_lisp.py
                                      ; stamps the dated twin in releases/

(setq *lin:log* nil)   ; collected report lines

;; Record a line for the report.
(defun lin:log (msg)
  (setq *lin:log* (append *lin:log* (list msg)))
  msg
)

;; Keep only the first N report lines - the rollback when a Back drops
;; what an item logged.
(defun lin:trim (n / out i)
  (setq out nil i 0)
  (foreach l *lin:log*
    (if (< i n) (setq out (cons l out)))
    (setq i (1+ i))
  )
  (setq *lin:log* (reverse out))
)

;; Section header - printed to the command line and added to the report.
(defun lin:head (title)
  (princ (strcat "\n\n=== " title " ==="))
  (lin:log "")
  (lin:log (strcat "== " title " =="))
)

;; Simple check-off item.  Shows the item, waits for the tech to press
;; Enter when done (or type a note/value to record with it).  With back
;; non-nil, B (Back) returns the symbol LIN-BACK instead of logging.
(defun lin:check (item back / val)
  (setq val (getstring T (strcat "\n[ ] " item
                                 "\n      (Enter = done"
                                 (if back ", B = back" "")
                                 ", or type a note): ")))
  (cond
    ((and back (cal:back-word-p val)) 'LIN-BACK)
    ((= val "") (lin:log (strcat "[x] " item)) val)
    (T (lin:log (strcat "[x] " item " -- " val)) val)
  )
)

;; Ask the user to pick one keyword out of a list.  With back non-nil
;; the choices also take Back (Undo accepted as a hidden synonym),
;; returning the symbol LIN-BACK.
(defun lin:ask (prompt kwlist back / ans)
  (while (not ans)
    (initget 1 (if back (strcat kwlist " Back Undo") kwlist))
    (setq ans (getkword (strcat "\n" prompt " ["
                                (vl-string-translate " " "/" kwlist)
                                (if back "/Back" "") "]: ")))
  )
  (if (member ans '("Back" "Undo"))
    'LIN-BACK
    (progn (lin:log (strcat "[x] " prompt " -> " ans)) ans)
  )
)

;; Yes/No convenience wrapper.  Returns T for Yes, nil for No, or the
;; symbol LIN-BACK.
(defun lin:yesno (prompt back / v)
  (setq v (lin:ask prompt "Yes No" back))
  (if (eq v 'LIN-BACK) v (= v "Yes"))
)

;; Ask for a value; records the value, or "NA" if none was provided.
;; With back non-nil, B (Back) returns the symbol LIN-BACK instead.
(defun lin:value (label back / val)
  (setq val (getstring T (strcat "\n    " label " (value or NA"
                                 (if back ", B = back" "") "): ")))
  (cond
    ((and back (cal:back-word-p val)) 'LIN-BACK)
    ((or (= val "") (= (strcase val) "NA") (= (strcase val) "N/A"))
     (lin:log (strcat "    " label ": NA (not provided)")) val)
    (T (lin:log (strcat "    " label ": " val)) val)
  )
)

;; Run the checklist as a list of one-question stages with Back between
;; them.  Each stage is (test-expr . fn): a stage whose test evaluates
;; nil is skipped, and tests are re-evaluated on every pass, so backing
;; up and changing an answer re-routes the branch.  A stage returning
;; LIN-BACK rewinds to the previous asked stage and drops everything
;; logged since just before it; LIN-STOP ends the run early (the report
;; still prints).  Stage 1 has nowhere to go back to, so it re-asks.
(defun lin:stages (fns / i n v it asked mark)
  (setq i 0 n (length fns) asked nil)
  (while (< i n)
    (setq it (nth i fns))
    (if (and (car it) (not (eval (car it))))
      (setq i (1+ i))                       ; branch not taken - skip
      (progn
        (setq mark (length *lin:log*)
              v    (apply (cdr it) nil))
        (cond
          ((eq v 'LIN-BACK)
           (lin:trim mark)                  ; drop the aborted item's log
           (if asked
             (progn
               (setq i (caar asked))
               (lin:trim (cdar asked))
               (setq asked (cdr asked))
             )
             (princ "\n  Already at the first item.")
           ))
          ((eq v 'LIN-STOP) (setq i n))
          (T
           (setq asked (cons (cons i mark) asked)
                 i     (1+ i))
          )
        )
      )
    )
  )
)

;;; ------------------------------------------------------------------
;;; Checklist stages (one question each; heads travel with the first
;;; question under them so a Back re-prints the section header too)
;;; ------------------------------------------------------------------

(defun lin:st-read ()
  (lin:head "Job Review")
  (lin:check "Read all WSN (White Screen Notes), Notes from Merlin, and Customer Info" nil)
)

(defun lin:st-gate (/ v)
  (setq v (lin:yesno "Does this job actually require a Tech drawing?" T))
  (cond
    ((eq v 'LIN-BACK) v)
    ((null v)
     (lin:log "")
     (lin:log ">> Job does NOT require a Tech drawing - stopping checklist.")
     'LIN-STOP)
    (T v)
  )
)

(defun lin:st-wallht-chk ()
  (lin:head "Walls & Depth")
  (lin:check "Verify Finished Wall Ht & Pool Depth" T)
)

(defun lin:st-wallht-val ()
  (lin:value "Finished Wall Ht (single value, or \"Varies\")" T)
)

(defun lin:st-glp ()
  (lin:head "Liner Pattern & Bead")
  (lin:check "Place liner pattern block (GLP) - delete \"Not Supplied\" text" T)
)

(defun lin:st-bead ()
  (lin:value "Pool bead type / overlap (AG, etc.)" T)
)

(defun lin:st-perim ()
  (lin:head "Dimensions & Orientation")
  (lin:check "Pool perimeter & overall dims" T)
)

(defun lin:st-orient ()
  (lin:check "Verify orientation: Shallow end to the RIGHT of page" T)
)

(defun lin:st-crossdims ()
  ;; Report ALL cross dimensions provided by the customer.
  (princ "\nReport ALL cross dimensions provided by customer.")
  (princ "\n  Enter each as label=value (e.g. A-C=24'6\"), or NA. Blank line to finish.")
  (lin:log "[x] Cross dimensions provided by customer:")
  (lin:crossdims T)
)

(defun lin:st-corners ()
  (lin:head "Corners")
  (lin:check "Pool corners with dimensions" T)
)

(defun lin:st-mfgrs ()
  (lin:check (strcat "Watch for special mfgrs: Esther Williams (3x3, 5x5) "
                     "or Foxx (37\" Deep)") T)
)

(defun lin:st-cove ()
  (lin:head "Special Bottom Conditions")
  (lin:yesno "Does the shallow end have a Cove?" T)
)

(defun lin:st-ledge ()
  (lin:yesno "Does the pool have a Safety Ledge?" T)
)

(defun lin:st-depths ()
  (lin:yesno "Did the customer provide various depths for the bottom?" T)
)

(defun lin:st-sideview ()
  (lin:yesno "Does the pool require a side view?" T)
)

(defun lin:st-hopper ()
  (lin:head "Bottom & Trowel Lines")
  (lin:yesno "Are hopper corners radius?" T)
)

(defun lin:st-trowel ()
  (lin:check "Draw trowel lines accurately" T)
)

(defun lin:st-fib (/ v)
  (lin:head "Steps / Bench - Fiberglass")
  (setq v (lin:yesno "Are steps / bench Fiberglass?" T))
  (if (not (eq v 'LIN-BACK)) (setq fib v))
  v
)

(defun lin:st-fib-note ()
  (lin:check "Place FGS note or draw step outline if dimensions were provided" T)
)

(defun lin:st-fib-type ()
  (lin:ask "Is the step Straight or Radius? (ask if not given)"
           "Straight Radius" T)
)

(defun lin:st-vin (/ v)
  (lin:head "Steps / Bench - Vinyl-Covered")
  (setq v (lin:yesno "Are steps / bench Vinyl-covered?" T))
  (if (not (eq v 'LIN-BACK)) (setq vin v))
  v
)

(defun lin:st-vin-corner ()
  (lin:check "Verify step corner type & dimensions" T)
)

(defun lin:st-vin-attach ()
  (lin:check "Place Step Attachment block" T)
)

(defun lin:st-vin-attype ()
  (lin:yesno "Is the attachment type provided?" T)
)

(defun lin:st-vin-side ()
  (lin:check "Place side views for all steps and benches" T)
)

(defun lin:st-final ()
  (lin:head "Final")
  (lin:check "Did you scale the titleblock?  ** REDVIEW! **" T)
)

;;; ------------------------------------------------------------------
;;; Checklist
;;; ------------------------------------------------------------------

(defun c:LINCHECK (/ *error* fib vin)
  ;; a walker: it changes no setting and opens no undo group, so the
  ;; handler's whole job is to keep a cancel from printing a raw
  ;; AutoLISP message at the user (STANDARDS section 5)
  (defun *error* (msg)
    (if (and msg (not (wcmatch (strcase msg)
                               "*BREAK*,*CANCEL*,*QUIT*,*EXIT*")))
        (princ (strcat "\nLINCHECK error: " msg)))
    (princ))

  (setq *lin:log* nil fib nil vin nil)
  (princ "\n--- Liner Tech Drawing Checklist ---")
  (princ "\nWork down each item; the report prints at the end.")
  (princ "\n(after the first item, Back re-asks the previous one)\n")
  (lin:stages (list
    (cons nil  'lin:st-read)
    (cons nil  'lin:st-gate)
    (cons nil  'lin:st-wallht-chk)
    (cons nil  'lin:st-wallht-val)
    (cons nil  'lin:st-glp)
    (cons nil  'lin:st-bead)
    (cons nil  'lin:st-perim)
    (cons nil  'lin:st-orient)
    (cons nil  'lin:st-crossdims)
    (cons nil  'lin:st-corners)
    (cons nil  'lin:st-mfgrs)
    (cons nil  'lin:st-cove)
    (cons nil  'lin:st-ledge)
    (cons nil  'lin:st-depths)
    (cons nil  'lin:st-sideview)
    (cons nil  'lin:st-hopper)
    (cons nil  'lin:st-trowel)
    (cons nil  'lin:st-fib)
    (cons 'fib 'lin:st-fib-note)
    (cons 'fib 'lin:st-fib-type)
    (cons nil  'lin:st-vin)
    (cons 'vin 'lin:st-vin-corner)
    (cons 'vin 'lin:st-vin-attach)
    (cons 'vin 'lin:st-vin-attype)
    (cons 'vin 'lin:st-vin-side)
    (cons nil  'lin:st-final)
  ))
  (lin:report)
  (princ)
)

;; Collect the customer's cross dimensions (loop until a blank entry).
;; B (Back) removes the last entry, or - when there is none and back is
;; non-nil - leaves the stage with LIN-BACK.
(defun lin:crossdims (back / entry n done)
  (setq n 0 done nil)
  (while (not done)
    (setq entry (getstring T (strcat "\n  Cross dim (label=value / NA"
                                     ", B = back, blank to finish): ")))
    (cond
      ((cal:back-word-p entry)
       (if (> n 0)
         (progn
           (setq n (1- n))
           (lin:trim (1- (length *lin:log*)))
           (princ "\n  Stepping back one cross dim.")
         )
         (if back
           (setq done 'LIN-BACK)
           (princ "\n  Already at the first cross dim.")
         )
       ))
      ((= entry "") (setq done T))
      (T (setq n (1+ n)) (lin:log (strcat "    " entry)))
    )
  )
  (if (eq done 'LIN-BACK)
    'LIN-BACK
    (progn (if (= n 0) (lin:log "    (none provided)")) n)
  )
)

;; Print the collected report.
(defun lin:report ()
  (princ "\n\n")
  (princ "############################################")
  (princ "\n#          LINER CHECKLIST REPORT          #")
  (princ "\n############################################")
  (foreach line *lin:log*
    (princ (strcat "\n" line))
  )
  (princ "\n############################################")
  (princ "\n")
  (princ)
)

(princ "\nLINCHECK.LSP loaded. Type LINCHECK to run the liner checklist.")
(princ)


;;; ======================================================================
;;; >>> linfincheck.lsp
;;; ======================================================================

;;; ------------------------------------------------------------------
;;;  linfincheck.lsp — LINFINCHECK: the full liner-finish drawing QA
;;;
;;;  Grew from a dimension/arc auditor (based on check_drawing.lsp) into
;;;  a guided, one-at-a-time review of the whole title block: dims,
;;;  arcs, overlapping lines, steps and their side views, wall height,
;;;  the liner pattern, and the title block border. For just the first
;;;  three of those — the quick pass someone wants without going
;;;  through the whole liner-finish gauntlet — see dimcheck.lsp
;;;  instead; it shares this file's Move/Keep/Pick and report machinery
;;;  but leaves out steps, wall height, liner and border. Type
;;;  LINFINCHECK, then:
;;;
;;;  1. You are asked to highlight the drawing (any selection).
;;;     Everything selected is greyed out so only the item under
;;;     review stands out.
;;;
;;;  2. Dimensions are reviewed ONE AT A TIME, in a fixed marching
;;;     order: grouped by dimension style — "STANDARD", then "SIDE
;;;     STANDARD", then "STANDARD INCHES", then "CROSS DIMENSIONS",
;;;     then whatever styles are left (tune *lfc-style-order*) —
;;;     and inside each group left to right, top to bottom (row by
;;;     row, like reading). Each dimension is zoomed to, shown in
;;;     its own colour and highlighted while the rest stays grey.
;;;     For linear/aligned dimensions the two definition points are
;;;     audited first: a point that does not sit on any object is
;;;     shown where LINFINCHECK thinks it belongs, with BOTH spots
;;;     marked on screen and spelled out so there is no doubt which
;;;     is which —
;;;         a RED X   where you drew it,
;;;         a GREEN + where we would move it, joined by a line.
;;;     You then choose, one point at a time:
;;;         Enter / M  ->  MOVE it onto the nearest object (green +)
;;;         K          ->  KEEP it exactly where you drew it (red X);
;;;                        the point is put back and nothing changes
;;;         P          ->  PICK the spot yourself
;;;     A construction line (XLINE) is drawn through the dimension's
;;;     original points on layer LINFINCHECK-CONSTRUCTION so you can see
;;;     where it used to measure — only when a point actually moved.
;;;     Then the overall question for every dimension:
;;;         "Is this dimension correct?"
;;;         Enter / Y  ->  correct, the dimension is left alone
;;;         N          ->  the dimension is recoloured RED so it is
;;;                        easy to find and fix afterwards
;;;
;;;  3. Arcs are reviewed the same way, one endpoint at a time, with
;;;     the same Move / Keep / Pick choice. An endpoint not attached
;;;     to the end of another object is snapped there and both spots
;;;     are marked; Keep puts the arc back exactly as you drew it
;;;     (its original shape is restored, not re-fitted), Pick re-fits
;;;     it through your spot. Arcs whose endpoints actually changed
;;;     are recoloured MAGENTA — an arc you kept is left alone.
;;;
;;;  4. OVERLAPPING LINES are hunted down: two straight LINE entities
;;;     that are collinear and run on top of each other (a leftover
;;;     from drawing over an existing line to continue it and never
;;;     cleaning it up). Each overlapping pair is zoomed to and
;;;     highlighted, the overlapping stretch is marked with crosses,
;;;     and you choose:
;;;         Enter / M  ->  MERGE the two into one line spanning both
;;;                        (only when they share a layer; the merged
;;;                        line turns CYAN so you can see it changed)
;;;         F          ->  FLAG both lines CYAN to fix by hand
;;;         L          ->  LEAVE them as drawn (intentional)
;;;     Lines that merely touch end-to-end are fine and not reported.
;;;
;;;  5. STEP / STAIRCASE check. Groups of 3+ parallel lines stacked
;;;     less than 18 units apart (18" in inch drawings — tune
;;;     *lfc-step-maxgap*) look like steps. When such patterns are
;;;     found, LINFINCHECK first looks for a SIDE VIEW in the selection
;;;     (a side view reads as two step patterns at right angles to
;;;     each other — treads + risers — in the same spot, each one
;;;     marching along like a profile rather than sitting stacked).
;;;     Benches count: their profile is only two treads deep, so
;;;     side-view halves are found down to *lfc-bench-minlines*
;;;     while the "are these steps?" prompt still needs a full-size
;;;     *lfc-step-minlines* pattern. Whatever the side view belongs
;;;     to — stairs or a bench — its overall height is confirmed
;;;     against the Finished Wall Ht (see below).
;;;       - Side view found  -> steps are taken as real; skip ahead.
;;;       - No side view     -> each pattern is highlighted and you
;;;         are asked "Are these lines steps?". If any are, you are
;;;         asked whether a side view is drawn somewhere; if not, the
;;;         report tells you to ADD A SIDE VIEW.
;;;     Whenever steps + side view are present, the selection must
;;;     hold a block with the words "Step Attachment" (block name,
;;;     attribute or text inside it). None -> the report tells you to
;;;     add one. Found -> it is zoomed to and you confirm the CORRECT
;;;     one is placed; answering No flags it red and reports it.
;;;     A generic block still listing EVERY option ("Bead", "Flaps",
;;;     "Rod Pockets", "No Attachment" - tune *lfc-attach-options*)
;;;     means nobody picked one yet. That is only acceptable when the
;;;     drawing carries a "to be secured?" note (tune
;;;     *lfc-secured-phrase*) asking whoever it goes to; with the
;;;     note it reads as waiting on the customer, without it the
;;;     report says to add one. A block naming one option - or a
;;;     combination like Bead + Rod Pockets - counts as decided.
;;;     When the attachment style is "BEAD Step Attachment", every
;;;     plan-view step pattern must also have something drawn on
;;;     layer "Bead Track" (tune *lfc-bead-layer*) within
;;;     *lfc-bead-dist* of it. The whole drawing is searched, not
;;;     just the selection. The side view itself is exempt — bead
;;;     track is only demanded next to the plan-view steps. Patterns
;;;     with nothing nearby are called out in the report.
;;;     The OVERALL HEIGHT of the steps is confirmed too: measured
;;;     from the side view's geometry (its total rise), or typed /
;;;     picked as two points when the side view was not auto-found,
;;;     and compared against the WallHt attribute of the "Tech
;;;     Title" block (found space-insensitively, drawing-wide; tune
;;;     *lfc-title-block* / *lfc-wallht-tag*). Heights written as
;;;     40'', 3'-4'', 3' 4 1/2" or 40.5 are all understood, and a
;;;     label is ignored, so the attribute may read "Finished Wall
;;;     Ht = 40''" and still measure 40. The WallHt itself is
;;;     validated whenever a Tech Title exists, steps or not:
;;;       - several heights at once ("0'', 35 3/4'', 37 1/4''") ->
;;;         CHECK THE WALL HEIGHT, side view left alone;
;;;       - a lone 0'' (below *lfc-min-wallht*) -> NONSENSICAL,
;;;         fix the title block - the dim is never blamed for it;
;;;       - "?" -> fine only when a "Wall height" note (tune
;;;         *lfc-ask-phrase*) asks the customer somewhere in the
;;;         drawing; otherwise the report says to add one;
;;;       - a single sensible value ("35 3/4''") -> no warning. When the side view carries
;;;     its own overall-height dimension (the one whose definition
;;;     points span the full rise), that dimension is what gets
;;;     compared — and if it disagrees with WallHt, or its text was
;;;     overridden to disagree with the geometry it spans, it is
;;;     MARKED RED AUTOMATICALLY and reported. Any difference beyond
;;;     *lfc-height-tol* is reported in red as a MISMATCH.
;;;     Two title-block answers give nothing to check against, so
;;;     the side view is LEFT ALONE (never marked red) in both:
;;;       - "Finished Wall Ht = Varies" — the height genuinely
;;;         varies; the report just notes it.
;;;       - several heights at once, e.g. "= 0'', 40'', 45''" — the
;;;         report tells you to CHECK THE WALL HEIGHT in the title
;;;         block. A compound height ( 3'-4'' ) is still one value,
;;;         not several.
;;;
;;;  6. TECH TITLE DATE. The "Date" attribute of the Tech Title block
;;;     (same block as WallHt; tune *lfc-date-tag*) is checked whenever
;;;     a Tech Title exists, steps or not: it must read a real calendar
;;;     date in MM/DD/YYYY form — two digits, slash, two digits, slash,
;;;     four digits, month 01-12, and a day valid for that month (leap
;;;     Februaries included). Missing, blank, wrong format ("5/1/24",
;;;     "05-01-2024"), an out-of-range month/day, or a made-up day like
;;;     "02/30" is reported in red with what is wrong. A well-formed
;;;     calendar date that is NOT TODAY is reported too - a sheet going
;;;     out under an old date is the mistake that catches. Only
;;;     today's date, written MM/DD/YYYY, is a quiet OK; with no Tech
;;;     Title in reach the report says the date was not checked.
;;;
;;;  7. LINER MATERIAL check. The selection must hold a block named
;;;     (or containing the words) "Liner Material" / "Liner Material
;;;     with Step". Missing -> reported. Each one found is scanned
;;;     for the standalone words "NOT" and "ERROR" in its attributes
;;;     and text (e.g. "Not Selected", "Not Included", "#ERROR");
;;;     A field that carries one of those words was never really
;;;     filled in ("Not Supplied", "#ERROR"), so LINFINCHECK WIPES IT
;;;     BACK TO BLANK and says which fields it cleared - the pattern
;;;     block reads clean afterwards. Only attribute VALUES are
;;;     cleared: the block's own labels ("Pattern:", "Wall:",
;;;     "Floor:", "Step:") live in its definition and are never
;;;     touched, and a real pattern name is left alone. A bad word
;;;     sitting in the block's static text cannot be cleared, so it
;;;     is reported instead. LINFINSCAN, being read-only, reports these
;;;     as NEEDS WIPING and changes nothing. The liner pattern must also agree with how the
;;;     steps are built:
;;;       - a FIBERGLASS STEP anywhere in the highlighted area (as
;;;         text, a block, or the layer things sit on — see
;;;         *lfc-fgstep-words*) is its own unit, so the liner must
;;;         NOT carry a Step. One that does is reported.
;;;       - otherwise, when steps are drawn, the liner must cover
;;;         them: no liner block carrying a "Step" section (the
;;;         "Liner Material with Step" variant) is reported.
;;;
;;;  8. TITLE BLOCK BORDER. The outer drawing on layer "border"
;;;     (tune *lfc-border-layer*) must be the nominal sheet —
;;;     58'-8" wide by 45'-3 5/8" tall — or a scaled-UP multiple of
;;;     it. Anything smaller is reported in red as
;;;         "Title block should not be SCALED DOWN for Liners".
;;;     A border out of proportion (scaled unevenly) is reported
;;;     separately as STRETCHED, and a missing border as NO BORDER.
;;;     Everything on the layer is measured together, so a frame
;;;     drawn as one polyline and one drawn as four lines both
;;;     measure the same. The selection is used when it holds the
;;;     border, otherwise the whole drawing is searched.
;;;
;;;  8a. FEET AND INCHES. Every text box in the selection - TEXT,
;;;     MTEXT and the ATTRIB values on blocks - must state its inches
;;;     wherever it states feet: 5' is flagged, 5'-0", 3'-2" and a
;;;     plain 40" are fine. A feet mark is an apostrophe straight
;;;     after a digit, so "Water's Edge" is prose and never flagged.
;;;     This one runs in LITELINFINSCAN too.
;;;
;;;  8b. DIMENSION LAYER. Every dimension must sit on the
;;;     "DIMENSION" layer (tune *lfc-dim-layer*). Any that do not are
;;;     counted, the layers they landed on are named, and the report
;;;     tells you to run CDIM (tune *lfc-dimfix-cmd*) to move them.
;;;     This one runs in LITELINFINSCAN too.
;;;
;;;  9. A LINFINCHECK REPORT (MTEXT) is placed to the RIGHT of the
;;;     drawing on layer LINFINCHECK-REPORT, sized from the drawing's
;;;     extents so it sits to scale next to it.  The MAIN sheet leads
;;;     with what matters to the liner finish itself: a large title,
;;;     the date and version, a verdict line (ALL CLEAR, or the count
;;;     of red lines), the colour legend, a SUMMARY dashboard, then
;;;     the findings under underlined section headings (STEPS & SIDE
;;;     VIEWS, WALL HEIGHT, THE LINER, ...).  The DIMCHECK-style
;;;     findings — every dimension with its measured distance, every
;;;     arc, every overlapping line pair with its overlap length — go
;;;     in a separate DIMENSION AUDIT column to the RIGHT of the main
;;;     sheet, so the liner verdicts lead and the mechanical audit
;;;     reads alongside.  Any line describing something questionable
;;;     or that needs looking over (a flagged/wrong item, a missing
;;;     block, a "NOT" find, an "add ..." note, a skipped check) is
;;;     coloured RED in the report; everything that checked out stays
;;;     the report's normal colour and is drawn at *lfc-green-scale*
;;;     (3/4) of the red text's height, so the problems are the big
;;;     lines on the sheet.
;;;
;;;  LITELINFINSCAN is LINFINSCAN minus the DIMCHECK-style pass: no
;;;     dimension, arc or overlap audit and no DIMENSION AUDIT
;;;     column - just the liner-finish rules, for a drawing DIMCHECK
;;;     already went over.
;;;
;;;  All original colours are restored when the review ends — except
;;;  the red "fix me" dimensions, magenta moved arcs and cyan
;;;  merged/flagged lines, which stay marked on purpose. Everything
;;;  (including the report) runs inside one UNDO group, so a single U
;;;  reverts the whole review.
;;;
;;;  SAFETY NETS
;;;  - Locked layers in the selection are announced up front with an
;;;    offer to unlock for the run (re-locked afterwards, even on
;;;    error); left locked, their items are reported but untouched.
;;;  - Object-associative dimensions are warned about before their
;;;    points are moved — an associative point may re-anchor on its
;;;    own — and their report line says so in red.
;;;  - Rerunning LINFINCHECK replaces the previous report and marker
;;;    lines instead of stacking a second copy on top.
;;;  - Original colours are stashed in xdata before greying. If a
;;;    crash or kill ever leaves the drawing grey, LINFINCHECKRESCUE
;;;    restores every stashed colour and clears LINFINCHECK's report
;;;    and markers (flag colours included — it is the full reset).
;;;  - With several Tech Title blocks on the sheet, the one nearest
;;;    the checked area is used; titles disagreeing on WallHt are
;;;    called out in red.
;;; ------------------------------------------------------------------
;;; SHARED BUILD: requires CALOFIN-LIB.lsp (load via CALOFIN-LOADER.lsp).
;;; Generic helpers live there under cal: - see STANDARDS.md.

(vl-load-com)

;; ---- configuration -------------------------------------------------
(setq *lfc-version* "v1.9")        ; announced on load; release_lisp.py
                                    ; reads this banner and stamps the
                                    ; dated twin in releases/ from it

(defun c:LINFINCHECKVER ()
  (princ (strcat "\nLINFINCHECK " *lfc-version*))
  (princ))

;; --- tunables ------------------------------------------------------
(setq *lfc-tol*          1.0e-4)  ; max gap (drawing units) that still counts as attached
(setq *lfc-grey-color*   8)       ; grey used to fade out everything not under review
(setq *lfc-flag-color*   1)       ; red: dimensions you answered "No" to
(setq *lfc-arc-color*    6)       ; magenta: arcs whose endpoints were moved
(setq *lfc-olap-color*   4)       ; cyan: merged or flagged overlapping lines
(setq *lfc-olap-fuzz*    1.0e-4)  ; max sideways offset that still counts as "same line"
(setq *lfc-step-maxgap*  18.0)    ; steps: max tread spacing (drawing units; 18 = 18" when 1 unit = 1")
(setq *lfc-step-minlines* 3)      ; steps: how many stacked parallel lines look like steps
(setq *lfc-bench-minlines* 2)     ; side view: a bench profile is only two treads deep
(setq *lfc-step-angtol*  1.0)     ; steps: parallelism tolerance (degrees)
(setq *lfc-bead-layer*   "Bead Track") ; layer bead track must be drawn on
(setq *lfc-bead-dist*    18.0)    ; how close bead track must be to plan-view steps (units)
(setq *lfc-title-block*  "Tech Title") ; title block holding the wall height (spaces optional)
(setq *lfc-wallht-tag*   "WallHt")     ; attribute tag carrying the wall height
(setq *lfc-date-tag*     "Date")       ; attribute tag carrying the drawing date
(setq *lfc-height-tol*   0.25)    ; steps height vs WallHt: allowed difference (units)
(setq *lfc-min-wallht*   1.0)     ; a WallHt below this is NONSENSICAL (0'' walls do not exist)
(setq *lfc-ask-phrase*   "Wall height") ; the question text expected when WallHt is "?"
;; the generic Step Attachment block lists every option with a box; if
;; ALL of them are still showing, nobody picked one, and the drawing
;; must carry the question note instead
(setq *lfc-attach-options*
      '("Bead" "Flaps" "Rod Pockets" "No Attachment"))
(setq *lfc-secured-phrase* "to be secured")

;; dimension styles are reviewed in this order; styles not listed
;; come afterwards ("whatever else is left"), still left-to-right
(setq *lfc-style-order*
      '("STANDARD" "SIDE STANDARD" "STANDARD INCHES" "CROSS DIMENSIONS"))
;; every dimension belongs on this layer; CDIM is the command that
;; moves the strays there, and is what the report tells you to run
(setq *lfc-dim-layer*   "DIMENSION")
(setq *lfc-dimfix-cmd*  "CDIM")
(setq *lfc-constr-layer* "LINFINCHECK-CONSTRUCTION")
(setq *lfc-constr-color* 2)       ; yellow
(setq *lfc-green-scale*  0.75)    ; report: all-clear text height, as a fraction of the red text
(setq *lfc-block-depth*  3)       ; how many levels of nested blocks to search for names/text
(setq *lfc-orig-color*   1)       ; red X: where you drew the point
(setq *lfc-sugg-color*   3)       ; green +: where LINFINCHECK would move it
;; title block border: nominal 58'-8" x 45'-3 5/8", or a scaled-UP multiple
(setq *lfc-border-layer* "border")
(setq *lfc-border-w*     704.0)   ; 58'-8"     in drawing units (1 unit = 1 inch)
(setq *lfc-border-h*     543.625) ; 45'-3 5/8" in drawing units
(setq *lfc-border-tol*   0.005)   ; 0.5% slack on both the scale and the aspect ratio
(setq *lfc-fgstep-words*          ; a fiberglass step shows up under any of these
      '("Fiberglass Step" "FG Step"))
;; a liner pattern field carrying one of these was never really filled
;; in ("Not Supplied", "#ERROR") - LINFINCHECK wipes it back to blank
(setq *lfc-badwords*     '("NOT" "ERROR"))
(setq *lfc-report-layer* "LINFINCHECK-REPORT")
(setq *lfc-report-color* 3)       ; green
(setq *lfc-zoom-margin*  0.75)    ; empty space around the zoomed item (fraction of its size)
(setq *lfc-report-chars* 45.0)    ; report column width, in text heights
(setq *lfc-ask-all-arc-ends* nil) ; T = confirm EVERY arc endpoint, even already-attached ones

;; entity types dimension points and arc ends may attach to
(setq *lfc-curve-types*
      '("LINE" "ARC" "CIRCLE" "ELLIPSE" "LWPOLYLINE" "POLYLINE" "SPLINE"))

;; --- safety: xdata tags, colour stash, layer locks -----------------

(defun lfc:regapp ()
  (if (not (tblsearch "APPID" "LINFINCHECK"))
    (regapp "LINFINCHECK")))

(defun lfc:xd (ent / g)
  ;; LINFINCHECK's xdata groups on ent, nil when none
  (setq g (assoc -3 (entget ent '("LINFINCHECK"))))
  (if g (cdadr g)))

(defun lfc:tag (ent kind / ed)
  ;; stamp a LINFINCHECK-created entity (report, marker line) so a rerun
  ;; or LINFINCHECKRESCUE can find and clear it
  (lfc:regapp)
  (setq ed (entget ent '("LINFINCHECK")))
  (if (and ed (not (assoc -3 ed)))
    (entmod (append ed (list (list -3 (list "LINFINCHECK" (cons 1000 kind))))))))

(defun lfc:stash-color (ent col / ed)
  ;; remember the entity's own colour in xdata so LINFINCHECKRESCUE can
  ;; put it back even after a crash; an existing stash (from an
  ;; interrupted run - the TRUE original) is never overwritten
  (lfc:regapp)
  (setq ed (entget ent '("LINFINCHECK")))
  (if (and ed (not (assoc -3 ed)))
    (entmod (append ed (list (list -3 (list "LINFINCHECK"
                                            '(1000 . "COLOR")
                                            (cons 1071 col))))))))

(defun lfc:unstash (ent / ed)
  ;; drop LINFINCHECK's xdata once the run has restored things itself
  (setq ed (entget ent '("LINFINCHECK")))
  (if (and ed (assoc -3 ed))
    (entmod (subst (list -3 (list "LINFINCHECK")) (assoc -3 ed) ed))))

(defun lfc:clear-old (/ ss2 i e xd n)
  ;; erase the report and marker lines left by an earlier LINFINCHECK
  ;; run, so a rerun replaces them instead of stacking on top
  (setq ss2 (ssget "_X" '((-3 ("LINFINCHECK")))) n 0 i 0)
  (if ss2
    (repeat (sslength ss2)
      (setq e  (ssname ss2 i)
            i  (1+ i)
            xd (lfc:xd e))
      (if (member (cdr (assoc 1000 xd)) '("REPORT" "XLINE"))
        (progn (entdel e) (setq n (1+ n))))))
  (if (> n 0)
    (princ (strcat "\n(Removed " (itoa n)
                   " report/marker item(s) from an earlier LINFINCHECK run.)"))))

(defun lfc:layer-locked-p (name / ld)
  (setq ld (tblsearch "LAYER" name))
  (and ld (= 4 (logand 4 (cdr (assoc 70 ld))))))

(defun lfc:set-layer-lock (name lock / ed old new)
  ;; set or clear a layer's locked flag; T when it actually changed
  (setq ed  (entget (tblobjname "LAYER" name))
        old (cdr (assoc 70 ed))
        new (if lock (logior old 4) (logand old (~ 4))))
  (if (/= old new)
    (progn (entmod (subst (cons 70 new) (assoc 70 ed) ed)) T)))

(defun lfc:dim-assoc-p (ent / found g)
  ;; T when the dimension carries persistent reactors - the mark of
  ;; an object-associative dim, whose definition points may re-anchor
  ;; on their own after being moved
  (foreach g (entget ent)
    (if (and (= 102 (car g)) (= "{ACAD_REACTORS" (cdr g)))
      (setq found T)))
  found)

(defun c:LINFINCHECKRESCUE ( / ss i e xd n)
  ;; the way out after a crash or interrupted run: puts back every
  ;; colour LINFINCHECK stashed (flag colours included) and removes its
  ;; report and marker lines
  (setq ss (ssget "_X" '((-3 ("LINFINCHECK")))) n 0 i 0)
  (if ss
    (repeat (sslength ss)
      (setq e  (ssname ss i)
            i  (1+ i)
            xd (lfc:xd e))
      (cond
        ((member (cdr (assoc 1000 xd)) '("REPORT" "XLINE"))
         (entdel e)
         (setq n (1+ n)))
        ((assoc 1071 xd)
         (lfc:set-color e (cdr (assoc 1071 xd)))
         (lfc:unstash e)
         (setq n (1+ n))))))
  (if (> n 0)
    (princ (strcat "\nLINFINCHECKRESCUE: restored or removed " (itoa n) " item(s)."))
    (princ "\nLINFINCHECKRESCUE: nothing to restore - no LINFINCHECK markers in the drawing."))
  (princ))

;; --- small helpers -------------------------------------------------

(defun lfc:ent-color (ent / c)
  ;; the entity's explicit colour, 256 (ByLayer) when it has none
  (setq c (cdr (assoc 62 (entget ent))))
  (if c c 256))

(defun lfc:set-color (ent color / ed old)
  (setq ed  (entget ent)
        old (assoc 62 ed))
  (entmod (if old
            (subst (cons 62 color) old ed)
            (append ed (list (cons 62 color)))))
  (entupd ent))

(defun lfc:make-xline (p1 p2 / len)
  ;; infinite construction line through p1-p2 on the check layer,
  ;; tagged so reruns and LINFINCHECKRESCUE can clear it
  (setq len (distance p1 p2))
  (if (and (> len 1e-8)
           (entmake (list '(0 . "XLINE")
                          '(100 . "AcDbEntity")
                          (cons 8 *lfc-constr-layer*)
                          '(100 . "AcDbXline")
                          (cons 10 p1)
                          (cons 11 (mapcar '(lambda (x) (/ x len))
                                           (mapcar '- p2 p1))))))
    (lfc:tag (entlast) "XLINE")))

(defun lfc:closest-on (ent pt / res)
  ;; closest point on ent to pt; nil when ent is not curve-like
  (setq res (vl-catch-all-apply 'vlax-curve-getClosestPointTo (list ent pt)))
  (if (vl-catch-all-error-p res) nil res))

(defun lfc:nearest-curve (pt exclude cands / best bestd cp d e)
  ;; (ent closest-point distance) for the candidate closest to pt
  (foreach e cands
    (if (and (not (eq e exclude)) (setq cp (lfc:closest-on e pt)))
      (progn
        (setq d (distance pt cp))
        (if (or (null bestd) (< d bestd))
          (setq bestd d
                best  (list e cp d))))))
  best)

(defun lfc:curve-ends (ent / cl sp ep)
  ;; the curve's two endpoints; nil when closed (or not a curve)
  (setq cl (vl-catch-all-apply 'vlax-curve-isClosed (list ent)))
  (if (or (vl-catch-all-error-p cl) cl)
    nil
    (progn
      (setq sp (vl-catch-all-apply 'vlax-curve-getStartPoint (list ent))
            ep (vl-catch-all-apply 'vlax-curve-getEndPoint (list ent)))
      (if (or (vl-catch-all-error-p sp) (vl-catch-all-error-p ep))
        nil
        (list sp ep)))))

(defun lfc:closest-of (pt pts / best bestd d q)
  (foreach q pts
    (setq d (distance pt q))
    (if (or (null bestd) (< d bestd)) (setq bestd d best q)))
  best)

(defun lfc:nearest-end (pt exclude cands / best bestd d e q)
  ;; closest endpoint over every open candidate curve
  (foreach e cands
    (if (not (eq e exclude))
      (foreach q (lfc:curve-ends e)
        (setq d (distance pt q))
        (if (or (null bestd) (< d bestd)) (setq bestd d best q)))))
  best)

(defun lfc:ptstr (p)
  (strcat "(" (rtos (car p) 2 4) ", " (rtos (cadr p) 2 4) ")"))

(defun lfc:zoom-ent (ent / bb p1 p2 m)
  ;; zoom the current view onto ent with some breathing room
  (setq bb (cal:bbox-ent ent))
  (if bb
    (progn
      (setq p1 (car bb)
            p2 (cadr bb)
            m  (* *lfc-zoom-margin*
                  (max (- (car p2) (car p1)) (- (cadr p2) (cadr p1)) 1e-6)))
      (command "_.ZOOM" "_Window"
               (trans (list (- (car p1) m) (- (cadr p1) m) 0.0) 0 1)
               (trans (list (+ (car p2) m) (+ (cadr p2) m) 0.0) 0 1)))))

(defun lfc:zoom-2ents (e1 e2 / b1 b2 p1 p2 m)
  ;; zoom onto the combined box of two entities
  (setq b1 (cal:bbox-ent e1)
        b2 (cal:bbox-ent e2))
  (cond
    ((and b1 b2)
     (setq p1 (list (min (caar b1) (caar b2))
                    (min (cadar b1) (cadar b2)))
           p2 (list (max (caadr b1) (caadr b2))
                    (max (cadadr b1) (cadadr b2)))
           m  (* *lfc-zoom-margin*
                 (max (- (car p2) (car p1)) (- (cadr p2) (cadr p1)) 1e-6)))
     (command "_.ZOOM" "_Window"
              (trans (list (- (car p1) m) (- (cadr p1) m) 0.0) 0 1)
              (trans (list (+ (car p2) m) (+ (cadr p2) m) 0.0) 0 1)))
    (b1 (lfc:zoom-ent e1))
    (b2 (lfc:zoom-ent e2))))

(defun lfc:stage (ent saved keep)
  ;; bring an entity back to its own colour for review — unless it
  ;; already wears a LINFINCHECK marker colour it must not lose
  (if (and (entget ent) (not (member ent keep)))
    (lfc:set-color ent (cdr (assoc ent saved)))))

(defun lfc:unstage (ent keep)
  ;; send a reviewed entity back into the grey background
  (if (and (entget ent) (not (member ent keep)))
    (lfc:set-color ent *lfc-grey-color*)))

(defun lfc:mark-x (pt col / p s)
  ;; diagonal cross - marks WHERE YOU DREW IT
  (setq p (trans pt 0 1)
        s (* 0.02 (getvar "VIEWSIZE")))
  (grdraw (list (- (car p) s) (- (cadr p) s)) (list (+ (car p) s) (+ (cadr p) s)) col 1)
  (grdraw (list (- (car p) s) (+ (cadr p) s)) (list (+ (car p) s) (- (cadr p) s)) col 1))

(defun lfc:mark-plus (pt col / p s)
  ;; upright cross - marks WHERE LINFINCHECK WOULD PUT IT
  (setq p (trans pt 0 1)
        s (* 0.02 (getvar "VIEWSIZE")))
  (grdraw (list (- (car p) s) (cadr p)) (list (+ (car p) s) (cadr p)) col 1)
  (grdraw (list (car p) (- (cadr p) s)) (list (car p) (+ (cadr p) s)) col 1))

(defun lfc:mark-point (pt)
  ;; both strokes, for a point that is simply being pointed out
  (lfc:mark-x pt 2)
  (lfc:mark-plus pt 2))

(defun lfc:progress (what n total)
  (princ (strcat "\r  [" (itoa n) "/" (itoa total) "] " what "          ")))

(defun lfc:confirm-move (label orig sugg / ans newp)
  ;; The point has been put where LINFINCHECK thinks it belongs, but BOTH
  ;; spots are marked and spelled out so there is no doubt which is
  ;; which: a red X where you drew it, a green + where we would move
  ;; it, joined by a line. Returns
  ;;   'move - take our suggestion
  ;;   'keep - put it back exactly where you drew it
  ;;   <point> - a spot you picked yourself (current UCS)
  (lfc:mark-x    orig *lfc-orig-color*)
  (lfc:mark-plus sugg *lfc-sugg-color*)
  (if (> (distance orig sugg) 1e-8)
    (grdraw (trans orig 0 1) (trans sugg 0 1) *lfc-sugg-color* 1))
  (princ (strcat "\n  " label " - which spot is right?"
                 "\n    Keep = where you drew it   " (lfc:ptstr orig)
                 "  (red X)"
                 "\n    Move = onto nearest object " (lfc:ptstr sugg)
                 "  (green +), " (rtos (distance orig sugg) 2 4) " away"
                 "\n    Pick = somewhere else you point at"))
  (initget "Move Keep Pick")
  (setq ans (getkword
              "\n  [Move/Keep/Pick] <Move>: "))
  (cond
    ((or (null ans) (= ans "Move")) 'move)
    ((= ans "Keep") 'keep)
    (t (setq newp (getpoint (strcat "\n  Pick the spot for " label
                                    " <Move to the green +>: ")))
       (if newp newp 'move))))

(defun lfc:mtext (ins height width text layer / e)
  ;; entmake an MTEXT, splitting text into 250-char DXF chunks
  (if (setq e (cal:mtext ins height width text layer))
    (lfc:tag e "REPORT")))

(defun lfc:border-box (ss / i e ed bb lo hi)
  ;; overall extents of everything on the border layer, so a frame
  ;; drawn as one polyline and one drawn as four separate lines both
  ;; measure the same
  (setq i 0)
  (if ss
    (repeat (sslength ss)
      (setq e  (ssname ss i)
            i  (1+ i)
            ed (entget e))
      (if (and ed
               (= (strcase (cdr (assoc 8 ed))) (strcase *lfc-border-layer*))
               (setq bb (cal:bbox-ent e)))
        (setq lo (if lo
                   (list (min (car lo) (caar bb)) (min (cadr lo) (cadar bb)))
                   (list (caar bb) (cadar bb)))
              hi (if hi
                   (list (max (car hi) (caadr bb)) (max (cadr hi) (cadadr bb)))
                   (list (caadr bb) (cadadr bb)))))))
  (if (and lo hi) (list lo hi)))

(defun lfc:border-verdict (bb / bw bh sw sh sc)
  ;; measure the border against the nominal sheet. Returns the report
  ;; sentence; the drawing may be the nominal size or any scaled-UP
  ;; multiple of it, but never smaller.
  (if (null bb)
    (strcat "NO BORDER found on layer '" *lfc-border-layer* "'")
    (progn
      (setq bw (- (car (cadr bb)) (car (car bb)))
            bh (- (cadr (cadr bb)) (cadr (car bb))))
      (if (or (<= bw 1e-6) (<= bh 1e-6))
        "border has no measurable size"
        (progn
          (setq sw (/ bw *lfc-border-w*)
                sh (/ bh *lfc-border-h*)
                sc (min sw sh))
          (cond
            ;; a border out of proportion is wrong whatever its size
            ((> (abs (- sw sh)) (* *lfc-border-tol* (max sw sh)))
             (strcat (rtos bw) " x " (rtos bh) " - STRETCHED out of proportion ("
                     (rtos sw 2 3) "x wide but " (rtos sh 2 3)
                     "x tall); nominal is " (rtos *lfc-border-w*) " x "
                     (rtos *lfc-border-h*)))
            ;; the one the user asked for by name
            ((< sc (- 1.0 *lfc-border-tol*))
             (strcat (rtos bw) " x " (rtos bh) " is only " (rtos sc 2 3)
                     "x the nominal " (rtos *lfc-border-w*) " x "
                     (rtos *lfc-border-h*)
                     " - Title block should not be SCALED DOWN for Liners"))
            ((< sc (+ 1.0 *lfc-border-tol*))
             (strcat (rtos bw) " x " (rtos bh) " - nominal size, OK"))
            (t
             (strcat (rtos bw) " x " (rtos bh) " - " (rtos sc 2 3)
                     "x the nominal size, OK"))))))))

(defun lfc:attn-p (s)
  ;; T when a report line describes something questionable or that
  ;; needs looking over / fixing, so the report renders it in red
  (wcmatch (strcase s)
    "*FLAGGED*,*WRONG*,*SKIPPED*,*MAGENTA*,*MISSING*,*NOTHING*,*NO SIDE VIEW*,*NO 'STEP*,*NO BLOCK*,*WORD NOT*,*WORD ERROR*,* ADD *,*MISMATCH*,*NOT CONFIRMED*,*NOT ATTACHED*,*OVERLAP*,*CHECK THE WALL HEIGHT*,*FIBERGLASS STEP*,*ASSOCIATIVE*,*DISAGREE*,*SCALED DOWN*,*STRETCHED*,*NO BORDER*,*WIPED*,*NEEDS WIPING*,*NONSENSICAL*,*EXPECTED MM/DD/YYYY*,*NO INCHES*,*NOT TODAY*"))

(defun lfc:red (s)
  ;; wrap an MTEXT run so it renders in the flag colour, reverting
  ;; to the surrounding colour after (braces scope the change)
  (strcat "{\\C" (itoa *lfc-flag-color*) ";" s "}"))

(defun lfc:small (s)
  ;; all-clear text renders at *lfc-green-scale* of the height the
  ;; red attention text gets, so problems stand out on the sheet
  (strcat "{\\H" (rtos *lfc-green-scale* 2 4) "x;" s "}"))

(defun lfc:big (s)
  ;; the report's title line: half again the base height
  (strcat "{\\H1.5x;" s "}"))

(defun lfc:hdg (s)
  ;; a section heading: underlined, with a thin blank line above it
  ;; so the sections read as blocks (the \P inside the first group is
  ;; a paragraph break at 0.4x height - a narrow gap, not a full line)
  (strcat "{\\H0.4x;\\P}{\\L" s "}"))

(defun lfc:linegrp (s)
  ;; which underlined section a report line files under, keyed on the
  ;; fixed prefixes the review gives its lines
  (cond ((wcmatch s "Dim *,Dimensions:*") "DIMENSIONS")
        ((wcmatch s "Arc *")              "ARCS")
        ((wcmatch s "Lines *")            "OVERLAPPING LINES")
        ((wcmatch s "Steps:*,Step Attachment*,Bead Track:*")
         "STEPS & SIDE VIEWS")
        ((wcmatch s "Height dim *,*CHECK THE WALL HEIGHT*")
         "WALL HEIGHT")
        ((wcmatch s "Liner Material*")    "THE LINER")
        ((wcmatch s "Text *")             "TEXT & UNITS")
        (t                                "OTHER CHECKS")))

(defun lfc:dimline-p (s)
  ;; T for a line that belongs to the DIMENSION AUDIT column - the
  ;; DIMCHECK-style findings, as opposed to the liner's own checks
  (member (lfc:linegrp s) '("DIMENSIONS" "ARCS" "OVERLAPPING LINES")))

;; Every dimension belongs on the dimension layer.  This is the one
;; dimension check the lite scan keeps: it costs a layer read apiece,
;; and a sheet whose dimensions sit on the wrong layer plots wrong
;; however sound the dimensions themselves are - so the verdict, and
;; the suggestion to run CDIM over them, belong on the main sheet
;; rather than in the DIMENSION AUDIT column.  The offending layers
;; are named, since that is what you need to go fix them.
;; Returns (sentence . needs-attention).
(defun lfc:dimlayer-verdict (dims / n off lays lay e)
  (setq n 0 off 0 lays nil)
  (foreach e dims
    (if (entget e)
      (progn
        (setq n   (1+ n)
              lay (cdr (assoc 8 (entget e))))
        (if (/= (strcase lay) (strcase *lfc-dim-layer*))
          (progn
            (setq off (1+ off))
            (if (not (member (strcase lay) lays))
              (setq lays (cons (strcase lay) lays))))))))
  (cond
    ((= n 0)
     (cons "no dimensions in the selection" nil))
    ((= off 0)
     (cons (strcat "all " (itoa n) " on " *lfc-dim-layer*) nil))
    (t
     (cons (strcat (itoa off) " of " (itoa n) " NOT on layer "
                   *lfc-dim-layer* " ("
                   (lfc:join (reverse lays) ", ")
                   ") - run " *lfc-dimfix-cmd* " to move them")
           T))))

;; --- feet-and-inch text ----------------------------------------------
;; A distance written in feet must state its inches too: 5' is wrong,
;; 5'-0" (or 5'-0'') is right, and a plain 40" is right as it stands.
;;
;; A FEET MARK is an apostrophe standing straight after a DIGIT, and
;; that is what keeps prose out of this: "Water's Edge", "Owner's" and
;; "don't" are possessives, not measurements, and are never flagged.
;; Two apostrophes together are the inch mark AutoCAD text often uses
;; in place of ", so 5'-0'' closes exactly as 5'-0" does.
;;
;; T when some feet mark in s is never closed by an inch mark before
;; the next feet mark or the end of the string -- so "5' and 7'-0"" is
;; caught on its first value while "3'-2"" passes.
(defun lfc:feet-open-p (s / lst n i c prev open found)
  (setq lst   (vl-string->list s)
        n     (length lst)
        i     0
        prev  0
        open  nil
        found nil)
  (while (< i n)
    (setq c (nth i lst))
    (cond
      ((= c 34)                                    ; " closes it
       (setq open nil i (1+ i)))
      ((and (= c 39) (< (1+ i) n) (= (nth (1+ i) lst) 39))
       (setq open nil i (+ i 2)))                  ; '' closes it too
      ((and (= c 39) (>= prev 48) (<= prev 57))    ; digit then ' = feet
       (if open (setq found T))                    ; the one before never closed
       (setq open T i (1+ i)))
      (t (setq i (1+ i))))
    (setq prev (nth (1- i) lst)))
  (or found open))

;; MTEXT reads \, { and } as formatting, so a snippet quoted out of the
;; drawing has them blanked before it goes anywhere near the report.
(defun lfc:mtsafe (s)
  (vl-list->string
    (mapcar '(lambda (c) (if (member c '(92 123 125)) 32 c))
            (vl-string->list s))))

;; The text an entity carries: TEXT and ATTRIB keep it in group 1,
;; MTEXT spills the overflow into group 3 chunks ahead of that.
(defun lfc:ent-text (ent / ed g head tail)
  (setq ed (entget ent) head "" tail "")
  (foreach g ed
    (cond ((= 3 (car g)) (setq head (strcat head (cdr g))))
          ((= 1 (car g)) (setq tail (cdr g)))))
  (strcat head tail))

;; Every text box in the selection: TEXT and MTEXT, plus the ATTRIB
;; values on blocks -- the parts of a block someone types into.  Text
;; baked into a block DEFINITION is left alone: it reads the same on
;; every insert and is not fixable from this drawing.
;; Returns ((handle . string) ...).
(defun lfc:text-items (ss / i e ed et out a ad)
  (setq i 0)
  (if ss
    (repeat (sslength ss)
      (setq e  (ssname ss i)
            i  (1+ i)
            ed (entget e)
            et (if ed (cdr (assoc 0 ed))))
      (cond
        ((member et '("TEXT" "MTEXT"))
         (setq out (cons (cons (cdr (assoc 5 ed)) (lfc:ent-text e)) out)))
        ((and (= et "INSERT") (assoc 66 ed) (= 1 (cdr (assoc 66 ed))))
         (setq a (entnext e))
         (while (and a (setq ad (entget a)) (= "ATTRIB" (cdr (assoc 0 ad))))
           (setq out (cons (cons (cdr (assoc 5 ad)) (lfc:ent-text a)) out)
                 a   (entnext a)))))))
  (reverse out))

;; The verdict over every text box, plus one report line per offender.
;; Returns (sentence needs-attention (line ...)).
(defun lfc:audit-units (ss / items it s n bad lines)
  (setq items (lfc:text-items ss) n 0 bad 0 lines nil)
  (foreach it items
    (setq s (cdr it))
    (if (and s (/= s ""))
      (progn
        (setq n (1+ n))
        (if (lfc:feet-open-p s)
          (setq bad   (1+ bad)
                lines (cons (strcat "Text " (car it) ": \""
                                    (lfc:mtsafe (lfc:clip s 40))
                                    "\" gives feet with NO INCHES"
                                    " - write it 5'-0\" not 5'")
                            lines))))))
  (list
    (cond
      ((= n 0) "no text in the selection")
      ((= bad 0) (strcat "all " (itoa n) " text item"
                         (if (= 1 n) "" "s") " OK"))
      (t (strcat (itoa bad) " of " (itoa n) " text item"
                 (if (= 1 n) "" "s") " give feet with NO INCHES"
                 " - write 5'-0\" not 5'")))
    (> bad 0)
    (reverse lines)))

;; The whole report: the liner-finish checks on the MAIN sheet - a
;; large title, the date and version, a verdict line, the colour
;; legend, a SUMMARY dashboard, then the findings under underlined
;; headings - and the DIMCHECK-style findings (dimensions, arcs,
;; overlapping lines) in a DIMENSION AUDIT column to its right.  A
;; lite run writes the main sheet alone.
;;   title   the report's big first line ("LINFINCHECK REPORT", ...)
;;   note    extra legend sentence(s) up front, or nil
;;   hdr     (text . attn) pairs for the SUMMARY dashboard
;;   dhdr    (text . attn) pairs for the dimension column's dashboard
;;   lines   every finding line, report order
;;   lite    T = skip the dimension column
;; Returns the x of the report's right edge, for the caller's zoom.
(defun lfc:write-report (title note hdr dhdr lines lite
                         minx miny maxx maxy
                         / mainl diml l pr nred nmain ndim nlin grps grp
                           ref h ins ins2 txt right)
  (cal:ensure-layer *lfc-report-layer* *lfc-report-color*)
  (foreach l lines
    (if (lfc:dimline-p l)
      (setq diml (cons l diml))
      (setq mainl (cons l mainl))))
  (setq mainl (reverse mainl)
        diml  (reverse diml))
  ;; the verdict counts every line that will render red, either column
  (setq nred 0)
  (foreach pr (append hdr dhdr)
    (if (cdr pr) (setq nred (1+ nred))))
  (foreach l lines
    (if (lfc:attn-p l) (setq nred (1+ nred))))
  ;; sizing: weighted line count per column - the head is ~4.5 lines,
  ;; a heading is a line plus its 0.4 gap - and the taller column
  ;; drives the text height, clamped as before
  (setq nmain 4.5 grps nil)
  (foreach l mainl
    (if (not (member (lfc:linegrp l) grps))
      (setq grps (cons (lfc:linegrp l) grps))))
  (setq nmain (+ nmain (* 1.4 (1+ (length grps)))))   ; SUMMARY + sections
  (setq nmain (+ nmain (* (length hdr) *lfc-green-scale*)))
  (foreach l mainl
    (setq nmain (+ nmain (if (lfc:attn-p l) 1.0 *lfc-green-scale*))))
  (setq ndim 0.0)
  (if (not lite)
    (progn
      (setq ndim 2.5 grps nil)                        ; column title + legend
      (foreach l diml
        (if (not (member (lfc:linegrp l) grps))
          (setq grps (cons (lfc:linegrp l) grps))))
      (setq ndim (+ ndim (* 1.4 (length grps))))
      (setq ndim (+ ndim (* (length dhdr) *lfc-green-scale*)))
      (foreach l diml
        (setq ndim (+ ndim (if (lfc:attn-p l) 1.0 *lfc-green-scale*))))))
  (setq nlin (max nmain ndim))
  (if (and minx (> (max (- maxy miny) (- maxx minx)) 1e-8))
    (progn
      (setq ref (max (- maxy miny) (* 0.25 (- maxx minx)))
            h   (/ ref (* 1.66 nlin)))
      (if (> h (/ ref 30.0))  (setq h (/ ref 30.0)))
      (if (< h (/ ref 200.0)) (setq h (/ ref 200.0))))
    (progn
      (setq h (* (getvar "DIMTXT") (getvar "DIMSCALE")))
      (if (or (null h) (<= h 0.0)) (setq h 2.5))))
  (setq ins (if minx
              (list (+ maxx (* 0.05 (max (- maxx minx) 1.0))) maxy 0.0)
              (list 0.0 0.0 0.0)))
  ;; --- the main sheet
  (setq txt (strcat (lfc:big title)
                    "\\P"
                    (lfc:small (strcat (cal:datestr)
                                       "  -  LINFINCHECK "
                                       *lfc-version*))
                    "\\P"
                    "{\\H1.2x;"
                    (if (> nred 0)
                      (lfc:red (strcat (itoa nred) " LINE"
                                       (if (= 1 nred) "" "S")
                                       " NEED"
                                       (if (= 1 nred) "S" "")
                                       " ATTENTION"))
                      "ALL CLEAR - every check passed")
                    "}"
                    "\\P"
                    (lfc:small
                      (strcat (if note note "")
                              "Lines needing attention are in "
                              (lfc:red "red")
                              " at full size; lines that checked out"
                              " are smaller."))))
  (setq txt (strcat txt "\\P" (lfc:hdg "SUMMARY")))
  (foreach pr hdr
    (setq txt (strcat txt "\\P"
                      (if (cdr pr)
                        (lfc:red (strcat "  " (car pr)))
                        (lfc:small (strcat "  " (car pr)))))))
  (setq grp nil)
  (foreach l mainl
    (if (/= grp (lfc:linegrp l))
      (setq grp (lfc:linegrp l)
            txt (strcat txt "\\P" (lfc:hdg grp))))
    (setq txt (strcat txt "\\P"
                      (if (lfc:attn-p l)
                        (lfc:red (strcat "  " l))
                        (lfc:small (strcat "  " l))))))
  (lfc:mtext ins h (* *lfc-report-chars* h) txt *lfc-report-layer*)
  (setq right (+ (car ins) (* *lfc-report-chars* h)))
  ;; --- the DIMENSION AUDIT column
  (if (not lite)
    (progn
      (setq ins2 (list (+ (car ins) (* (+ *lfc-report-chars* 2.0) h))
                       (cadr ins) 0.0)
            txt  (strcat "{\\H1.2x;DIMENSION AUDIT}"
                         "\\P"
                         (lfc:small
                           (strcat "Dimensions, arcs and overlapping"
                                   " lines - DIMCHECK's ground, kept"
                                   " off the main sheet."))))
      (foreach pr dhdr
        (setq txt (strcat txt "\\P"
                          (if (cdr pr)
                            (lfc:red (strcat "  " (car pr)))
                            (lfc:small (strcat "  " (car pr)))))))
      (setq grp nil)
      (foreach l diml
        (if (/= grp (lfc:linegrp l))
          (setq grp (lfc:linegrp l)
                txt (strcat txt "\\P" (lfc:hdg grp))))
        (setq txt (strcat txt "\\P"
                          (if (lfc:attn-p l)
                            (lfc:red (strcat "  " l))
                            (lfc:small (strcat "  " l))))))
      (lfc:mtext ins2 h (* *lfc-report-chars* h) txt *lfc-report-layer*)
      (setq right (+ (car ins2) (* *lfc-report-chars* h)))))
  right)

;; --- geometry ------------------------------------------------------

(defun lfc:planar-arc-p (ed / n)
  ;; only arcs drawn in the world XY plane are handled
  (setq n (cdr (assoc 210 ed)))
  (or (null n)
      (and (< (abs (car n)) 1e-9)
           (< (abs (cadr n)) 1e-9)
           (> (caddr n) 0.0))))

(defun lfc:rebuild-arc (ent which fixed mid target / c r a1 a2 am tmp ed pair)
  ;; re-fit the arc through its fixed end, its old midpoint and the
  ;; target point; returns T on success
  (if (and (> (distance target fixed) 1e-8)
           (setq c (cal:circumcenter fixed mid target)))
    (progn
      (setq r  (distance c target)
            a1 (angle c (if (eq which 'start) target fixed))
            a2 (angle c (if (eq which 'start) fixed target))
            am (angle c mid))
      ;; ARC entities always sweep counter-clockwise from start to
      ;; end; keep the sweep that contains the old midpoint
      (if (> (cal:angnorm (- am a1)) (cal:angnorm (- a2 a1)))
        (setq tmp a1
              a1  a2
              a2  tmp))
      (setq ed (entget ent))
      (foreach pair (list (cons 10 c) (cons 40 r) (cons 50 a1) (cons 51 a2))
        (setq ed (subst pair (assoc (car pair) ed) ed)))
      (if (entmod ed)
        (progn (entupd ent) T)))))

(defun lfc:move-arc-end (ent which target / mid other)
  ;; re-fit the arc so the chosen endpoint lands on target (WCS)
  (setq mid   (vlax-curve-getPointAtDist
                ent
                (/ (vlax-curve-getDistAtParam ent (vlax-curve-getEndParam ent)) 2.0))
        other (if (eq which 'start)
                (vlax-curve-getEndPoint ent)
                (vlax-curve-getStartPoint ent)))
  (lfc:rebuild-arc ent which other mid target))

(defun lfc:overlap-info (la lb / a1 a2 b1 b2 u lena s1 s2 tmp lo hi)
  ;; when segments la and lb are collinear (within *lfc-olap-fuzz*)
  ;; and run on top of each other for more than *lfc-tol*, returns
  ;;   (ov-start ov-end ov-length union-start union-end)
  ;; nil when they do not overlap (touching end-to-end is fine)
  (setq a1 (lfc:seg-p1 la)
        a2 (lfc:seg-p2 la)
        b1 (lfc:seg-p1 lb)
        b2 (lfc:seg-p2 lb)
        u  (cal:unitn (mapcar '- a2 a1)))
  (if (and u
           (<= (cal:pt-line-dist b1 a1 u) *lfc-olap-fuzz*)
           (<= (cal:pt-line-dist b2 a1 u) *lfc-olap-fuzz*))
    (progn
      (setq lena (distance a1 a2)
            s1   (cal:proj-param b1 a1 u)
            s2   (cal:proj-param b2 a1 u))
      (if (> s1 s2) (setq tmp s1 s1 s2 s2 tmp))
      (setq lo (max 0.0 s1)
            hi (min lena s2))
      (if (> (- hi lo) *lfc-tol*)
        (list (cal:axis-pt a1 u lo)
              (cal:axis-pt a1 u hi)
              (- hi lo)
              (cal:axis-pt a1 u (min 0.0 s1))
              (cal:axis-pt a1 u (max lena s2)))))))

(defun lfc:merge-lines (la lb info / ed)
  ;; stretch la's LINE over the union of both, delete lb's LINE
  (setq ed (entget (lfc:seg-ent la))
        ed (subst (cons 10 (nth 3 info)) (assoc 10 ed) ed)
        ed (subst (cons 11 (nth 4 info)) (assoc 11 ed) ed))
  (entmod ed)
  (entupd (lfc:seg-ent la))
  (entdel (lfc:seg-ent lb)))

(defun lfc:whole-line-p (s / ed)
  ;; T when the segment IS its owner entity - only whole LINEs can be
  ;; merged; a polyline edge has to be fixed by hand
  (setq ed (entget (lfc:seg-ent s)))
  (= "LINE" (cdr (assoc 0 ed))))

(defun lfc:find-overlaps (segs / atol fams a placed fam recs e p1 p2 dx dy
                                off s1 s2 tmp rest r q pairs seen key)
  ;; every overlapping segment pair, without comparing all pairs:
  ;; segments are bucketed by direction, then swept in offset order so
  ;; only genuinely collinear neighbours are ever tested. Segments of
  ;; the same entity are skipped (a polyline meeting itself is not a
  ;; duplicate), as are pairs already found through another segment.
  (setq atol  (* 0.5 (/ pi 180.0))              ; 0.5 deg is ample at this fuzz
        fams  nil
        pairs nil
        seen  nil)
  (foreach e segs
    (setq a      (lfc:seg-dir-ang e)
          placed nil)
    (foreach fam fams
      (if (and (not placed)
               (or (<= (cal:ang-diff a (car fam)) atol)))
        (setq fams   (subst (cons (car fam) (cons e (cdr fam))) fam fams)
              placed T)))
    (if (not placed) (setq fams (cons (list a e) fams))))
  (foreach fam fams
    (if (cdr (cdr fam))                          ; two or more to compare
      (progn
        (setq a  (car fam)
              dx (cos a)
              dy (sin a)
              recs nil)
        (foreach e (cdr fam)
          (setq p1  (lfc:seg-p1 e)
                p2  (lfc:seg-p2 e)
                off (- (* (cadr p1) dx) (* (car p1) dy))
                s1  (+ (* (car p1) dx) (* (cadr p1) dy))
                s2  (+ (* (car p2) dx) (* (cadr p2) dy)))
          (if (> s1 s2) (setq tmp s1 s1 s2 s2 tmp))
          (setq recs (cons (list off s1 s2 e) recs)))
        (setq recs (lfc:sort-recs recs))
        ;; sorted by offset: only sweep forward while still collinear
        (while recs
          (setq r    (car recs)
                rest (cdr recs))
          (while (and rest
                      (<= (- (car (car rest)) (car r)) *lfc-olap-fuzz*))
            (setq q (car rest))
            (if (and (not (eq (lfc:seg-ent (cadddr r))
                              (lfc:seg-ent (cadddr q))))
                     ;; spans must actually meet before the exact test
                     (> (min (caddr r) (caddr q)) (max (cadr r) (cadr q)))
                     (lfc:overlap-info (cadddr r) (cadddr q)))
              (progn
                (setq key (list (lfc:seg-ent (cadddr r))
                                (lfc:seg-ent (cadddr q))))
                (if (not (member key seen))
                  (setq seen  (cons key (cons (reverse key) seen))
                        pairs (cons (list (cadddr r) (cadddr q)) pairs)))))
            (setq rest (cdr rest)))
          (setq recs (cdr recs))))))
  (reverse pairs))

;; --- step pattern detection ----------------------------------------

;; --- segments: lines AND polyline edges ----------------------------
;; Detection works on "segs" - (start end owner-entity) records - so a
;; side view or a run of steps drawn as one polyline counts exactly
;; like the same shape drawn as separate LINEs.

(defun lfc:seg-p1 (s) (car s))
(defun lfc:seg-p2 (s) (cadr s))
(defun lfc:seg-ent (s) (caddr s))

(defun lfc:ocs->wcs (p nz)
  (if (and nz (not (equal nz '(0.0 0.0 1.0) 1e-9))) (trans p nz 0) p))

(defun lfc:lwpoly-segs (ent / ed nz elev vs bl cls n i segs g)
  ;; straight edges of an LWPOLYLINE; bulged (arc) edges are skipped
  (setq ed   (entget ent)
        nz   (cdr (assoc 210 ed))
        elev (cdr (assoc 38 ed))
        cls  (= 1 (logand 1 (cdr (assoc 70 ed))))
        vs   nil
        bl   nil)
  (if (null elev) (setq elev 0.0))
  (foreach g ed
    (cond
      ((= 10 (car g))
       (setq vs (cons (lfc:ocs->wcs (list (car (cdr g)) (cadr (cdr g)) elev) nz) vs)
             bl (cons 0.0 bl)))
      ((= 42 (car g))
       (if bl (setq bl (cons (cdr g) (cdr bl)))))))
  (setq vs (reverse vs)
        bl (reverse bl)
        n  (length vs)
        i  0)
  (while (< i (1- n))
    (if (equal 0.0 (nth i bl) 1e-12)
      (setq segs (cons (list (nth i vs) (nth (1+ i) vs) ent) segs)))
    (setq i (1+ i)))
  (if (and cls (> n 2) (equal 0.0 (nth (1- n) bl) 1e-12))
    (setq segs (cons (list (nth (1- n) vs) (car vs) ent) segs)))
  segs)

(defun lfc:heavy-poly-segs (ent / e ed vs bl cls n i segs)
  ;; straight edges of an old-style POLYLINE (VERTEX entities)
  (setq cls (= 1 (logand 1 (cdr (assoc 70 (entget ent)))))
        e   (entnext ent)
        vs  nil
        bl  nil)
  (while (and e (= "VERTEX" (cdr (assoc 0 (setq ed (entget e))))))
    (if (zerop (logand 16 (cdr (assoc 70 ed))))    ; skip spline frame points
      (setq vs (cons (cdr (assoc 10 ed)) vs)
            bl (cons (if (assoc 42 ed) (cdr (assoc 42 ed)) 0.0) bl)))
    (setq e (entnext e)))
  (setq vs (reverse vs)
        bl (reverse bl)
        n  (length vs)
        i  0)
  (while (< i (1- n))
    (if (equal 0.0 (nth i bl) 1e-12)
      (setq segs (cons (list (nth i vs) (nth (1+ i) vs) ent) segs)))
    (setq i (1+ i)))
  (if (and cls (> n 2) (equal 0.0 (nth (1- n) bl) 1e-12))
    (setq segs (cons (list (nth (1- n) vs) (car vs) ent) segs)))
  segs)

(defun lfc:ent-segs (ent / ed et)
  ;; every straight segment an entity contributes, in WCS
  (setq ed (entget ent)
        et (cdr (assoc 0 ed)))
  (cond
    ((= et "LINE")       (list (list (cdr (assoc 10 ed)) (cdr (assoc 11 ed)) ent)))
    ((= et "LWPOLYLINE") (lfc:lwpoly-segs ent))
    ((= et "POLYLINE")   (lfc:heavy-poly-segs ent))))

(defun lfc:collect-segs (ents / segs e s)
  ;; all straight segments of a list of entities, longer than the
  ;; attachment tolerance (zero-length stubs help nothing)
  (foreach e ents
    (if (entget e)
      (foreach s (lfc:ent-segs e)
        (if (> (distance (car s) (cadr s)) *lfc-tol*)
          (setq segs (cons s segs))))))
  (reverse segs))

(defun lfc:group-ents (g / out e s)
  ;; the distinct entities a group's segments belong to
  (foreach s (cdr g)
    (setq e (lfc:seg-ent s))
    (if (not (member e out)) (setq out (cons e out))))
  (reverse out))

(defun lfc:seg-dir-ang (s / a)
  ;; segment direction folded into [0, pi)
  (setq a (angle (lfc:seg-p1 s) (lfc:seg-p2 s)))
  (if (>= a pi) (- a pi) a))

(defun lfc:sort-recs (recs / out r pre rest)
  ;; stable insertion sort by (car rec); keeps equal elements
  (setq out nil)
  (foreach r recs
    (setq pre  nil
          rest out)
    (while (and rest (>= (car r) (caar rest)))
      (setq pre  (cons (car rest) pre)
            rest (cdr rest)))
    (setq out (append (reverse pre) (list r) rest)))
  out)

(defun lfc:step-groups (lns minlines / atol fams a placed recs pts p1 p2 dx dy
                             off s1 s2 tmp cur chains gap groups e fam r)
  ;; hunt for step-like patterns: minlines or more parallel LINEs
  ;; stacked less than *lfc-step-maxgap* apart, each sideways-
  ;; overlapping the one before it (like stair treads).
  ;; Returns a list of groups, each (direction-angle ent ent ...)
  ;; ordered bottom tread to top.
  (setq atol   (* *lfc-step-angtol* (/ pi 180.0))
        fams   nil
        groups nil)
  ;; bucket the segments into parallel families
  (foreach e lns
    (progn
      (setq a      (lfc:seg-dir-ang e)
            placed nil)
      (foreach fam fams
        (if (and (not placed) (<= (cal:ang-diff a (car fam)) atol))
          (setq fams   (subst (cons (car fam) (cons e (cdr fam))) fam fams)
                placed T)))
      (if (not placed)
        (setq fams (cons (list a e) fams)))))
  ;; inside each family, sort by sideways offset and chain the stack
  (foreach fam fams
    (if (>= (length (cdr fam)) minlines)
      (progn
        (setq a    (car fam)
              dx   (cos a)
              dy   (sin a)
              recs nil)
        (foreach e (cdr fam)
          (setq p1  (lfc:seg-p1 e)
                p2  (lfc:seg-p2 e)
                off (- (* (cadr p1) dx) (* (car p1) dy))
                s1  (+ (* (car p1) dx) (* (cadr p1) dy))
                s2  (+ (* (car p2) dx) (* (cadr p2) dy)))
          (if (> s1 s2) (setq tmp s1 s1 s2 s2 tmp))
          (setq recs (cons (list off s1 s2 e) recs)))
        (setq recs (lfc:sort-recs recs))
        ;; cur = (ents distinct-tread-count span-lo span-hi last-off)
        (setq cur nil chains nil)
        (foreach r recs
          (cond
            ((null cur)
             (setq cur (list (list (cadddr r)) 1 (cadr r) (caddr r) (car r))))
            (t
             (setq gap (- (car r) (nth 4 cur)))
             (cond
               ((<= gap *lfc-tol*)           ; same tread drawn in pieces
                (setq cur (list (cons (cadddr r) (car cur))
                                (cadr cur)
                                (min (nth 2 cur) (cadr r))
                                (max (nth 3 cur) (caddr r))
                                (car r))))
               ;; next tread: plan-view treads overlap sideways, but in
               ;; a side view consecutive risers only touch corner to
               ;; corner (a zigzag), so allow a sideways gap up to one
               ;; tread depth as well
               ((and (<= gap *lfc-step-maxgap*)
                     (<= (- (max (nth 2 cur) (cadr r))
                            (min (nth 3 cur) (caddr r)))
                         *lfc-step-maxgap*))
                (setq cur (list (cons (cadddr r) (car cur))
                                (1+ (cadr cur))
                                (cadr r)
                                (caddr r)
                                (car r))))
               (t                             ; stack broken
                (if (>= (cadr cur) minlines)
                  (setq chains (cons (cons a (reverse (car cur))) chains)))
                (setq cur (list (list (cadddr r)) 1 (cadr r) (caddr r) (car r))))))))
        (if (and cur (>= (cadr cur) minlines))
          (setq chains (cons (cons a (reverse (car cur))) chains)))
        (setq groups (append groups (reverse chains))))))
  groups)

(defun lfc:staircase-p (g / a dx dy recs e pts p1 p2 off s1 s2 tmp
                           merged r prev sign d ov shorter ok)
  ;; T when the group's members march along like a stair or bench
  ;; profile - each tread shifted to the next, touching or barely
  ;; overlapping it - rather than sitting squarely on top of one
  ;; another like the two long sides of a rectangle, or nested like
  ;; plan-view step outlines. This is what separates a real side
  ;; view from any two parallel lines that happen to be close.
  (setq a    (car g)
        dx   (cos a)
        dy   (sin a)
        recs nil)
  (foreach e (cdr g)
    (setq p1  (lfc:seg-p1 e)
          p2  (lfc:seg-p2 e)
          off (- (* (cadr p1) dx) (* (car p1) dy))
          s1  (+ (* (car p1) dx) (* (cadr p1) dy))
          s2  (+ (* (car p2) dx) (* (cadr p2) dy)))
    (if (> s1 s2) (setq tmp s1 s1 s2 s2 tmp))
    (setq recs (cons (list off s1 s2) recs)))
  (setq recs   (lfc:sort-recs recs)
        merged nil)
  (foreach r recs                              ; fuse pieces of one tread
    (if (and merged (<= (abs (- (car r) (caar merged))) *lfc-tol*))
      (setq merged (cons (list (caar merged)
                               (min (cadar merged) (cadr r))
                               (max (caddar merged) (caddr r)))
                         (cdr merged)))
      (setq merged (cons r merged))))
  (setq merged (reverse merged)
        ok     (> (length merged) 1)
        sign   0
        prev   nil)
  (foreach r merged
    (if (and ok prev)
      (progn
        (setq ov      (- (min (caddr prev) (caddr r))
                         (max (cadr prev) (cadr r)))
              shorter (min (- (caddr prev) (cadr prev))
                           (- (caddr r) (cadr r)))
              d       (- (cadr r) (cadr prev)))
        (cond
          ((> ov (* 0.5 shorter)) (setq ok nil))    ; stacked, not stepped
          ((<= (abs d) *lfc-tol*) (setq ok nil))   ; no march along
          ((= sign 0) (setq sign (if (> d 0.0) 1 -1)))
          ((/= sign (if (> d 0.0) 1 -1)) (setq ok nil)))))  ; direction flipped
    (setq prev r))
  ok)

(defun lfc:pts-bbox (segs / xs ys e p)
  ;; ((minx miny) (maxx maxy)) over the endpoints of a list of segments
  (setq xs nil ys nil)
  (foreach e segs
    (foreach p (list (lfc:seg-p1 e) (lfc:seg-p2 e))
      (setq xs (cons (car p) xs)
            ys (cons (cadr p) ys))))
  (if xs
    (list (list (apply 'min xs) (apply 'min ys))
          (list (apply 'max xs) (apply 'max ys)))))

(defun lfc:boxes-touch (b1 b2 m)
  ;; do two ((minx miny)(maxx maxy)) boxes overlap once grown by m?
  (and b1 b2
       (<= (- (caar b2) m) (caadr b1))
       (<= (- (caar b1) m) (caadr b2))
       (<= (- (cadar b2) m) (cadadr b1))
       (<= (- (cadar b1) m) (cadadr b2))))

(defun lfc:bead-near-p (gbb beadbbs / hit bb)
  ;; is any bead-track box within *lfc-bead-dist* of the group box?
  (setq hit nil)
  (foreach bb beadbbs
    (if (lfc:boxes-touch gbb bb *lfc-bead-dist*)
      (setq hit T)))
  hit)

(defun lfc:zoom-box (bb / p1 p2 m)
  ;; zoom the current view onto a ((minx miny)(maxx maxy)) box
  (if bb
    (progn
      (setq p1 (car bb)
            p2 (cadr bb)
            m  (* *lfc-zoom-margin*
                  (max (- (car p2) (car p1)) (- (cadr p2) (cadr p1)) 1e-6)))
      (command "_.ZOOM" "_Window"
               (trans (list (- (car p1) m) (- (cadr p1) m) 0.0) 0 1)
               (trans (list (+ (car p2) m) (+ (cadr p2) m) 0.0) 0 1)))))

;; --- block & text helpers ------------------------------------------

(defun lfc:norm-text (s)
  ;; uppercase, with every non-alphanumeric squashed to a space, so
  ;; word searches ignore case, punctuation and MTEXT format codes
  (if (null s)
    ""
    (vl-list->string
      (mapcar '(lambda (c)
                 (cond
                   ((and (>= c 48) (<= c 57)) c)         ; 0-9
                   ((and (>= c 65) (<= c 90)) c)         ; A-Z
                   ((and (>= c 97) (<= c 122)) (- c 32)) ; a-z -> A-Z
                   (t 32)))
               (vl-string->list s)))))

(defun lfc:block-name (ent / res)
  ;; effective block name (sees through dynamic blocks)
  (setq res (vl-catch-all-apply
              'vla-get-EffectiveName
              (list (vlax-ename->vla-object ent))))
  (if (vl-catch-all-error-p res)
    (cdr (assoc 2 (entget ent)))
    res))

(defun lfc:blockdef-texts (bname depth / lst e et g)
  ;; TEXT/MTEXT/ATTDEF inside a block definition, following nested
  ;; blocks down to depth so a title wrapped in a wrapper is found
  (setq e (tblobjname "BLOCK" bname))
  (if e
    (progn
      (setq e (entnext e))
      (while (and e (/= "ENDBLK" (setq et (cdr (assoc 0 (entget e))))))
        (cond
          ((member et '("TEXT" "ATTDEF"))
           (setq lst (cons (cdr (assoc 1 (entget e))) lst)))
          ((= et "MTEXT")
           (foreach g (entget e)
             (if (member (car g) '(1 3))
               (setq lst (cons (cdr g) lst)))))
          ((and (= et "INSERT") (> depth 1))
           (setq lst (cons (cdr (assoc 2 (entget e))) lst)  ; nested block NAME
                 lst (append (lfc:blockdef-texts (cdr (assoc 2 (entget e)))
                                                  (1- depth))
                             lst))))
        (setq e (entnext e)))))
  lst)

(defun lfc:ins-texts (ent / ed lst e)
  ;; every piece of text an INSERT shows: its attribute values plus
  ;; the text inside its block definition, nested blocks included
  (setq ed  (entget ent)
        lst nil)
  (if (= 1 (cdr (assoc 66 ed)))               ; attributes follow
    (progn
      (setq e (entnext ent))
      (while (and e (= "ATTRIB" (cdr (assoc 0 (entget e)))))
        (setq lst (cons (cdr (assoc 1 (entget e))) lst)
              e   (entnext e)))))
  (append lst (lfc:blockdef-texts (cdr (assoc 2 ed)) *lfc-block-depth*)))

(defun lfc:attrib-bad-tags (ent words / e ed val tags)
  ;; tags of the INSERT's ATTRIBUTES whose value carries one of the
  ;; standalone words. Only attribute VALUES are considered - the
  ;; block's own labels ("Wall:", "Floor:") live in its definition and
  ;; must never be touched.
  (if (= 1 (cdr (assoc 66 (entget ent))))
    (progn
      (setq e (entnext ent))
      (while (and e (= "ATTRIB" (cdr (assoc 0 (setq ed (entget e))))))
        (setq val (cdr (assoc 1 ed)))
        (if (vl-some '(lambda (w)
                        (wcmatch (strcat " " (lfc:norm-text val) " ")
                                 (strcat "* " (strcase w) " *")))
                     words)
          (setq tags (cons (cdr (assoc 2 ed)) tags)))
        (setq e (entnext e)))))
  (reverse tags))

(defun lfc:wipe-attribs (ent tags / e ed n)
  ;; blank the listed attribute values so the pattern reads clean:
  ;; the label stays, whatever was written after it goes
  (setq n 0)
  (if (= 1 (cdr (assoc 66 (entget ent))))
    (progn
      (setq e (entnext ent))
      (while (and e (= "ATTRIB" (cdr (assoc 0 (setq ed (entget e))))))
        (if (member (cdr (assoc 2 ed)) tags)
          (progn
            (entmod (subst '(1 . "") (assoc 1 ed) ed))
            (entupd e)
            (setq n (1+ n))))
        (setq e (entnext e)))))
  (if (> n 0) (entupd ent))
  n)

(defun lfc:ins-attrib-deep (ent tag / val s)
  ;; the tag's value on the INSERT, or on a block nested inside it
  (setq val (lfc:ins-attrib ent tag))
  (if val
    val
    (foreach s (lfc:blockdef-texts (cdr (assoc 2 (entget ent)))
                                    *lfc-block-depth*)
      (if (and (null val)
               (wcmatch (lfc:squash s) (strcat "*" (lfc:squash tag) "*")))
        (setq val s)))))

(defun lfc:block-has-layer-p (bname layer depth / e et found)
  ;; does the block definition (or a block it nests, down to depth)
  ;; draw anything on the given layer?
  (setq e (tblobjname "BLOCK" bname))
  (if e
    (progn
      (setq e (entnext e))
      (while (and e (not found)
                  (/= "ENDBLK" (setq et (cdr (assoc 0 (entget e))))))
        (if (= (strcase (cdr (assoc 8 (entget e)))) (strcase layer))
          (setq found T))
        (if (and (not found) (= et "INSERT") (> depth 1))
          (if (lfc:block-has-layer-p (cdr (assoc 2 (entget e))) layer (1- depth))
            (setq found T)))
        (setq e (entnext e)))))
  found)

(defun lfc:ins-matches (ent phrase / pat found s)
  ;; T when the INSERT's (effective) name or any text it shows
  ;; contains the phrase, ignoring case and punctuation
  (setq pat   (strcat "*" (lfc:norm-text phrase) "*")
        found (wcmatch (lfc:norm-text (lfc:block-name ent)) pat))
  (foreach s (lfc:ins-texts ent)
    (if (wcmatch (lfc:norm-text s) pat)
      (setq found T)))
  found)

(defun lfc:ins-text-has (ent phrase / pat found s)
  ;; T when any text the INSERT shows carries the phrase (its block
  ;; NAME is deliberately not consulted - an option label has to be
  ;; drawn in the block, not implied by what it is called)
  (setq pat   (strcat "*" (lfc:squash phrase) "*")
        found nil)
  (foreach s (lfc:ins-texts ent)
    (if (wcmatch (lfc:squash s) pat) (setq found T)))
  found)

(defun lfc:attach-undecided-p (ent / w undecided)
  ;; T when the block still shows EVERY attachment option, i.e. nobody
  ;; has picked one yet
  (setq undecided T)
  (foreach w *lfc-attach-options*
    (if (not (lfc:ins-text-has ent w)) (setq undecided nil)))
  undecided)

(defun lfc:ins-has-word (ent word / found s)
  ;; T when the INSERT's (effective) name or any text it shows
  ;; contains the given standalone word — "NOT" hits "Not Selected"
  ;; but never "NOTE"; "STEP" hits "with Step" but never "Stepstone"
  (setq word  (strcase word)
        found nil)
  (foreach s (cons (lfc:block-name ent) (lfc:ins-texts ent))
    (if (and s
             (wcmatch (strcat " " (lfc:norm-text s) " ")
                      (strcat "* " word " *")))
      (setq found T)))
  found)

(defun lfc:phrase-p (s / sq)
  ;; T when the text carries one of *lfc-fgstep-words*, with case,
  ;; spaces and punctuation ignored - so "FiberglassStep" (a layer
  ;; name) matches "Fiberglass Step" just as well
  (setq sq (lfc:squash s))
  (vl-some '(lambda (w) (wcmatch sq (strcat "*" (lfc:squash w) "*")))
           *lfc-fgstep-words*))

(defun lfc:clip (s n)
  (if (> (strlen s) n) (strcat (substr s 1 n) "...") s))

(defun lfc:fgstep-src (ss blks / found i e ed et g b s)
  ;; what makes a fiberglass step show up in the highlighted area:
  ;; a description of the first match ("block '8' Straight FG Step'",
  ;; "layer 'FiberglassStep'", "text 'FG Step'"), nil when there is
  ;; none. Blocks are matched on their name, their attributes and the
  ;; text inside their definition.
  (setq found nil
        i     0)
  (repeat (sslength ss)
    (setq e (ssname ss i)
          i (1+ i))
    (if (and (not found) (setq ed (entget e)))
      (progn
        (setq et (cdr (assoc 0 ed))
              s  (cdr (assoc 8 ed)))
        (if (lfc:phrase-p s)                    ; the layer it sits on
          (setq found (strcat "layer '" (lfc:clip s 40) "'")))
        (if (and (not found) (member et '("TEXT" "MTEXT")))
          (foreach g ed
            (if (and (not found)
                     (member (car g) '(1 3))
                     (lfc:phrase-p (cdr g)))
              (setq found (strcat "text '" (lfc:clip (cdr g) 40) "'"))))))))
  (foreach b blks                                ; block names & their text
    (if (not found)
      (progn
        (setq s (lfc:block-name b))
        (if (lfc:phrase-p s)
          (setq found (strcat "block '" (lfc:clip s 40) "'")))
        (if (not found)
          (foreach s (lfc:ins-texts b)
            (if (and (not found) (lfc:phrase-p s))
              (setq found (strcat "block text '" (lfc:clip s 40) "'"))))))))
  found)

(defun lfc:drawing-has-phrase (phrase / pat ss2 i e ed found g)
  ;; T when any TEXT or MTEXT in the drawing carries the phrase,
  ;; case and punctuation ignored
  (setq pat (strcat "*" (lfc:norm-text phrase) "*")
        ss2 (ssget "_X" '((0 . "TEXT,MTEXT")))
        i   0)
  (if ss2
    (repeat (sslength ss2)
      (setq e  (ssname ss2 i)
            i  (1+ i)
            ed (entget e))
      (foreach g ed
        (if (and (not found)
                 (member (car g) '(1 3))
                 (wcmatch (lfc:norm-text (cdr g)) pat))
          (setq found T)))))
  found)

(defun lfc:join (lst sep / out s)
  ;; "A" + "B" + ... joined with sep
  (foreach s lst
    (setq out (if out (strcat out sep s) s)))
  out)

(defun lfc:squash (s)
  ;; norm-text with the spaces removed too, so "Tech Title" finds a
  ;; block that is actually named "TechTitle"
  (vl-list->string (vl-remove 32 (vl-string->list (lfc:norm-text s)))))

(defun lfc:ins-attrib (ent tag / e ed val)
  ;; value of the attribute with the given tag on an INSERT; nil
  ;; when the block has no such attribute
  (setq tag (strcase tag))
  (if (= 1 (cdr (assoc 66 (entget ent))))
    (progn
      (setq e (entnext ent))
      (while (and e (null val) (= "ATTRIB" (cdr (assoc 0 (entget e)))))
        (setq ed (entget e))
        (if (= tag (strcase (cdr (assoc 2 ed))))
          (setq val (cdr (assoc 1 ed))))
        (setq e (entnext e)))))
  val)

(defun lfc:parse-num (s / p num den)
  ;; "4", "4.5", "1/2" -> real
  (setq p (vl-string-search "/" s))
  (if p
    (progn
      (setq num (atof (substr s 1 p))
            den (atof (substr s (+ p 2))))
      (if (> den 0.0) (/ num den) 0.0))
    (atof s)))

(defun lfc:after-eq (s / p)
  ;; the part after the last "=", so a label never contributes its
  ;; own digits: "Finished Wall Ht = 40''" -> " 40''"
  (while (setq p (vl-string-search "=" s))
    (setq s (substr s (+ p 2))))
  s)

(defun lfc:len-values (s / lst i n c numstr toks unit vals cur tok)
  ;; every length written in the text, as a list of numbers in inches
  ;; (drawing units). ' = feet, '' or " = inches, a bare number counts
  ;; as inches. Feet and bare numbers carry on into the same value, an
  ;; inch mark closes it, so a compound height stays ONE value while a
  ;; list stays several:
  ;;   "40''"          -> (40.0)
  ;;   "3'-4''"        -> (40.0)
  ;;   "3' 4 1/2\""    -> (40.5)
  ;;   "0'', 40'', 45''" -> (0.0 40.0 45.0)
  ;; A label before the last "=" is ignored, so the attribute may read
  ;; "Finished Wall Ht = 40''" and still measure 40.
  (setq s    (lfc:after-eq s)
        lst  (vl-string->list s)
        i    0
        n    (length lst)
        toks nil)
  (while (< i n)
    (setq c (nth i lst))
    (if (or (and (>= c 48) (<= c 57)) (= c 46) (= c 47))  ; digit . /
      (progn
        (setq numstr "")
        (while (and (< i n)
                    (setq c (nth i lst))
                    (or (and (>= c 48) (<= c 57)) (= c 46) (= c 47)))
          (setq numstr (strcat numstr (chr c))
                i      (1+ i)))
        (setq unit nil)
        (cond
          ((and (< i n) (= (nth i lst) 34))               ; "
           (setq unit 'in
                 i    (1+ i)))
          ((and (< i n) (= (nth i lst) 39))               ; '
           (if (and (< (1+ i) n) (= (nth (1+ i) lst) 39))
             (setq unit 'in                               ; ''
                   i    (+ i 2))
             (setq unit 'ft
                   i    (1+ i)))))
        (setq toks (append toks (list (cons (lfc:parse-num numstr) unit)))))
      (setq i (1+ i))))
  (setq vals nil
        cur  nil)
  (foreach tok toks
    (setq cur (+ (if cur cur 0.0)
                 (if (eq (cdr tok) 'ft) (* 12.0 (car tok)) (car tok))))
    (if (eq (cdr tok) 'in)                     ; inches close the value
      (setq vals (append vals (list cur))
            cur  nil)))
  (if cur (setq vals (append vals (list cur))))
  vals)

(defun lfc:parse-len (s)
  ;; the first length written in the text, in inches; nil when none
  (car (lfc:len-values s)))

(defun lfc:varies-p (s)
  ;; T when the height reads "Varies" instead of carrying a number
  (wcmatch (strcat " " (lfc:norm-text (lfc:after-eq s)) " ")
           "* VARIES *"))

(defun lfc:all-digits-p (s / i n c ok)
  (setq n (strlen s) ok (> n 0) i 1)
  (while (and ok (<= i n))
    (setq c (ascii (substr s i 1)))
    (if (or (< c 48) (> c 57)) (setq ok nil))
    (setq i (1+ i)))
  ok)

(defun lfc:days-in-month (mo yr)
  (cond
    ((member mo '(1 3 5 7 8 10 12)) 31)
    ((member mo '(4 6 9 11)) 30)
    ((and (= 0 (rem yr 4)) (or (/= 0 (rem yr 100)) (= 0 (rem yr 400)))) 29) ; leap Feb
    (t 28)))

(defun lfc:today-mdy ( / d)
  ;; (month day year) off the computer clock.  CDATE is
  ;; YYYYMMDD.HHMMSSmsec, decoded arithmetically so DIMZIN (which trims
  ;; rtos output) cannot mangle it.
  (setq d (fix (getvar "CDATE")))
  (list (rem (fix (/ d 100)) 100) (rem d 100) (fix (/ d 10000))))

(defun lfc:mdy-str (mdy)
  (strcat (cal:zeropad2 (car mdy)) "/" (cal:zeropad2 (cadr mdy)) "/"
          (itoa (caddr mdy))))

(defun lfc:date-verdict (raw / s mo dd yr now)
  ;; nil when raw is a clean MM/DD/YYYY calendar date; otherwise a
  ;; short string saying what is wrong with it
  (setq s (vl-string-trim " \t" (lfc:after-eq raw)))
  (cond
    ((= s "") "is blank - expected MM/DD/YYYY")
    ((or (/= (strlen s) 10)
         (/= (substr s 3 1) "/")
         (/= (substr s 6 1) "/")
         (not (lfc:all-digits-p (substr s 1 2)))
         (not (lfc:all-digits-p (substr s 4 2)))
         (not (lfc:all-digits-p (substr s 7 4))))
     (strcat "'" raw "' is not in MM/DD/YYYY format - expected MM/DD/YYYY"))
    (t
     (setq mo (atoi (substr s 1 2))
           dd (atoi (substr s 4 2))
           yr (atoi (substr s 7 4)))
     (cond
       ((or (< mo 1) (> mo 12))
        (strcat "'" raw "' - " (substr s 1 2)
                " is not a month (01-12) - expected MM/DD/YYYY"))
       ((or (< dd 1) (> dd (lfc:days-in-month mo yr)))
        (strcat "'" raw "' - " (substr s 4 2)
                " is not a valid day for that month - expected MM/DD/YYYY"))
       ;; a real date, but is it TODAY?  A sheet going out under an old
       ;; date is the mistake this catches -- the drawing was reworked
       ;; and the title block never caught up.
       ((progn (setq now (lfc:today-mdy))
               (not (and (= mo (car now)) (= dd (cadr now))
                         (= yr (caddr now)))))
        (strcat "'" s "' is NOT TODAY'S DATE (" (lfc:mdy-str now)
                ") - update it"))
       (t nil)))))

;; --- dimension review ----------------------------------------------

(defun lfc:dim-style (ent / s)
  ;; the dimension's style name, "" when it has none
  (setq s (cdr (assoc 3 (entget ent))))
  (if s s ""))

(defun lfc:style-rank (style / i r s)
  ;; position of the style in *lfc-style-order* (exact name match,
  ;; case-blind); unlisted styles land after every listed one
  (setq style (strcase style)
        i     0
        r     nil)
  (foreach s *lfc-style-order*
    (if (and (null r) (= (strcase s) style)) (setq r i))
    (setq i (1+ i)))
  (if r r (length *lfc-style-order*)))

(defun lfc:ent-center (ent / bb)
  ;; (x y) centre of the entity's box; falls back to its group-10 point
  (setq bb (cal:bbox-ent ent))
  (if bb
    (list (* 0.5 (+ (caar bb) (caadr bb)))
          (* 0.5 (+ (cadar bb) (cadadr bb))))
    (progn
      (setq bb (cdr (assoc 10 (entget ent))))
      (if bb (list (car bb) (cadr bb)) (list 0.0 0.0)))))

(defun lfc:dim-order-p (r1 r2 rowtol)
  ;; strict "r1 reviews before r2" for recs (rank cx cy ent):
  ;; style rank first, then row (higher = earlier), then left first
  (cond
    ((< (car r1) (car r2)) T)
    ((> (car r1) (car r2)) nil)
    ((> (- (caddr r1) (caddr r2)) rowtol) T)   ; r1 sits a row above
    ((> (- (caddr r2) (caddr r1)) rowtol) nil) ; r2 sits a row above
    (t (< (cadr r1) (cadr r2)))))              ; same row: left first

(defun lfc:sort-dims (dims rowtol / recs cen r out pre rest e)
  ;; stable insertion sort into review order
  (setq recs nil)
  (foreach e dims
    (setq cen  (lfc:ent-center e)
          recs (cons (list (lfc:style-rank (lfc:dim-style e))
                           (car cen) (cadr cen) e)
                     recs)))
  (setq recs (reverse recs)
        out  nil)
  (foreach r recs
    (setq pre  nil
          rest out)
    (while (and rest (not (lfc:dim-order-p r (car rest) rowtol)))
      (setq pre  (cons (car rest) pre)
            rest (cdr rest)))
    (setq out (append (reverse pre) (list r) rest)))
  (mapcar '(lambda (r) (nth 3 r)) out))

(defun lfc:dim-meas (ent / ed dtype p13 p14 ang v meas)
  ;; the dimension's current measurement as display text, formatted
  ;; with the drawing's unit settings (LUNITS/AUNITS); nil if unknown.
  ;; Linear/aligned dims are recomputed from their definition points
  ;; so the value reflects any point that was just moved.
  (setq ed    (entget ent)
        dtype (logand 7 (cdr (assoc 70 ed)))
        meas  (cdr (assoc 42 ed)))            ; stored actual measurement
  (cond
    ((= dtype 1)                              ; aligned: point-to-point
     (setq p13 (cdr (assoc 13 ed))
           p14 (cdr (assoc 14 ed)))
     (if (and p13 p14) (rtos (distance p13 p14))))
    ((= dtype 0)                              ; rotated/linear: project the
     (setq p13 (cdr (assoc 13 ed))            ; points onto the dim direction
           p14 (cdr (assoc 14 ed))
           ang (cdr (assoc 50 ed)))
     (if (and p13 p14)
       (progn
         (if (null ang) (setq ang 0.0))
         (setq v (mapcar '- p14 p13))
         (rtos (abs (+ (* (car v) (cos ang))
                       (* (cadr v) (sin ang))))))))
    ((member dtype '(2 5))                    ; angular: show the angle
     (if (and meas (>= meas 0.0)) (angtos meas)))
    (t                                        ; radius/diameter/ordinate
     (if (and meas (>= meas 0.0)) (rtos meas)))))

(defun lfc:dim-num (ent / ed dtype p13 p14 ang v)
  ;; the dimension's linear measurement as a NUMBER, recomputed from
  ;; its definition points; falls back to the stored measurement
  (setq ed    (entget ent)
        dtype (logand 7 (cdr (assoc 70 ed)))
        p13   (cdr (assoc 13 ed))
        p14   (cdr (assoc 14 ed)))
  (cond
    ((and (= dtype 1) p13 p14) (distance p13 p14))
    ((and (= dtype 0) p13 p14)
     (setq ang (cdr (assoc 50 ed)))
     (if (null ang) (setq ang 0.0))
     (setq v (mapcar '- p14 p13))
     (abs (+ (* (car v) (cos ang)) (* (cadr v) (sin ang)))))
    (t (cdr (assoc 42 ed)))))

(defun lfc:dim-stated (ent / txt v)
  ;; the value the dimension actually STATES: its text override when
  ;; it carries a readable one, else what it measures
  (setq txt (cdr (assoc 1 (entget ent))))
  (if (and txt
           (/= txt "")
           (not (vl-string-search "<>" txt))    ; "<>" = show the measurement
           (setq v (lfc:parse-len txt)))
    v
    (lfc:dim-num ent)))

(defun lfc:pt-in-box (p bb m)
  ;; is point p inside the ((minx miny)(maxx maxy)) box grown by m?
  (and bb p
       (>= (car p)  (- (caar bb) m))
       (<= (car p)  (+ (caadr bb) m))
       (>= (cadr p) (- (cadar bb) m))
       (<= (cadr p) (+ (cadadr bb) m))))

(defun lfc:height-dim (dims bb rise / best bestdy ed p13 p14 dy e)
  ;; the side view's OVERALL-HEIGHT dimension: both definition points
  ;; sit in the side view and span its full rise. The widest such
  ;; dimension wins, so a single riser's dim is never mistaken for it.
  (foreach e dims
    (if (entget e)
      (progn
        (setq ed  (entget e)
              p13 (cdr (assoc 13 ed))
              p14 (cdr (assoc 14 ed)))
        (if (and p13 p14
                 (lfc:pt-in-box p13 bb *lfc-height-tol*)
                 (lfc:pt-in-box p14 bb *lfc-height-tol*))
          (progn
            (setq dy (abs (- (cadr p14) (cadr p13))))
            (if (and (>= dy (- rise *lfc-height-tol*))
                     (or (null bestdy) (> dy bestdy)))
              (setq bestdy dy
                    best   e)))))))
  best)

(defun lfc:audit-dim-point (ent gcode label cands / ed pt near sugg ans final how)
  ;; audits one definition point: an off-object point is put where it
  ;; looks like it belongs, then you choose - Move (take it), Keep
  ;; (put it back exactly where you drew it) or Pick your own spot.
  ;; Returns (original final how) when the point was looked at, where
  ;; how is 'auto / 'user / 'kept; nil when the point was already fine.
  (setq ed (entget ent)
        pt (cdr (assoc gcode ed)))
  (if pt
    (progn
      (setq near (lfc:nearest-curve pt nil cands))
      (if (and near (> (caddr near) *lfc-tol*))
        (progn
          (setq sugg (cadr near))
          ;; show the suggestion in place, but keep the original spot
          ;; marked so both are on screen while the question is asked
          (entmod (subst (cons gcode sugg) (assoc gcode ed) ed))
          (entupd ent)
          (princ (strcat "\n  " label " is not on any object - nearest one is "
                         (rtos (caddr near) 2 4) " away."))
          (setq ans (lfc:confirm-move label pt sugg))
          (cond
            ((eq ans 'move)
             (setq final sugg
                   how   'auto)
             (princ (strcat "\n  " label " MOVED onto the nearest object, "
                            (lfc:ptstr final) ".")))
            ((eq ans 'keep)
             (setq ed    (entget ent)
                   final pt
                   how   'kept)
             (entmod (subst (cons gcode pt) (assoc gcode ed) ed))
             (entupd ent)
             (princ (strcat "\n  " label " KEPT where you drew it, "
                            (lfc:ptstr final) " - nothing changed.")))
            (t
             (setq final (trans ans 1 0)
                   how   'user
                   ed    (entget ent))
             (entmod (subst (cons gcode final) (assoc gcode ed) ed))
             (entupd ent)
             (princ (strcat "\n  " label " moved to the spot you picked, "
                            (lfc:ptstr final) "."))))
          (redraw)
          (list pt final how))))))

(defun lfc:review-dim (ent cands num total / ed dtype h sty p13 p14 r1 r2
                                              looked moved kept ok note meas assocnote)
  ;; interactive review of one dimension.
  ;; Returns (handle ok-flag report-note moved-point-count measurement).
  (setq ed    (entget ent)
        h     (cdr (assoc 5 ed))
        sty   (lfc:dim-style ent)
        dtype (logand 7 (cdr (assoc 70 ed))))
  (lfc:zoom-ent ent)
  (redraw ent 3)
  (princ (strcat "\n\nDimension " (itoa num) " of " (itoa total)
                 " (handle " h
                 (if (= sty "") "" (strcat ", style " sty))
                 ")"))
  (if (member dtype '(0 1))                   ; rotated/linear or aligned
    (progn
      (if (lfc:dim-assoc-p ent)
        (princ "\n  Note: this dimension is object-associative - a moved point may re-anchor on its own."))
      (setq p13 (cdr (assoc 13 ed))           ; the two dimmed points
            p14 (cdr (assoc 14 ed))
            r1  (lfc:audit-dim-point ent 13 "dimension point 1" cands)
            r2  (lfc:audit-dim-point ent 14 "dimension point 2" cands))))
  (setq looked (append (if r1 (list r1)) (if r2 (list r2)))
        moved  (vl-remove-if '(lambda (x) (eq (caddr x) 'kept)) looked)
        kept   (vl-remove-if-not '(lambda (x) (eq (caddr x) 'kept)) looked))
  ;; only when something actually moved is there an old position worth
  ;; drawing a construction line through
  (if moved (lfc:make-xline p13 p14))        ; through the ORIGINAL points
  (if (and moved (lfc:dim-assoc-p ent))
    (setq assocnote " (ASSOCIATIVE - verify the moved point holds)"))
  (setq meas (lfc:dim-meas ent))             ; after any point moves
  (if meas (princ (strcat "\n  Measures " meas ".")))
  (redraw ent 3)
  (setq ok (cal:ask-yn-nav "\n  Is this dimension correct?"))
  (redraw ent 4)
  (redraw)
  (if (member ok '(back skip))
    (list h ok nil (length moved) meas)       ; navigation: caller handles it
    (progn
      (setq ok (eq ok 'yes))
      (setq note (strcat
                   (if ok "OK" "FLAGGED to fix (red)")
                   (if moved
                     (strcat " - " (itoa (length moved))
                             " point(s) moved onto the nearest object")
                     "")
                   (if kept
                     (strcat " - " (itoa (length kept))
                             " point(s) kept where you drew them")
                     "")
                   (if assocnote assocnote "")))
      (if (not ok) (lfc:set-color ent *lfc-flag-color*))
      (list h ok note (length moved) meas))))

;; --- arc review ----------------------------------------------------

(defun lfc:arc-end-target (ent which cands / p other near ends target)
  ;; where the attachment audit says this endpoint should go;
  ;; nil when the endpoint is already fine (or nothing to attach to)
  (setq p     (if (eq which 'start)
                (vlax-curve-getStartPoint ent)
                (vlax-curve-getEndPoint ent))
        other (if (eq which 'start)
                (vlax-curve-getEndPoint ent)
                (vlax-curve-getStartPoint ent))
        near  (lfc:nearest-curve p ent cands))
  (cond
    ((null near) nil)                         ; nothing to attach to at all
    ((<= (caddr near) *lfc-tol*)             ; endpoint sits on an object...
     (setq ends (lfc:curve-ends (car near)))
     ;; never snap onto the arc's own other endpoint
     (setq ends (vl-remove-if '(lambda (q) (< (distance q other) 1e-8)) ends))
     (cond
       ((null ends) nil)                      ; closed curve: no ends to demand
       ((vl-some '(lambda (q) (<= (distance p q) *lfc-tol*)) ends)
        nil)                                  ; ...and at one of its ends: OK
       (t (lfc:closest-of p ends))))         ; ...but mid-object: closest end
    (t                                        ; floating: closest end anywhere,
     (setq target (lfc:nearest-end p ent cands))
     (if (or (null target) (< (distance target other) 1e-8))
       (cadr near)                            ; else closest point on closest object
       target))))

(defun lfc:arc-state (ent / ed)
  ;; the groups that define an arc's shape, for an exact put-it-back
  (setq ed (entget ent))
  (list (assoc 10 ed) (assoc 40 ed) (assoc 50 ed) (assoc 51 ed)))

(defun lfc:arc-restore (ent st / ed g)
  ;; restore a saved shape exactly, rather than re-fitting back to it
  (setq ed (entget ent))
  (foreach g st (setq ed (subst g (assoc (car g) ed) ed)))
  (entmod ed)
  (entupd ent))

(defun lfc:review-arc-end (ent which label cands / p target st ans final how)
  ;; audits one arc endpoint: a detached end is snapped where it looks
  ;; like it belongs, then you choose - Move (take it), Keep (put the
  ;; arc back exactly as drawn) or Pick your own spot.
  ;; Returns (original final how) when the end was looked at, where how
  ;; is 'auto / 'user / 'kept; nil when the end was already fine.
  (setq p      (if (eq which 'start)
                 (vlax-curve-getStartPoint ent)
                 (vlax-curve-getEndPoint ent))
        target (lfc:arc-end-target ent which cands)
        st     (lfc:arc-state ent))
  (cond
    (target
     (if (lfc:move-arc-end ent which target)
       (progn
         (princ (strcat "\n  " label " is not attached to an object end - nearest is "
                        (rtos (distance p target) 2 4) " away."))
         (setq ans (lfc:confirm-move label p target))
         (cond
           ((eq ans 'move)
            (setq final target
                  how   'auto)
            (princ (strcat "\n  " label " SNAPPED to the object end, "
                           (lfc:ptstr final) ".")))
           ((eq ans 'keep)
            (lfc:arc-restore ent st)
            (setq final p
                  how   'kept)
            (princ (strcat "\n  " label " KEPT where you drew it, "
                           (lfc:ptstr final) " - the arc is unchanged.")))
           (t
            (setq ans (trans ans 1 0))
            (if (lfc:move-arc-end ent which ans)
              (progn
                (setq final ans
                      how   'user)
                (princ (strcat "\n  " label " moved to the spot you picked, "
                               (lfc:ptstr final) ".")))
              (progn
                (setq final target
                      how   'auto)
                (princ "\n  Could not re-fit the arc through that spot (collinear?); left it on the object end.")))))
         (redraw)
         (list p final how))
       (progn
         (princ (strcat "\n  " label " should attach at " (lfc:ptstr target)
                        " but the arc could not be re-fitted (points collinear?)."))
         nil)))
    (*lfc-ask-all-arc-ends*                  ; optional: confirm attached ends too
     (setq ans (lfc:confirm-move label p p))
     (redraw)
     (if (member ans '(move keep))
       nil
       (progn
         (setq ans (trans ans 1 0))
         (if (lfc:move-arc-end ent which ans)
           (list p ans 'user)
           (progn
             (princ "\n  Could not re-fit the arc through that spot (collinear?); unchanged.")
             nil)))))
    (t nil)))

(defun lfc:review-arc (ent cands num total / ed h planar r1 r2 looked moved kept note)
  ;; interactive review of one arc's endpoints.
  ;; Returns (handle untouched-flag report-note moved-point-count).
  (setq ed     (entget ent)
        h      (cdr (assoc 5 ed))
        planar (lfc:planar-arc-p ed))
  (lfc:zoom-ent ent)
  (redraw ent 3)
  (princ (strcat "\n\nArc " (itoa num) " of " (itoa total)
                 " (handle " h ")"))
  (if planar
    (setq r1 (lfc:review-arc-end ent 'start "arc start point" cands)
          r2 (lfc:review-arc-end ent 'end   "arc end point"   cands))
    (princ "\n  Arc is not in the world XY plane - endpoint audit skipped."))
  (redraw ent 4)
  (redraw)
  (setq looked (append (if r1 (list r1)) (if r2 (list r2)))
        moved  (vl-remove-if '(lambda (x) (eq (caddr x) 'kept)) looked)
        kept   (vl-remove-if-not '(lambda (x) (eq (caddr x) 'kept)) looked))
  (if moved (lfc:set-color ent *lfc-arc-color*))
  (setq note (cond
               ((not planar) "not in world XY plane - skipped")
               ((and moved kept)
                (strcat (itoa (length moved)) " endpoint(s) moved (magenta), "
                        (itoa (length kept)) " kept where you drew them"))
               (moved (strcat (itoa (length moved))
                              " endpoint(s) moved (magenta)"))
               (kept (strcat (itoa (length kept))
                             " endpoint(s) kept where you drew them"))
               (t "endpoints OK")))
  (list h (null moved) note (length moved)))

;; --- overlapping line review ---------------------------------------

(defun lfc:review-olap (la lb num total / info ea eb h1 h2 lay1 lay2 label
                                           ans mergeable kinds)
  ;; interactive review of one overlapping segment pair.
  ;; Returns nil when the pair no longer overlaps (an earlier merge
  ;; absorbed it); otherwise (label report-note action ents...) where
  ;; action is merged / flagged / left and ents keep their cyan.
  (setq ea (lfc:seg-ent la)
        eb (lfc:seg-ent lb))
  (if (and (entget ea) (entget eb) (setq info (lfc:overlap-info la lb)))
    (progn
      (setq h1        (cdr (assoc 5 (entget ea)))
            h2        (cdr (assoc 5 (entget eb)))
            lay1      (cdr (assoc 8 (entget ea)))
            lay2      (cdr (assoc 8 (entget eb)))
            mergeable (and (lfc:whole-line-p la)
                           (lfc:whole-line-p lb)
                           (= (strcase lay1) (strcase lay2)))
            kinds     (if (and (lfc:whole-line-p la) (lfc:whole-line-p lb))
                        "lines"
                        "segments")
            label     (strcat h1 "+" h2 " (overlap " (rtos (caddr info)) ")"))
      (lfc:zoom-2ents ea eb)
      (redraw ea 3)
      (redraw eb 3)
      (lfc:mark-point (car info))
      (lfc:mark-point (cadr info))
      (princ (strcat "\n\nOverlap " (itoa num) " of " (itoa total)
                     ": " kinds " " h1 " + " h2
                     " run on top of each other for " (rtos (caddr info)) "."))
      (if mergeable
        (progn
          (initget "Merge Flag Leave")
          (setq ans (getkword
                      "\n  Merge into one line, Flag to fix, or Leave as is? [Merge/Flag/Leave] <Merge>: "))
          (if (null ans) (setq ans "Merge")))
        (progn
          (princ (if (= (strcase lay1) (strcase lay2))
                   "\n  (Polyline edge - cannot be merged automatically.)"
                   (strcat "\n  (Different layers: " lay1 " / " lay2
                           " - cannot be merged automatically.)")))
          (initget "Flag Leave")
          (setq ans (getkword
                      "\n  Flag to fix, or Leave as is? [Flag/Leave] <Flag>: "))
          (if (null ans) (setq ans "Flag"))))
      (redraw ea 4)
      (redraw eb 4)
      (redraw)
      (cond
        ((= ans "Merge")
         (lfc:merge-lines la lb info)
         (lfc:set-color ea *lfc-olap-color*)
         (princ "\n  Merged into one line (cyan).")
         (list label "merged into one line (cyan)" 'merged ea))
        ((= ans "Flag")
         (lfc:set-color ea *lfc-olap-color*)
         (lfc:set-color eb *lfc-olap-color*)
         (princ "\n  Flagged to fix (cyan).")
         (list label
               (if (lfc:whole-line-p la)
                 (if (= (strcase lay1) (strcase lay2))
                   "flagged to fix (cyan)"
                   "different layers - flagged to fix (cyan)")
                 "polyline edge - flagged to fix (cyan)")
               'flagged ea eb))
        (t
         (princ "\n  Left as drawn.")
         (list label "left as drawn" 'left))))))

;; --- command -------------------------------------------------------

(defun c:LINFINCHECK ( / *error* oldecho vc vs undo-open ss i e et
                      cands dims arcs lns plns segs blks olaps rest e1 e2 pr
                      saved keep res n total lines ans
                      ndok ndflag ndmoved naok namoved nasnap
                      nomerged noflag noleft
                      sgroups scand svgroups pgroups g1 g2 stepsp svmode
                      satts attwrong attundec liners linerbadw linernostep bad w bn bh bp
                      linerstep linerfg fgstep badtags linerwiped
                      bgroups beadneed beadok beadmiss beadss beadbbs gbb
                      stepsum linersum rowtol sty g b l pair hdr
                      htsum stepht wallht wallraw tins tpat tss
                      datesum dateraw datebad
                      svbb hdim dimht htval htbad
                      wallvals wallvar wallmany htskip wallzero wallask
                      laylist locked relock lay tlist tbest cx cy tvals s d
                      dlines skiprest bordbb bordsum
                      minx miny maxx maxy bb m dhdr right dimlay units carried cmv)

  (defun *error* (msg)
    ;; put the greys back (flagged/moved items keep their colour),
    ;; re-lock what we unlocked, clear markers, close the undo group
    (foreach pair saved
      (if (and (not (member (car pair) keep)) (entget (car pair)))
        (lfc:set-color (car pair) (cdr pair))))
    (foreach l relock (lfc:set-layer-lock l T))
    (redraw)
    (if undo-open
      (progn (setvar "CMDECHO" 0) (command "_.UNDO" "_End")))
    (if oldecho (setvar "CMDECHO" oldecho))
    (if (and msg (not (wcmatch (strcase msg) "*BREAK*,*CANCEL*,*QUIT*,*EXIT*")))
      (princ (strcat "\nLINFINCHECK error: " msg)))
    (princ))

  (prompt "\nHighlight the drawing to LINFINCHECK: ")
  (setq ss (ssget))
  (cond
    ((null ss)
     (prompt "\nNothing selected - LINFINCHECK cancelled."))
    (t
     (setq cands nil dims nil arcs nil lns nil blks nil segs nil
           saved nil keep nil lines nil i 0
           ndok 0 ndflag 0 ndmoved 0 naok 0 namoved 0 nasnap 0
           nomerged 0 noflag 0 noleft 0)
     (repeat (sslength ss)
       (setq e  (ssname ss i)
             i  (1+ i)
             et (cdr (assoc 0 (entget e))))
       (if (= et "DIMENSION") (setq dims (cons e dims)))
       (if (= et "ARC") (setq arcs (cons e arcs)))
       (if (= et "LINE") (setq lns (cons e lns)))
       (if (member et '("LINE" "LWPOLYLINE" "POLYLINE"))
         (setq plns (cons e plns)))
       (if (= et "INSERT") (setq blks (cons e blks)))
       (if (member et *lfc-curve-types*) (setq cands (cons e cands))))
     (setq dims  (reverse dims)
           arcs  (reverse arcs)
           lns   (reverse lns)
           plns  (reverse plns)
           blks  (reverse blks)
           cands (reverse cands)
           ;; detection runs on segments, so a run of steps or a side
           ;; view drawn as one polyline counts like separate lines
           segs  (lfc:collect-segs plns))
     (cond
       ((and (null dims) (null arcs) (< (length segs) 2) (null blks))
        (prompt "\nSelection holds no dimensions, arcs, lines, or blocks to check - nothing to do."))
       (t
        (setq oldecho (getvar "CMDECHO"))
        (setvar "CMDECHO" 0)
        (setq vc (getvar "VIEWCTR")
              vs (getvar "VIEWSIZE"))
        (command "_.UNDO" "_Begin")
        (setq undo-open T)
        (cal:ensure-layer *lfc-constr-layer* *lfc-constr-color*)
        (cal:ensure-layer *lfc-report-layer* *lfc-report-color*)

        ;; a locked layer swallows every fix and recolour silently -
        ;; surface that up front and offer to unlock for the run
        (setq laylist nil relock nil i 0)
        (repeat (sslength ss)
          (setq lay (cdr (assoc 8 (entget (ssname ss i))))
                i   (1+ i))
          (if (and lay (not (member lay laylist)))
            (setq laylist (cons lay laylist))))
        (setq locked (vl-remove-if-not 'lfc:layer-locked-p laylist))
        (if locked
          (if (cal:ask-yn
                (strcat "\n" (itoa (length locked))
                        " locked layer(s) in the selection ("
                        (lfc:join locked ", ")
                        ") - LINFINCHECK cannot recolour or fix anything on them. Unlock for this run?")
                "Yes")
            (progn
              (foreach l locked (lfc:set-layer-lock l nil))
              (setq relock locked)
              (princ "\n  Unlocked; they will be re-locked when the run ends."))
            (princ "\n  Locked layers stay locked - items on them are reported but left untouched.")))

        ;; a rerun replaces the previous run's report and markers
        (lfc:clear-old)

        ;; extents of the selection (report goes to the right of them)
        (setq i 0)
        (repeat (sslength ss)
          (setq e  (ssname ss i)
                i  (1+ i)
                bb (cal:bbox-ent e))
          (if bb
            (setq minx (if minx (min minx (caar bb)) (caar bb))
                  miny (if miny (min miny (cadar bb)) (cadar bb))
                  maxx (if maxx (max maxx (caadr bb)) (caadr bb))
                  maxy (if maxy (max maxy (cadadr bb)) (cadadr bb)))))

        ;; march order for the dimensions: style groups first
        ;; (*lfc-style-order*), then row by row, left to right
        (setq rowtol (if (and miny maxy (> (- maxy miny) 1e-8))
                       (* 0.05 (- maxy miny))
                       1.0))
        (setq dims (lfc:sort-dims dims rowtol))

        ;; grey out the whole selection so each item can take the
        ;; stage, stashing every original colour in xdata first so
        ;; LINFINCHECKRESCUE can recover them even after a crash
        (setq i 0)
        (repeat (sslength ss)
          (setq e (ssname ss i)
                i (1+ i))
          (if (entget e)
            (progn
              (setq saved (cons (cons e (lfc:ent-color e)) saved))
              (lfc:stash-color e (lfc:ent-color e))
              (lfc:set-color e *lfc-grey-color*))))

        ;; --- dimensions, one at a time -----------------------------
        (if dims
          (princ (strcat "\n--- Reviewing " (itoa (length dims))
                         " dimension(s): Enter = correct, N = flag to fix, "
                         "B = back one, S = skip the rest ---")))
        ;; index-based so Back can step to the previous dimension and
        ;; Skip can leave the rest unreviewed without losing the report
        (setq n 0 total (length dims) dlines nil skiprest nil)
        (while (and (< n total) (not skiprest))
          (setq e   (nth n dims)
                res nil)
          (lfc:set-color e (cdr (assoc e saved)))       ; step into the light
          (setq res (lfc:review-dim e cands (1+ n) total))
          ;; points already moved count however the prompt was answered
          (setq ndmoved (+ ndmoved (cadddr res)))
          (cond
            ((eq (cadr res) 'skip)
             (lfc:set-color e *lfc-grey-color*)
             (setq skiprest T)
             (princ (strcat "\n  Skipping the remaining "
                            (itoa (- total n)) " dimension(s).")))
            ((eq (cadr res) 'back)
             ;; undo what the previous item recorded, then redo it
             (lfc:set-color e *lfc-grey-color*)
             (if (> n 0)
               (progn
                 (setq n  (1- n)
                       e1 (nth n dims))
                 (if (car dlines)                        ; roll back its tally
                   (progn
                     (if (cadr (car dlines))
                       (setq ndok (1- ndok))
                       (setq ndflag (1- ndflag)))
                     ;; A MOVED POINT STAYS MOVED.  Back re-asks the
                     ;; question; it does not put the point back, and
                     ;; its construction line is still standing.  So
                     ;; the move is CARRIED to the re-review, not
                     ;; un-counted -- subtracting it made the report
                     ;; claim "points adjusted: 0" over a drawing
                     ;; whose points really had been adjusted, and
                     ;; the rebuilt line lost its "moved" note with
                     ;; it (the second pass finds them attached and
                     ;; has nothing to report).
                     (if (> (caddr (car dlines)) 0)
                       (setq carried (cons (cons e1 (caddr (car dlines)))
                                           (vl-remove (assoc e1 carried)
                                                      carried))))
                     (setq dlines (cdr dlines))))
                 (setq keep (vl-remove e1 keep))
                 (lfc:set-color e1 *lfc-grey-color*)
                 (princ "\n  Stepping back one dimension."))
               (princ "\n  Already at the first dimension."))
             (setq n (1- n)))                            ; loop's 1+ re-enters it
            (t
             (if (cadr res)
               (progn (setq ndok (1+ ndok))
                      (lfc:set-color e *lfc-grey-color*))
               (progn (setq ndflag (1+ ndflag))
                      (setq keep (cons e keep))))
             (setq sty (lfc:dim-style e))
             ;; moves this dim collected on an earlier pass, before a
             ;; Back sent us round again -- they are real and belong
             ;; in both the line and the tally
             (setq cmv (cond ((cdr (assoc e carried))) (0)))
             (setq dlines (cons (list (strcat "Dim " (car res)
                                              (if (= sty "") "" (strcat " [" sty "]"))
                                              (if (nth 4 res)
                                                (strcat " = " (nth 4 res))
                                                "")
                                              ": " (caddr res)
                                              (if (> cmv 0)
                                                (strcat " - " (itoa cmv)
                                                        " point(s) moved before"
                                                        " you stepped back")
                                                ""))
                                      (cadr res)
                                      (+ (cadddr res) cmv))
                                dlines))))
          (setq n (1+ n)))
        (if skiprest
          (setq lines (cons (strcat "Dimensions: " (itoa (- total (length dlines)))
                                    " left UNREVIEWED (skipped by user)")
                            lines)))
        (foreach pair (reverse dlines)
          (setq lines (cons (car pair) lines)))

        ;; --- arcs, one endpoint at a time --------------------------
        (if arcs
          (princ (strcat "\n--- Reviewing " (itoa (length arcs))
                         " arc(s): checking endpoint attachment ---")))
        (setq n 0 total (length arcs))
        (foreach e arcs
          (setq n (1+ n))
          (lfc:set-color e (cdr (assoc e saved)))
          (setq res (lfc:review-arc e cands n total))
          (setq nasnap (+ nasnap (cadddr res)))
          (if (cadr res)
            (progn (setq naok (1+ naok))
                   (lfc:set-color e *lfc-grey-color*))
            (progn (setq namoved (1+ namoved))
                   (setq keep (cons e keep))))           ; moved: stays magenta
          (setq lines (cons (strcat "Arc " (car res) ": " (caddr res)) lines)))

        ;; --- overlapping lines, one pair at a time ------------------
        (setq olaps (lfc:find-overlaps segs))
        (if olaps
          (princ (strcat "\n--- Reviewing " (itoa (length olaps))
                         " overlapping line pair(s): Enter = merge, F = flag, L = leave ---")))
        (setq n 0 total (length olaps))
        (foreach pr olaps
          (setq n  (1+ n)
                e1 (lfc:seg-ent (car pr))
                e2 (lfc:seg-ent (cadr pr)))
          (lfc:stage e1 saved keep)
          (lfc:stage e2 saved keep)
          (setq res (lfc:review-olap (car pr) (cadr pr) n total))
          (cond
            ((null res)                       ; absorbed by an earlier merge
             (lfc:unstage e1 keep)
             (lfc:unstage e2 keep))
            ((eq (caddr res) 'left)
             (setq noleft (1+ noleft))
             (lfc:unstage e1 keep)
             (lfc:unstage e2 keep)
             (setq lines (cons (strcat "Lines " (car res) ": " (cadr res)) lines)))
            (t
             (if (eq (caddr res) 'merged)
               (setq nomerged (1+ nomerged))
               (setq noflag (1+ noflag)))
             (setq keep (append (cdddr res) keep))
             (setq lines (cons (strcat "Lines " (car res) ": " (cadr res)) lines)))))

        ;; --- step / staircase check ---------------------------------
        ;; hunt down to the bench minimum so a two-tread bench profile
        ;; is still found; the staircase test below keeps the extra
        ;; short groups from being mistaken for side views
        (setq sgroups  (lfc:step-groups
                         segs
                         (min *lfc-step-minlines* *lfc-bench-minlines*))
              svgroups nil
              stepsp   nil
              svmode   nil
              satts    nil
              attwrong nil
              attundec nil
              bgroups  nil)
        ;; a staircase side view reads as two step patterns at right
        ;; angles to each other (treads + risers) in the same spot
        (setq scand (vl-remove-if-not 'lfc:staircase-p sgroups))
        (setq rest scand)
        (while rest
          (setq g1 (car rest))
          (foreach g2 (cdr rest)
            (if (and (> (cal:ang-diff (car g1) (car g2)) (- (* 0.5 pi) 0.09))
                     (lfc:boxes-touch (lfc:pts-bbox (cdr g1))
                                       (lfc:pts-bbox (cdr g2))
                                       *lfc-step-maxgap*))
              (progn
                (if (not (member g1 svgroups)) (setq svgroups (cons g1 svgroups)))
                (if (not (member g2 svgroups)) (setq svgroups (cons g2 svgroups))))))
          (setq rest (cdr rest)))
        ;; only full-size patterns are worth asking about; the short
        ;; bench-sized ones matter solely as side-view halves
        (setq pgroups (vl-remove-if
                        '(lambda (g)
                           (or (member g svgroups)
                               (< (length (cdr g)) *lfc-step-minlines*)))
                        sgroups))
        (cond
          (svgroups                           ; staircase drawing found
           (setq stepsp  T
                 svmode  'auto
                 bgroups pgroups)             ; plan-view patterns
           (princ "\n--- Step check: staircase side view detected in the selection ---")
           (setq lines (cons (strcat "Steps: staircase side view detected ("
                                     (itoa (length svgroups)) " step pattern(s))")
                             lines))
           (foreach g pgroups
             (setq lines (cons (strcat "Steps: pattern of " (itoa (length (cdr g)))
                                       " parallel lines (side view already present)")
                               lines))))
          (pgroups                            ; possible steps, no staircase drawing
           (princ (strcat "\n--- Step check: " (itoa (length pgroups))
                          " possible step pattern(s), no staircase side view found ---"))
           (setq n 0 total (length pgroups))
           (foreach g pgroups
             (setq n (1+ n))
             (foreach e (lfc:group-ents g) (lfc:stage e saved keep))
             (lfc:zoom-box (lfc:pts-bbox (cdr g)))
             (foreach e (lfc:group-ents g) (if (entget e) (redraw e 3)))
             (princ (strcat "\n\nStep pattern " (itoa n) " of " (itoa total) ": "
                            (itoa (length (cdr g)))
                            " parallel lines stacked less than "
                            (rtos *lfc-step-maxgap*) " apart."))
             (setq ans (cal:ask-yn "\n  Are these lines steps?" "Yes"))
             (foreach e (lfc:group-ents g) (if (entget e) (redraw e 4)))
             (foreach e (lfc:group-ents g) (lfc:unstage e keep))
             (redraw)
             (if ans
               (setq stepsp  T
                     bgroups (cons g bgroups)))
             (setq lines (cons (strcat "Steps: pattern of " (itoa (length (cdr g)))
                                       " parallel lines - "
                                       (if ans "CONFIRMED as steps" "not steps"))
                               lines)))))
        (if stepsp
          (progn
            (if (null svmode)                 ; steps confirmed, no side view seen
              (progn
                (princ "\n  Steps confirmed but no staircase side view was detected.")
                (if (cal:ask-yn "\n  Is a side view of the steps drawn somewhere?" "Yes")
                  (setq svmode 'user))))
            (if (null svmode)
              (progn
                (princ "\n  Note: ADD A SIDE VIEW of the steps.")
                (setq lines (cons "Steps: NO SIDE VIEW - add a side view of the steps"
                                  lines)))
              (progn                          ; side view present: demand the block
                (setq satts (vl-remove-if-not
                              '(lambda (b) (lfc:ins-matches b "Step Attachment"))
                              blks))
                (if (null satts)
                  (progn
                    (princ "\n  Note: no 'Step Attachment' block found - add one.")
                    (setq lines (cons "Steps: side view present but NO 'Step Attachment' block - add one"
                                      lines)))
                  (foreach b satts
                    (lfc:stage b saved keep)
                    (lfc:zoom-ent b)
                    (redraw b 3)
                    (setq ans (cal:ask-yn
                                (strcat "\n  Step Attachment block "
                                        (cdr (assoc 5 (entget b)))
                                        " - is the correct one placed?")
                                "Yes"))
                    (redraw b 4)
                    (redraw)
                    (if ans
                      (progn
                        (lfc:unstage b keep)
                        (setq lines (cons (strcat "Step Attachment "
                                                  (cdr (assoc 5 (entget b)))
                                                  ": confirmed correct")
                                          lines)))
                      (progn
                        (setq attwrong T)
                        (lfc:set-color b *lfc-flag-color*)
                        (setq keep (cons b keep))
                        (setq lines (cons (strcat "Step Attachment "
                                                  (cdr (assoc 5 (entget b)))
                                                  ": WRONG ONE - flagged to fix (red)")
                                          lines))))
                    ;; every option still showing = nobody picked one,
                    ;; so the drawing has to ask the question instead
                    (if (lfc:attach-undecided-p b)
                      (if (lfc:drawing-has-phrase *lfc-secured-phrase*)
                        (progn
                          (setq attundec 'asked)
                          (princ (strcat "\n  All "
                                         (itoa (length *lfc-attach-options*))
                                         " attachment options are still showing, and the drawing asks '"
                                         *lfc-secured-phrase* "?' - waiting on the customer."))
                          (setq lines (cons (strcat "Step Attachment "
                                                    (cdr (assoc 5 (entget b)))
                                                    ": all "
                                                    (itoa (length *lfc-attach-options*))
                                                    " options still shown ("
                                                    (lfc:join *lfc-attach-options* "/")
                                                    ") and a '" *lfc-secured-phrase*
                                                    "?' note is present - waiting on the customer")
                                            lines)))
                        (progn
                          (setq attundec 'unasked)
                          (princ (strcat "\n  Note: all attachment options are still showing but NOTHING asks '"
                                         *lfc-secured-phrase* "?' - add the note."))
                          (setq lines (cons (strcat "Step Attachment "
                                                    (cdr (assoc 5 (entget b)))
                                                    ": all "
                                                    (itoa (length *lfc-attach-options*))
                                                    " options still shown ("
                                                    (lfc:join *lfc-attach-options* "/")
                                                    ") but NOTHING asks '"
                                                    *lfc-secured-phrase*
                                                    "?' - add the note")
                                            lines)))))))))))

        ;; --- Bead Track check (bead step attachments only) ----------
        ;; when the attachment style is "Bead Step Attachment", each
        ;; plan-view step pattern needs bead track drawn nearby; the
        ;; side view is exempt. The WHOLE drawing is searched, not
        ;; just the selection.
        (setq beadneed nil beadok 0 beadmiss 0)
        (if (and satts
                 bgroups
                 (vl-some '(lambda (b) (lfc:ins-matches b "Bead Step Attachment"))
                          satts))
          (progn
            (setq beadneed T)
            (princ (strcat "\n--- Bead Track check: attachment style is 'Bead Step Attachment' ---"))
            (setq beadss  (ssget "_X" (list (cons 8 *lfc-bead-layer*)))
                  beadbbs nil
                  i       0)
            (if beadss
              (repeat (sslength beadss)
                (setq bb (cal:bbox-ent (ssname beadss i))
                      i  (1+ i))
                (if bb (setq beadbbs (cons bb beadbbs)))))
            ;; bead track drawn INSIDE a block never lands in that
            ;; layer filter, so take the box of any insert whose
            ;; definition carries the layer
            (setq beadss (ssget "_X" '((0 . "INSERT")))
                  i      0)
            (if beadss
              (repeat (sslength beadss)
                (setq b (ssname beadss i)
                      i (1+ i))
                (if (lfc:block-has-layer-p (cdr (assoc 2 (entget b)))
                                            *lfc-bead-layer* 2)
                  (progn
                    (setq bb (cal:bbox-ent b))
                    (if bb (setq beadbbs (cons bb beadbbs)))))))
            (foreach g bgroups
              (setq gbb (lfc:pts-bbox (cdr g)))
              (if (and gbb beadbbs (lfc:bead-near-p gbb beadbbs))
                (progn
                  (setq beadok (1+ beadok))
                  (setq lines (cons (strcat "Bead Track: present near step pattern of "
                                            (itoa (length (cdr g))) " lines")
                                    lines)))
                (progn
                  (setq beadmiss (1+ beadmiss))
                  (princ (strcat "\n  Note: nothing on layer '" *lfc-bead-layer*
                                 "' near a step pattern - add bead track."))
                  (setq lines (cons (strcat "Bead Track: NOTHING on layer '"
                                            *lfc-bead-layer*
                                            "' near step pattern of "
                                            (itoa (length (cdr g)))
                                            " lines - add bead track")
                                    lines)))))))

        ;; --- Tech Title WallHt & overall height ---------------------
        ;; the title block's wall height is validated whenever a Tech
        ;; Title exists - steps or no steps - and the side view's rise
        ;; is compared against it when steps are present
        (setq htsum nil stepht nil wallht nil wallraw nil tins nil
              svbb nil hdim nil dimht nil htval nil htbad nil
              wallvals nil wallvar nil wallmany nil htskip nil
              wallzero nil wallask nil)
        ;; overall height from the steps
        (if stepsp
          (cond
            ((eq svmode 'auto)               ; side view found: measure it
             (setq svbb (lfc:pts-bbox (apply 'append (mapcar 'cdr svgroups))))
             (if svbb (setq stepht (- (cadr (cadr svbb)) (cadr (car svbb))))))
            ((eq svmode 'user)               ; user says it exists elsewhere
             (princ "\n  Confirm the overall step height against the Tech Title.")
             (setq stepht (getdist "\n  Type the overall step height or pick two points <skip>: ")))))
        ;; every Tech Title block: those in the selection, else
        ;; drawing-wide; the one nearest the checked area wins, and
        ;; titles that disagree on WallHt are called out
        (setq tpat  (strcat "*" (lfc:squash *lfc-title-block*) "*")
              tlist nil)
        (foreach b blks
          (if (wcmatch (lfc:squash (lfc:block-name b)) tpat)
            (setq tlist (cons b tlist))))
        (if (null tlist)
          (progn
            (setq tss (ssget "_X" '((0 . "INSERT")))
                  i   0)
            (if tss
              (repeat (sslength tss)
                (setq b (ssname tss i)
                      i (1+ i))
                (if (wcmatch (lfc:squash (lfc:block-name b)) tpat)
                  (setq tlist (cons b tlist)))))))
        (setq cx (if minx (* 0.5 (+ minx maxx)) 0.0)
              cy (if miny (* 0.5 (+ miny maxy)) 0.0)
              tbest nil)
        (foreach b tlist
          (setq bp (cdr (assoc 10 (entget b)))
                d  (distance (list cx cy) (list (car bp) (cadr bp))))
          (if (or (null tbest) (< d tbest))
            (setq tbest d
                  tins  b)))
        (if (> (length tlist) 1)
          (progn
            (setq tvals nil)
            (foreach b tlist
              (setq s (lfc:ins-attrib b *lfc-wallht-tag*))
              (if s
                (progn
                  (setq s (lfc:norm-text (lfc:after-eq s)))
                  (if (not (member s tvals))
                    (setq tvals (cons s tvals))))))
            (if (> (length tvals) 1)
              (progn
                (princ (strcat "\n  Note: " (itoa (length tlist)) " '"
                               *lfc-title-block* "' blocks disagree on "
                               *lfc-wallht-tag* "; using the nearest one."))
                (setq lines (cons (strcat (itoa (length tlist)) " '"
                                          *lfc-title-block*
                                          "' blocks DISAGREE on "
                                          *lfc-wallht-tag*
                                          " - CHECK THE WALL HEIGHT (nearest one used)")
                                  lines))))))
        (if tins
          (setq wallraw  (lfc:ins-attrib-deep tins *lfc-wallht-tag*)
                wallvals (if wallraw (lfc:len-values wallraw))
                wallvar  (and wallraw (lfc:varies-p wallraw))
                wallmany (> (length wallvals) 1)
                wallzero (and wallvals (not wallmany)
                              (< (car wallvals) *lfc-min-wallht*))
                wallask  (and (null wallvals)
                              wallraw
                              (vl-string-search "?" (lfc:after-eq wallraw)))
                wallht   (if (and wallvals (not wallmany) (not wallzero))
                           (car wallvals))))
        ;; Varies, several heights, a nonsensical zero or a "?" give
        ;; nothing to check the side view against - leave it alone
        ;; rather than marking a dimension red
        (setq htskip (or wallvar wallmany wallzero wallask))
        ;; the side view's own overall-height dimension, and the
        ;; height it states - that dimension is what gets compared
        (if (and svbb stepht (not htskip))
          (setq hdim (lfc:height-dim dims svbb stepht)))
        (if hdim (setq dimht (lfc:dim-stated hdim)))
        (setq htval (if dimht dimht stepht))
        (setq htbad (and htval wallht
                         (> (abs (- htval wallht)) *lfc-height-tol*)))
        ;; a dimension that disagrees with the title block is wrong:
        ;; mark it red automatically and keep it red
        (if (and htbad hdim)
          (progn
            (lfc:set-color hdim *lfc-flag-color*)
            (if (not (member hdim keep)) (setq keep (cons hdim keep)))
            (princ (strcat "\n  Side view height dimension "
                           (cdr (assoc 5 (entget hdim)))
                           " disagrees with " *lfc-wallht-tag*
                           " - marked red."))
            (setq lines (cons (strcat "Height dim "
                                      (cdr (assoc 5 (entget hdim)))
                                      " states " (rtos dimht)
                                      " but " *lfc-wallht-tag* " is '"
                                      wallraw "' - MISMATCH, marked red")
                              lines))))
        ;; a dimension whose text was overridden to disagree with
        ;; the geometry it spans is wrong too
        (if (and hdim dimht stepht
                 (> (abs (- dimht stepht)) *lfc-height-tol*))
          (progn
            (lfc:set-color hdim *lfc-flag-color*)
            (if (not (member hdim keep)) (setq keep (cons hdim keep)))
            (setq lines (cons (strcat "Height dim "
                                      (cdr (assoc 5 (entget hdim)))
                                      " states " (rtos dimht)
                                      " but the side view is drawn "
                                      (rtos stepht)
                                      " tall - MISMATCH, marked red")
                              lines))))
        (setq htsum
          (cond
            ((and (null tins) stepsp)
             (strcat "steps rise " (if htval (rtos htval) "?") " but no '"
                     *lfc-title-block* "' block was found - NOT CONFIRMED"))
            ((null tins) nil)                 ; no title, no steps: quiet
            (wallvar
             (strcat *lfc-wallht-tag* " reads '" wallraw "' - height varies"
                     (if htval ", side view left alone" "")))
            (wallmany
             (strcat *lfc-wallht-tag* " holds " (itoa (length wallvals))
                     " heights ('" wallraw "') - CHECK THE WALL HEIGHT in the "
                     *lfc-title-block*
                     (if htval ", side view left alone" "")))
            (wallzero
             (strcat *lfc-wallht-tag* " is '" wallraw
                     "' - a NONSENSICAL wall height, fix the "
                     *lfc-title-block*))
            (wallask
             (if (lfc:drawing-has-phrase *lfc-ask-phrase*)
               (strcat *lfc-wallht-tag* " reads '" wallraw
                       "' and the drawing asks for the wall height - waiting on the customer")
               (strcat *lfc-wallht-tag* " reads '" wallraw
                       "' but NOTHING in the drawing asks for it - add a '"
                       *lfc-ask-phrase* "' note for the customer")))
            ((null wallht)
             (strcat "the " *lfc-wallht-tag* " attribute "
                     (if wallraw
                       (strcat "'" wallraw "' is unreadable")
                       "is missing")
                     " - NOT CONFIRMED"))
            ((null htval)
             (if stepsp
               "steps present but their overall height was NOT CONFIRMED (no side view measured)"
               (strcat *lfc-wallht-tag* " = '" wallraw "' - OK")))
            ((not htbad)
             (strcat "steps rise " (rtos htval) " = WallHt '" wallraw
                     "' - MATCHES"))
            (t
             (strcat "steps rise " (rtos htval) " but WallHt is '" wallraw
                     "' (" (rtos wallht) ") - MISMATCH"
                     (if hdim ", dimension marked red" ", look at it")))))
        (if htsum (princ (strcat "\n  Wall height: " htsum)))

        ;; --- Tech Title Date ------------------------------------------
        ;; runs whenever a Tech Title exists, independent of steps
        (setq datesum nil dateraw nil datebad nil)
        (if tins
          (progn
            (setq dateraw (lfc:ins-attrib-deep tins *lfc-date-tag*))
            (setq datebad
              (if dateraw
                (lfc:date-verdict dateraw)
                "is missing - expected MM/DD/YYYY"))
            (setq datesum
              (if datebad
                (strcat *lfc-date-tag* " " datebad)
                (strcat *lfc-date-tag* " = '" dateraw "' - OK")))
            (princ (strcat "\n  Date: " datesum)))
          (setq datesum (strcat "no '" *lfc-title-block*
                                "' block in reach - date NOT CHECKED")))

        ;; --- Liner Material check -----------------------------------
        (setq liners      (vl-remove-if-not
                            '(lambda (b) (lfc:ins-matches b "Liner Material"))
                            blks)
              linerbadw   nil
              linernostep nil
              linerstep   nil
              linerfg     nil
              linerwiped  0
              fgstep      (lfc:fgstep-src ss blks))
        (if fgstep
          (princ (strcat "\n--- Fiberglass Step found in the highlighted area: "
                         fgstep " ---")))
        (if (null liners)
          (progn
            (princ "\n--- Liner check: no 'Liner Material' block in the selection ---")
            (setq lines (cons "Liner Material: NO block found - add 'Liner Material' or 'Liner Material with Step'"
                              lines)))
          (progn
            (princ (strcat "\n--- Liner check: " (itoa (length liners))
                           " 'Liner Material' block(s) found ---"))
            (foreach b liners
              (setq bn      (lfc:block-name b)
                    bh      (cdr (assoc 5 (entget b)))
                    bp      (cdr (assoc 10 (entget b)))
                    badtags (lfc:attrib-bad-tags b *lfc-badwords*)
                    bad     nil)
              (foreach w *lfc-badwords*
                (if (lfc:ins-has-word b w)
                  (setq bad (append bad (list w)))))
              (foreach w bad
                (if (not (member w linerbadw))
                  (setq linerbadw (append linerbadw (list w)))))
              (cond
                ;; a pattern field that says "Not Supplied" or carries an
                ;; ERROR was never filled in - wipe it back to blank so
                ;; the block reads clean, and say which fields went
                (badtags
                 (lfc:wipe-attribs b badtags)
                 (setq linerwiped (+ linerwiped (length badtags)))
                 (princ (strcat "\n  '" bn "': wiped "
                                (lfc:join badtags ", ") " clean."))
                 (setq lines (cons (strcat "Liner Material (" bn ") " bh " at "
                                           (lfc:ptstr bp) ": "
                                           (lfc:join badtags ", ")
                                           " carried " (lfc:join bad " & ")
                                           " - WIPED clean")
                                   lines)))
                ;; the word sits in the block's own text, not in a field
                ;; we can clear - report it and leave it alone
                (bad
                 (princ (strcat "\n  Note: '" bn "' contains the word "
                                (lfc:join bad " & ") " - look at it."))
                 (setq lines (cons (strcat "Liner Material (" bn ") " bh " at "
                                           (lfc:ptstr bp)
                                           ": contains the word "
                                           (lfc:join bad " & ")
                                           " - look at it")
                                   lines)))
                (t
                 (setq lines (cons (strcat "Liner Material (" bn ") " bh ": OK")
                                   lines)))))
            (setq linerstep (vl-some '(lambda (b) (lfc:ins-has-word b "STEP"))
                                     liners))
            (cond
              ;; a fiberglass step is its own unit - the liner pattern
              ;; must NOT carry a step of its own
              (fgstep
               (if linerstep
                 (progn
                   (setq linerfg T)
                   (princ "\n  Note: a Fiberglass Step is in the drawing but the liner pattern has a Step.")
                   (setq lines (cons (strcat "Liner Material: a Fiberglass Step ("
                                             fgstep
                                             ") is in the drawing but the liner pattern HAS a Step - it should not")
                                     lines)))))
              ;; otherwise steps drawn -> the liner pattern must cover them
              ((and stepsp (not linerstep))
               (setq linernostep T)
               (princ "\n  Note: steps are drawn but the liner pattern is MISSING its Step.")
               (setq lines (cons "Liner Material: steps are drawn but the liner pattern is MISSING its 'Step' - use 'Liner Material with Step'"
                                 lines))))))

        ;; --- restore colours (flagged/moved keep theirs) ------------
        ;; restored entities drop their rescue stash; flagged/moved
        ;; ones keep it so LINFINCHECKRESCUE can clear the marks later
        (foreach pair saved
          (if (and (not (member (car pair) keep)) (entget (car pair)))
            (progn
              (lfc:set-color (car pair) (cdr pair))
              (lfc:unstash (car pair)))))
        (foreach l relock (lfc:set-layer-lock l T))
        (setq relock nil)

        ;; --- title block border size --------------------------------
        ;; the whole title block is normally in the selection; fall
        ;; back to the drawing when the border was not highlighted
        (setq bordbb (lfc:border-box ss))
        (if (null bordbb)
          (setq bordbb (lfc:border-box
                         (ssget "_X" (list (cons 8 *lfc-border-layer*))))))
        (setq bordsum (lfc:border-verdict bordbb))
        (princ (strcat "\n--- Border: " bordsum " ---"))

        ;; --- one-line verdicts for steps & liner --------------------
        (setq stepsum
              (cond
                ((null sgroups) "no step patterns detected")
                ((not stepsp)
                 (strcat (itoa (length sgroups))
                         " pattern(s) reviewed - none are steps"))
                (t
                 (strcat "steps present; side view "
                         (cond ((eq svmode 'auto) "detected")
                               ((eq svmode 'user) "confirmed by user")
                               (t "MISSING - add one"))
                         (cond ((null svmode) "")
                               ((null satts)
                                "; Step Attachment block MISSING - add one")
                               (attwrong
                                "; Step Attachment flagged WRONG (red)")
                               (t "; Step Attachment confirmed"))
                         (cond ((eq attundec 'unasked)
                                (strcat "; every attachment option still shown, NOTHING asks '"
                                        *lfc-secured-phrase* "?'"))
                               ((eq attundec 'asked)
                                "; attachment not chosen yet, the drawing asks the question")
                               (t ""))
                         (cond ((not beadneed) "")
                               ((> beadmiss 0)
                                (strcat "; Bead Track MISSING near "
                                        (itoa beadmiss) " pattern(s)"))
                               (t "; Bead Track present"))))))
        (setq linersum
              (cond
                ((null liners)
                 "block MISSING - add 'Liner Material' (or 'with Step')")
                (t
                 (strcat (itoa (length liners)) " block(s) found"
                         (if (> linerwiped 0)
                           (strcat "; " (itoa linerwiped)
                                   " pattern field(s) WIPED clean")
                           (if linerbadw
                             (strcat "; word " (lfc:join linerbadw " & ")
                                     " found - review")
                             ""))
                         (if linernostep
                           "; steps drawn but liner MISSING its Step"
                           "")
                         (if linerfg
                           "; Fiberglass Step in the drawing but the liner HAS a Step"
                           "")
                         (if (and (null linerbadw) (not linernostep) (not linerfg)
                                  (= linerwiped 0))
                           " - OK"
                           "")))))

        ;; --- report on the right side, to scale with the drawing ----
        ;; the liner-finish checks lead on the main sheet; the
        ;; DIMCHECK-style findings go in the DIMENSION AUDIT column
        ;; beside it
        (setq dhdr
          (list
            (cons (strcat "Dimensions checked: " (itoa (length dims))
                          " (correct: " (itoa ndok)
                          ", flagged to fix: " (itoa ndflag)
                          ", points adjusted: " (itoa ndmoved) ")")
                  (> ndflag 0))
            (cons (strcat "Arcs checked: " (itoa (length arcs))
                          " (OK: " (itoa naok)
                          ", with endpoints moved: " (itoa namoved)
                          ", endpoints moved in total: " (itoa nasnap) ")")
                  (> namoved 0))
            (cons (strcat "Overlapping line pairs: " (itoa (length olaps))
                          (if olaps
                            (strcat " (merged: " (itoa nomerged)
                                    ", flagged: " (itoa noflag)
                                    ", left as drawn: " (itoa noleft) ")")
                            " - none found"))
                  (> noflag 0))))
        (setq dimlay (lfc:dimlayer-verdict dims)
              units  (lfc:audit-units ss))
        (foreach l (caddr units)
          (princ (strcat "\n  " l))
          (setq lines (cons l lines)))
        (setq hdr
          (list
            (cons (strcat "Dimension layer: " (car dimlay)) (cdr dimlay))
            (cons (strcat "Feet & inches: " (car units)) (cadr units))
            (cons (strcat "Steps: " stepsum)          (lfc:attn-p stepsum))
            (cons (strcat "Liner Material: " linersum) (lfc:attn-p linersum))
            (cons (strcat "Title block border: " bordsum) (lfc:attn-p bordsum))))
        (if htsum
          (setq hdr (append hdr (list (cons (strcat "Wall height: " htsum)
                                            (lfc:attn-p htsum))))))
        (if datesum
          (setq hdr (append hdr (list (cons (strcat "Date: " datesum)
                                            (lfc:attn-p datesum))))))
        (setq right (lfc:write-report "LINFINCHECK REPORT" nil hdr dhdr
                                      (reverse lines) nil
                                      minx miny maxx maxy))

        ;; --- show the drawing plus the report -----------------------
        (if minx
          (progn
            (setq m (* 0.05 (max (- maxx minx) (- maxy miny) 1.0)))
            (command "_.ZOOM" "_Window"
                     (trans (list (- minx m) (- miny m) 0.0) 0 1)
                     (trans (list (+ right m) (+ maxy m) 0.0) 0 1)))
          (command "_.ZOOM" "_Center" vc vs))

        (command "_.UNDO" "_End")
        (setq undo-open nil)
        (setvar "CMDECHO" oldecho)
        (princ (strcat "\n\n--- LINFINCHECK complete ---"
                       "\nDimensions: " (itoa (length dims)) " checked, "
                       (itoa ndok) " correct, "
                       (itoa ndflag) " flagged to fix (red)"
                       (if (> ndmoved 0)
                         (strcat ", " (itoa ndmoved) " point(s) adjusted")
                         "")
                       "\nArcs: " (itoa (length arcs)) " checked, "
                       (itoa namoved) " with endpoint(s) moved ("
                       (itoa nasnap) " endpoint(s), magenta)"
                       "\nOverlapping lines: " (itoa (length olaps)) " pair(s) found"
                       (if olaps
                         (strcat ", " (itoa nomerged) " merged, "
                                 (itoa noflag) " flagged (cyan), "
                                 (itoa noleft) " left as drawn")
                         "")
                       "\nSteps: " stepsum
                       (if htsum (strcat "\nWall height: " htsum) "")
                       (if datesum (strcat "\nDate: " datesum) "")
                       "\nLiner Material: " linersum
                       "\nTitle block border: " bordsum
                       "\nReport placed on the right side of the drawing (layer "
                       *lfc-report-layer* ")."
                       (if (> ndmoved 0)
                         (strcat "\nConstruction lines through moved dimensions' original points are on layer "
                                 *lfc-constr-layer* ".")
                         "")
                       "\nOne UNDO reverts everything LINFINCHECK changed (including the report)."))))))
  (princ))

;; --- LINFINSCAN / LITELINFINSCAN: the read-only twins -----------------
;;  LITELINFINSCAN skips the DIMCHECK-style pass entirely - no
;;  dimension, arc or overlap audit and no DIMENSION AUDIT column -
;;  for a drawing DIMCHECK already went over.
;;  Runs every audit, asks nothing, and changes nothing in the drawing
;;  except writing the report. Use it as a quick pre-flight, or when
;;  you want the findings without touching a released sheet.

(defun c:LINFINSCAN () (lfc:scan nil))

(defun c:LITELINFINSCAN () (lfc:scan T))

;; The read-only scan.  lite = T skips the DIMCHECK-style pass - no
;; dimension, arc or overlap audit and no DIMENSION AUDIT column -
;; for a drawing DIMCHECK already went over.
(defun lfc:scan (lite / *error* oldecho name ss i e et ed cands dims arcs
                     plns segs
                     blks lines olaps pr sgroups scand svgroups pgroups
                     g g1 g2 rest svbb stepht satts liners fgstep linerstep
                     beadss beadbbs bb gbb tlist tins bp cx cy d tbest
                     wallraw wallvals wallvar wallmany wallzero wallask
                     wallht hdim dimht
                     htval htbad htsum stepsum linersum bad wnd
                     datesum dateraw datebad
                     nd ndbad na nabad m hdr dhdr l badtags dimlay units
                     bordbb bordsum attundec
                     minx miny maxx maxy p13 p14 near s b w)

  (setq name (if lite "LITELINFINSCAN" "LINFINSCAN"))
  (defun *error* (msg)
    (if oldecho (setvar "CMDECHO" oldecho))
    (if (and msg (not (wcmatch (strcase msg) "*BREAK*,*CANCEL*,*QUIT*,*EXIT*")))
      (princ (strcat "\n" name " error: " msg)))
    (princ))

  (prompt (strcat "\nHighlight the drawing to " name
                  " (Enter = whole drawing): "))
  (setq ss (ssget))
  (if (null ss) (setq ss (ssget "_X")))
  (cond
    ((null ss) (prompt "\nNothing to scan."))
    (t
     (setq oldecho (getvar "CMDECHO"))
     (setvar "CMDECHO" 0)
     (setq i 0 nd 0 ndbad 0 na 0 nabad 0)
     (repeat (sslength ss)
       (setq e  (ssname ss i)
             i  (1+ i)
             et (cdr (assoc 0 (entget e))))
       (if (= et "DIMENSION") (setq dims (cons e dims)))
       (if (= et "ARC") (setq arcs (cons e arcs)))
       (if (member et '("LINE" "LWPOLYLINE" "POLYLINE")) (setq plns (cons e plns)))
       (if (= et "INSERT") (setq blks (cons e blks)))
       (if (member et *lfc-curve-types*) (setq cands (cons e cands)))
       (setq bb (cal:bbox-ent e))
       (if bb
         (setq minx (if minx (min minx (caar bb)) (caar bb))
               miny (if miny (min miny (cadar bb)) (cadar bb))
               maxx (if maxx (max maxx (caadr bb)) (caadr bb))
               maxy (if maxy (max maxy (cadadr bb)) (cadadr bb)))))
     ;; segs feeds TWO passes: the DIMCHECK-style overlap hunt, which a
     ;; lite scan skips, and the steps / side-view rule, which is a
     ;; LINER rule a lite scan keeps.  Nil'ing it for lite took the
     ;; steps rule out with the overlaps, so a sheet with an obvious
     ;; staircase reported "no step patterns detected" and its
     ;; rise-vs-WallHt mismatch vanished.  Collect it either way; the
     ;; overlap pass keeps its own lite guard below.
     (setq dims (reverse dims) arcs (reverse arcs)
           plns (reverse plns) blks (reverse blks) cands (reverse cands)
           segs (lfc:collect-segs plns))

     ;; --- dimensions: report stray definition points, move nothing
     ;;     (a lite scan leaves the DIMCHECK-style pass out entirely)
     (foreach e (if lite
                  nil
                  (lfc:sort-dims dims (if (and miny maxy)
                                        (* 0.05 (- maxy miny)) 1.0)))
       (setq ed  (entget e)
             nd  (1+ nd)
             p13 (cdr (assoc 13 ed))
             p14 (cdr (assoc 14 ed))
             bad nil)
       (if (member (logand 7 (cdr (assoc 70 ed))) '(0 1))
         (foreach s (list (cons "point 1" p13) (cons "point 2" p14))
           (if (cdr s)
             (progn
               (setq near (lfc:nearest-curve (cdr s) nil cands))
               (if (and near (> (caddr near) *lfc-tol*))
                 (setq bad (append bad (list (strcat (car s) " off by "
                                                     (rtos (caddr near) 2 4))))))))))
       (if bad (setq ndbad (1+ ndbad)))
       (setq lines (cons (strcat "Dim " (cdr (assoc 5 ed))
                                 (if (= (lfc:dim-style e) "") ""
                                   (strcat " [" (lfc:dim-style e) "]"))
                                 (if (lfc:dim-meas e)
                                   (strcat " = " (lfc:dim-meas e)) "")
                                 ": "
                                 (if bad
                                   (strcat "NOT attached - " (lfc:join bad ", "))
                                   "OK")
                                 (if (lfc:dim-assoc-p e) " (associative)" ""))
                         lines)))

     ;; --- arcs: report unattached endpoints, move nothing
     (foreach e (if lite nil arcs)
       (setq na  (1+ na)
             bad nil)
       (if (lfc:planar-arc-p (entget e))
         (foreach s '(("start" . start) ("end" . end))
           (if (lfc:arc-end-target e (cdr s) cands)
             (setq bad (append bad (list (car s)))))))
       (if bad (setq nabad (1+ nabad)))
       (setq lines (cons (strcat "Arc " (cdr (assoc 5 (entget e))) ": "
                                 (if bad
                                   (strcat (lfc:join bad " & ")
                                           " NOT attached to an object end")
                                   "endpoints OK"))
                         lines)))

     ;; --- overlaps
     (setq olaps (if lite nil (lfc:find-overlaps segs)))
     (foreach pr olaps
       (setq lines (cons (strcat "Lines "
                                 (cdr (assoc 5 (entget (lfc:seg-ent (car pr)))))
                                 "+"
                                 (cdr (assoc 5 (entget (lfc:seg-ent (cadr pr)))))
                                 ": OVERLAP of "
                                 (rtos (caddr (lfc:overlap-info (car pr) (cadr pr))))
                                 " - flagged")
                         lines)))

     ;; --- steps / side view (detection only, nothing asked)
     (setq sgroups (lfc:step-groups segs (min *lfc-step-minlines*
                                               *lfc-bench-minlines*))
           scand   (vl-remove-if-not 'lfc:staircase-p sgroups)
           rest    scand)
     (while rest
       (setq g1 (car rest))
       (foreach g2 (cdr rest)
         (if (and (> (cal:ang-diff (car g1) (car g2)) (- (* 0.5 pi) 0.09))
                  (lfc:boxes-touch (lfc:pts-bbox (cdr g1))
                                    (lfc:pts-bbox (cdr g2))
                                    *lfc-step-maxgap*))
           (progn
             (if (not (member g1 svgroups)) (setq svgroups (cons g1 svgroups)))
             (if (not (member g2 svgroups)) (setq svgroups (cons g2 svgroups))))))
       (setq rest (cdr rest)))
     (setq pgroups (vl-remove-if
                     '(lambda (x) (or (member x svgroups)
                                      (< (length (cdr x)) *lfc-step-minlines*)))
                     sgroups))
     (if svgroups
       (setq svbb   (lfc:pts-bbox (apply 'append (mapcar 'cdr svgroups)))
             stepht (- (cadr (cadr svbb)) (cadr (car svbb)))))
     (setq satts (vl-remove-if-not
                   '(lambda (x) (lfc:ins-matches x "Step Attachment")) blks))
     ;; every attachment option still showing = nobody picked one
     (setq attundec nil)
     (foreach b satts
       (if (and (null attundec) (lfc:attach-undecided-p b))
         (progn
           (setq attundec (if (lfc:drawing-has-phrase *lfc-secured-phrase*)
                            'asked 'unasked))
           (setq lines (cons (strcat "Step Attachment "
                                     (cdr (assoc 5 (entget b)))
                                     ": all "
                                     (itoa (length *lfc-attach-options*))
                                     " options still shown ("
                                     (lfc:join *lfc-attach-options* "/")
                                     (if (eq attundec 'asked)
                                       (strcat ") and a '" *lfc-secured-phrase*
                                               "?' note is present - waiting on the customer")
                                       (strcat ") but NOTHING asks '"
                                               *lfc-secured-phrase*
                                               "?' - add the note")))
                             lines)))))
     (setq stepsum
           (cond
             ((and (null svgroups) (null pgroups)) "no step patterns detected")
             (svgroups
              (strcat "side view detected, rise " (rtos stepht)
                      (if satts "; Step Attachment present"
                        "; Step Attachment block MISSING - add one")
                      (cond ((eq attundec 'unasked)
                             (strcat "; every option still shown, NOTHING asks '"
                                     *lfc-secured-phrase* "?'"))
                            ((eq attundec 'asked)
                             "; attachment not chosen yet, the drawing asks the question")
                            (t ""))))
             (t (strcat (itoa (length pgroups))
                        " possible step pattern(s) - run LINFINCHECK to confirm"))))
     (foreach g pgroups
       (setq lines (cons (strcat "Steps: possible pattern of "
                                 (itoa (length (cdr g))) " parallel lines")
                         lines)))
     ;; bead track when the attachment is a bead one
     (if (and satts svgroups
              (vl-some '(lambda (x) (lfc:ins-matches x "Bead Step Attachment"))
                       satts))
       (progn
         (setq beadss (ssget "_X" (list (cons 8 *lfc-bead-layer*))) i 0)
         (if beadss
           (repeat (sslength beadss)
             (setq bb (cal:bbox-ent (ssname beadss i)) i (1+ i))
             (if bb (setq beadbbs (cons bb beadbbs)))))
         (foreach g pgroups
           (setq gbb (lfc:pts-bbox (cdr g)))
           (if (not (and gbb beadbbs (lfc:bead-near-p gbb beadbbs)))
             (setq lines (cons (strcat "Bead Track: NOTHING on layer '"
                                       *lfc-bead-layer*
                                       "' near a step pattern - add bead track")
                               lines))))))

     ;; --- wall height
     (setq tlist (vl-remove-if-not
                   '(lambda (x) (wcmatch (lfc:squash (lfc:block-name x))
                                         (strcat "*" (lfc:squash *lfc-title-block*) "*")))
                   blks))
     (if (null tlist)
       (progn
         (setq beadss (ssget "_X" '((0 . "INSERT"))) i 0)
         (if beadss
           (repeat (sslength beadss)
             (setq b (ssname beadss i) i (1+ i))
             (if (wcmatch (lfc:squash (lfc:block-name b))
                          (strcat "*" (lfc:squash *lfc-title-block*) "*"))
               (setq tlist (cons b tlist)))))))
     (setq cx (if minx (* 0.5 (+ minx maxx)) 0.0)
           cy (if miny (* 0.5 (+ miny maxy)) 0.0))
     (foreach b tlist
       (setq bp (cdr (assoc 10 (entget b)))
             d  (distance (list cx cy) (list (car bp) (cadr bp))))
       (if (or (null tbest) (< d tbest)) (setq tbest d tins b)))
     (if tins
       (setq wallraw  (lfc:ins-attrib-deep tins *lfc-wallht-tag*)
             wallvals (if wallraw (lfc:len-values wallraw))
             wallvar  (and wallraw (lfc:varies-p wallraw))
             wallmany (> (length wallvals) 1)
             wallzero (and wallvals (not wallmany)
                           (< (car wallvals) *lfc-min-wallht*))
             wallask  (and (null wallvals)
                           wallraw
                           (vl-string-search "?" (lfc:after-eq wallraw)))
             wallht   (if (and wallvals (not wallmany) (not wallzero))
                        (car wallvals))))
     (if (and svbb stepht (not (or wallvar wallmany wallzero wallask)))
       (setq hdim (lfc:height-dim dims svbb stepht)))
     (if hdim (setq dimht (lfc:dim-stated hdim)))
     (setq htval (if dimht dimht stepht)
           htbad (and htval wallht (> (abs (- htval wallht)) *lfc-height-tol*)))
     (setq htsum
           (cond
             ((and (null tins) (null htval)) nil)
             ((null tins) (strcat "steps rise " (rtos htval) " but no '"
                                  *lfc-title-block* "' block found - NOT CONFIRMED"))
             (wallvar (strcat *lfc-wallht-tag* " reads '" wallraw
                              "' - height varies, not checked"))
             (wallmany (strcat *lfc-wallht-tag* " holds "
                               (itoa (length wallvals)) " heights ('" wallraw
                               "') - CHECK THE WALL HEIGHT in the " *lfc-title-block*))
             (wallzero (strcat *lfc-wallht-tag* " is '" wallraw
                               "' - a NONSENSICAL wall height, fix the "
                               *lfc-title-block*))
             (wallask
              (if (lfc:drawing-has-phrase *lfc-ask-phrase*)
                (strcat *lfc-wallht-tag* " reads '" wallraw
                        "' and the drawing asks for the wall height - waiting on the customer")
                (strcat *lfc-wallht-tag* " reads '" wallraw
                        "' but NOTHING in the drawing asks for it - add a '"
                        *lfc-ask-phrase* "' note for the customer")))
             ((null wallht) (strcat "the " *lfc-wallht-tag* " attribute "
                                    (if wallraw
                                      (strcat "'" wallraw "' is unreadable")
                                      "is missing")
                                    " - NOT CONFIRMED"))
             ((null htval) (strcat *lfc-wallht-tag* " = '" wallraw "' - OK"))
             ((not htbad) (strcat "steps rise " (rtos htval) " = WallHt '"
                                  wallraw "' - MATCHES"))
             (t (strcat "steps rise " (rtos htval) " but WallHt is '" wallraw
                        "' (" (rtos wallht) ") - MISMATCH"))))

     ;; --- Tech Title Date (read-only twin of LINFINCHECK's check)
     (setq datesum nil dateraw nil datebad nil)
     (if tins
       (progn
         (setq dateraw (lfc:ins-attrib-deep tins *lfc-date-tag*))
         (setq datebad
           (if dateraw
             (lfc:date-verdict dateraw)
             "is missing - expected MM/DD/YYYY"))
         (setq datesum
           (if datebad
             (strcat *lfc-date-tag* " " datebad)
             (strcat *lfc-date-tag* " = '" dateraw "' - OK"))))
          (setq datesum (strcat "no '" *lfc-title-block*
                                "' block in reach - date NOT CHECKED")))

     ;; --- liner
     (setq liners (vl-remove-if-not
                    '(lambda (x) (lfc:ins-matches x "Liner Material")) blks)
           fgstep (lfc:fgstep-src ss blks))
     (if liners
       (setq linerstep (vl-some '(lambda (x) (lfc:ins-has-word x "STEP")) liners)))
     (foreach b liners
       (setq bad     nil
             badtags (lfc:attrib-bad-tags b *lfc-badwords*))
       (foreach w *lfc-badwords*
         (if (lfc:ins-has-word b w)
           (progn (setq bad (append bad (list w)))
                  (if (not (member w wnd)) (setq wnd (append wnd (list w)))))))
       ;; read-only: say which fields LINFINCHECK would clear, clear nothing
       (setq lines (cons (strcat "Liner Material (" (lfc:block-name b) ") "
                                 (cdr (assoc 5 (entget b))) ": "
                                 (cond
                                   (badtags
                                    (strcat (lfc:join badtags ", ")
                                            " carries " (lfc:join bad " & ")
                                            " - NEEDS WIPING (run LINFINCHECK)"))
                                   (bad
                                    (strcat "contains the word "
                                            (lfc:join bad " & ") " - look at it"))
                                   (t "OK")))
                         lines)))
     (if (and fgstep linerstep)
       (setq lines (cons (strcat "Liner Material: a Fiberglass Step (" fgstep
                                 ") is in the drawing but the liner pattern HAS a Step - it should not")
                         lines)))
     (if (and (not fgstep) svgroups liners (not linerstep))
       (setq lines (cons "Liner Material: steps are drawn but the liner pattern is MISSING its 'Step'"
                         lines)))
     (setq linersum
           (cond
             ((null liners) "block MISSING - add 'Liner Material' (or 'with Step')")
             (t (strcat (itoa (length liners)) " block(s) found"
                        (if wnd (strcat "; word " (lfc:join wnd " & ") " found - review") "")
                        (if (and fgstep linerstep)
                          "; Fiberglass Step in the drawing but the liner HAS a Step" "")
                        (if (and (null wnd) (not (and fgstep linerstep))) " - OK" "")))))

     ;; --- title block border size
     (setq bordbb (lfc:border-box ss))
     (if (null bordbb)
       (setq bordbb (lfc:border-box
                      (ssget "_X" (list (cons 8 *lfc-border-layer*))))))
     (setq bordsum (lfc:border-verdict bordbb))

     ;; --- report (the only thing the scan writes) --------------------
     (cal:ensure-layer *lfc-report-layer* *lfc-report-color*)
     (lfc:clear-old)
     (setq dhdr (if lite
                  nil
                  (list
                    (cons (strcat "Dimensions scanned: " (itoa nd) " ("
                                  (itoa ndbad)
                                  " with a stray definition point)")
                          (> ndbad 0))
                    (cons (strcat "Arcs scanned: " (itoa na) " ("
                                  (itoa nabad) " with an unattached end)")
                          (> nabad 0))
                    (cons (strcat "Overlapping line pairs: "
                                  (itoa (length olaps)))
                          (> (length olaps) 0)))))
     (setq dimlay (lfc:dimlayer-verdict dims)
           units  (lfc:audit-units ss))
     (foreach l (caddr units)
       (princ (strcat "\n  " l))
       (setq lines (cons l lines)))
     (setq hdr (list
                 (cons (strcat "Dimension layer: " (car dimlay)) (cdr dimlay))
                 (cons (strcat "Feet & inches: " (car units)) (cadr units))
                 (cons (strcat "Steps: " stepsum)           (lfc:attn-p stepsum))
                 (cons (strcat "Liner Material: " linersum) (lfc:attn-p linersum))
                 (cons (strcat "Title block border: " bordsum) (lfc:attn-p bordsum))))
     (if htsum
       (setq hdr (append hdr (list (cons (strcat "Wall height: " htsum)
                                         (lfc:attn-p htsum))))))
     (if datesum
       (setq hdr (append hdr (list (cons (strcat "Date: " datesum)
                                         (lfc:attn-p datesum))))))
     (lfc:write-report (strcat name " REPORT")
                       (strcat "Read-only scan - nothing in the drawing"
                               " was changed.  "
                               (if lite
                                 (strcat "Lite: dimensions, arcs and"
                                         " overlaps were not audited -"
                                         " run DIMCHECK or LINFINSCAN"
                                         " for those.  ")
                                 ""))
                       hdr dhdr (reverse lines) lite
                       minx miny maxx maxy)
     (setvar "CMDECHO" oldecho)
     (princ (strcat "\n--- " name " complete (read-only) ---"
                    (if lite
                      "\nLite: dimensions, arcs and overlaps were not audited."
                      (strcat "\nDimensions: " (itoa nd) " scanned, "
                              (itoa ndbad) " with a stray point"
                              "\nArcs: " (itoa na) " scanned, "
                              (itoa nabad) " with an unattached end"
                              "\nOverlapping line pairs: "
                              (itoa (length olaps))))
                    "\nSteps: " stepsum
                    "\nLiner Material: " linersum
                    "\nTitle block border: " bordsum
                    (if htsum (strcat "\nWall height: " htsum) "")
                    (if datesum (strcat "\nDate: " datesum) "")
                    "\nReport written on layer " *lfc-report-layer*
                    "; nothing else was changed."))))
  (princ))


;; --- TUTORIALLINFINCHECK: learn it two ways ---------------------------
;;  List  - every check spelled out, at the command line and (if you
;;          want) dropped into the drawing as a reference sheet.
;;  Demo  - draws a small practice drawing with faults planted in it,
;;          walks you through each one showing what LINFINCHECK sees and
;;          what the colours mean, then scans it so you see a report.
;;  Both  - the list, then the demo.
;;  Everything the demo draws is in one UNDO group and can be erased
;;  when you are done, so it never touches your real work.

(defun lfc:tut-checklist ()
  (list
    "WHAT LINFINCHECK CHECKS"
    ""
    "1. DIMENSIONS - one at a time"
    (strcat "   Order: style groups " (lfc:join *lfc-style-order* " > ")
            " > anything else,")
    "     then left to right, top to bottom inside each group."
    "   Every other object greys out; the one under review is zoomed to."
    "   A definition point not touching any object: you choose"
    "     Move (green +, onto the nearest object) / Keep (red X, exactly"
    "     where you drew it) / Pick your own spot."
    "   Then 'Is this dimension correct?'  Enter = yes,  N = flag it RED,"
    "     B = back one dimension,  S = skip the rest."
    "   The measured distance is shown, and object-associative dims are"
    "     called out (a moved point can re-anchor itself)."
    ""
    "2. ARCS - one endpoint at a time"
    "   Each end must sit at the END of another object; a loose one gets"
    "     the same Move / Keep / Pick choice. Keep restores the arc"
    "     exactly. Arcs that changed turn MAGENTA."
    ""
    "3. OVERLAPPING LINES"
    "   Collinear geometry running on top of itself, in LINEs and in"
    "     polyline edges. Touching end-to-end is fine and is not"
    "     reported. Per pair: Merge into one / Flag CYAN / Leave."
    "     Merge is offered only for two whole LINEs on one layer."
    ""
    "4. STEPS, BENCHES AND SIDE VIEWS"
    (strcat "   Step pattern = " (itoa *lfc-step-minlines*)
            "+ parallel lines stacked under "
            (rtos *lfc-step-maxgap*) " apart.")
    "   A side view is two patterns at right angles that march along"
    "     like a profile - benches (two treads) count. A rectangle or"
    "     nested plan outlines are NOT mistaken for one."
    "   No side view -> you are asked if the lines are steps, then"
    "     whether a side view exists; if not, the report says ADD ONE."
    "   Steps + side view -> a 'Step Attachment' block is required and"
    "     you confirm the right one is placed."
    (strcat "   A block still listing every option ("
            (lfc:join *lfc-attach-options* "/") ") means")
    (strcat "     nobody chose one - fine only if a '" *lfc-secured-phrase*
            "?' note asks.")
    (strcat "   'Bead Step Attachment' -> something must be on layer '"
            *lfc-bead-layer* "' within " (rtos *lfc-bead-dist*)
            " of each")
    "     plan-view step pattern (the side view itself is exempt)."
    ""
    "5. WALL HEIGHT (Tech Title)"
    (strcat "   The '" *lfc-title-block* "' block's " *lfc-wallht-tag*
            " is read whether or not")
    "     steps are drawn. 40'', 3'-4'', 3' 4 1/2'' and 40.5 all parse,"
    "     and any label before '=' is ignored."
    "     one sensible value  -> OK, and it is compared to the side view"
    "     several values      -> CHECK THE WALL HEIGHT"
    "     0'' (or near zero)  -> NONSENSICAL, fix the title block"
    (strcat "     ?                   -> only OK if a '" *lfc-ask-phrase*
            "' note asks the customer")
    "     Varies              -> fine, nothing to compare"
    "   A side-view height dim that disagrees is marked RED on its own."
    ""
    "6. DATE (Tech Title)"
    (strcat "   The '" *lfc-title-block* "' block's " *lfc-date-tag*
            " must read a real calendar")
    "     date as MM/DD/YYYY (e.g. 05/01/2024). Missing, blank, the wrong"
    "     format, or an out-of-range month/day is reported in red with"
    "     what is wrong; a clean date is a quiet OK."
    ""
    "7. LINER MATERIAL"
    "   A 'Liner Material' / 'Liner Material with Step' block must be"
    "     present."
    (strcat "   A pattern field reading " (lfc:join *lfc-badwords* " or ")
            " (e.g. 'Not Supplied',")
    "     '#ERROR') is WIPED back to blank - the label stays, the junk"
    "     goes. Real names like 'Tex' are never touched."
    "   A Fiberglass Step in the drawing -> the liner must NOT carry a"
    "     Step. Otherwise steps drawn -> the liner MUST have its Step."
    ""
    "8. TITLE BLOCK BORDER"
    (strcat "   The outer drawing on layer '" *lfc-border-layer*
            "' must be " (rtos *lfc-border-w*) " x "
            (rtos *lfc-border-h*))
    "     (58'-8'' x 45'-3 5/8'') or any scaled-UP multiple. Smaller ->"
    "     'Title block should not be SCALED DOWN for Liners'."
    "     Uneven -> STRETCHED. Nothing there -> NO BORDER."
    ""
    "9. THE REPORT"
    "   An MTEXT sheet to the right of the drawing, sized to scale with"
    (strcat "     it. Problems in RED at full size; all-clear in green at "
            (rtos (* 100.0 *lfc-green-scale*) 2 0) "%.")
    ""
    "COMMANDS"
    "   LINFINCHECK         the full interactive review (fixes things)"
    "   LINFINSCAN          the same audits, read-only - changes nothing"
    "   LINFINCHECKRESCUE   put back every colour, remove the markers"
    "   LINFINCHECKVER      which build is loaded"
    "   TUTORIALLINFINCHECK this tutorial"
    ""
    "GOOD HABITS"
    "   Highlight the whole title block so the border and the Tech Title"
    "     are included. Run LINFINSCAN first if you want to look before"
    "     anything is touched. One U undoes an entire LINFINCHECK run."))

(defun lfc:tut-pause (msg)
  (princ (strcat "\n  " msg))
  (getstring "\n  --- press Enter to continue ---")
  (princ))

(defun lfc:tut-line (p1 p2 lay)
  (entmake (list '(0 . "LINE") '(100 . "AcDbEntity") (cons 8 lay)
                 '(100 . "AcDbLine") (cons 10 p1) (cons 11 p2)))
  (entlast))

(defun lfc:tut-dim (p1 p2 dimpt rot / old res)
  ;; a linear dimension, made with the command so it is valid in any
  ;; release; osnap is muted so the picks land exactly where told
  (setq old (getvar "OSMODE"))
  (setvar "OSMODE" 0)
  (if (zerop rot)
    (command "_.DIMLINEAR" p1 p2 "_H" dimpt)
    (command "_.DIMLINEAR" p1 p2 "_V" dimpt))
  (setvar "OSMODE" old)
  (entlast))

(defun lfc:tut-demo (/ org ox oy made e ss2 i)
  (princ "\n\n--- DEMO: a practice drawing with faults planted in it ---")
  (setq org (getpoint "\n  Pick an empty spot for the practice drawing: "))
  (if (null org)
    (princ "\n  Cancelled - nothing drawn.")
    (progn
      (setq org (trans org 1 0)
            ox  (car org)
            oy  (cadr org)
            made nil)

      ;; --- fault 1: two lines overlapping ------------------------
      (setq made (cons (lfc:tut-line (list ox oy 0.0)
                                      (list (+ ox 100.0) oy 0.0) "0") made))
      (setq made (cons (lfc:tut-line (list (+ ox 60.0) oy 0.0)
                                      (list (+ ox 180.0) oy 0.0) "0") made))
      (command "_.ZOOM" "_Object" (car made) "")
      (command "_.ZOOM" "_0.4x")
      (lfc:tut-pause
        (strcat "FAULT 1 - overlapping lines.\n  Two lines run on top of each other from "
                "60 to 100: someone drew over\n  an existing line to carry on and never cleaned it up. "
                "LINFINCHECK\n  shows the overlap marked at both ends and offers Merge / Flag /\n"
                "  Leave. Lines that merely TOUCH end to end are fine and are\n  never reported."))

      ;; --- fault 2: a dim whose point misses the line -------------
      (setq made (cons (lfc:tut-line (list ox (+ oy 80.0) 0.0)
                                      (list (+ ox 120.0) (+ oy 80.0) 0.0) "0") made))
      (setq e (lfc:tut-dim (list ox (+ oy 80.0) 0.0)
                            (list (+ ox 120.0) (+ oy 88.0) 0.0)   ; 8 units OFF the line
                            (list (+ ox 60.0) (+ oy 110.0) 0.0) 0))
      (if e (setq made (cons e made)))
      (command "_.ZOOM" "_Window"
               (trans (list (- ox 20.0) (+ oy 50.0) 0.0) 0 1)
               (trans (list (+ ox 150.0) (+ oy 130.0) 0.0) 0 1))
      (lfc:tut-pause
        (strcat "FAULT 2 - a dimension point off the geometry.\n"
                "  The right-hand point of this dimension sits 8 units above the\n"
                "  line, so it is not measuring the line at all. LINFINCHECK marks\n"
                "  BOTH spots - a RED X where you drew it, a GREEN + where it\n"
                "  belongs - and lets you Move it, Keep it exactly as drawn, or\n"
                "  Pick a spot yourself. Answer N to the 'is this correct?'\n"
                "  question and the whole dimension turns RED to fix later."))

      ;; --- fault 3: a step side view + its height dim -------------
      (setq made (cons (lfc:tut-line (list (+ ox 36.0) (+ oy 200.0) 0.0)
                                      (list (+ ox 36.0) (+ oy 190.0) 0.0) "0") made)
            made (cons (lfc:tut-line (list (+ ox 36.0) (+ oy 190.0) 0.0)
                                      (list (+ ox 24.0) (+ oy 190.0) 0.0) "0") made)
            made (cons (lfc:tut-line (list (+ ox 24.0) (+ oy 190.0) 0.0)
                                      (list (+ ox 24.0) (+ oy 180.0) 0.0) "0") made)
            made (cons (lfc:tut-line (list (+ ox 24.0) (+ oy 180.0) 0.0)
                                      (list (+ ox 12.0) (+ oy 180.0) 0.0) "0") made)
            made (cons (lfc:tut-line (list (+ ox 12.0) (+ oy 180.0) 0.0)
                                      (list (+ ox 12.0) (+ oy 170.0) 0.0) "0") made)
            made (cons (lfc:tut-line (list (+ ox 12.0) (+ oy 170.0) 0.0)
                                      (list ox (+ oy 170.0) 0.0) "0") made)
            made (cons (lfc:tut-line (list ox (+ oy 170.0) 0.0)
                                      (list ox (+ oy 160.0) 0.0) "0") made))
      (setq e (lfc:tut-dim (list ox (+ oy 160.0) 0.0)
                            (list (+ ox 36.0) (+ oy 200.0) 0.0)
                            (list (+ ox 60.0) (+ oy 180.0) 0.0) 1))
      (if e (setq made (cons e made)))
      (command "_.ZOOM" "_Window"
               (trans (list (- ox 20.0) (+ oy 145.0) 0.0) 0 1)
               (trans (list (+ ox 90.0) (+ oy 215.0) 0.0) 0 1))
      (lfc:tut-pause
        (strcat "FAULT 3 - a step side view.\n"
                "  Four risers and three treads: LINFINCHECK reads this as a side\n"
                "  view because the two families of parallel lines sit at right\n"
                "  angles and march along like a profile. A bench - only two\n"
                "  treads - counts too, while a plain rectangle does not.\n"
                "  The vertical dimension spanning the whole rise is the OVERALL\n"
                "  HEIGHT. It gets compared with the Tech Title's WallHt, and if\n"
                "  the two disagree that dimension is marked RED automatically."))

      ;; --- fault 4: an arc floating free --------------------------
      (entmake (list '(0 . "ARC") '(100 . "AcDbEntity") '(8 . "0")
                     '(100 . "AcDbCircle")
                     (cons 10 (list (+ ox 220.0) (+ oy 40.0) 0.0))
                     (cons 40 30.0) '(100 . "AcDbArc")
                     (cons 50 0.0) (cons 51 pi)))
      (setq made (cons (entlast) made))
      (command "_.ZOOM" "_Window"
               (trans (list (+ ox 175.0) (- oy 10.0) 0.0) 0 1)
               (trans (list (+ ox 265.0) (+ oy 90.0) 0.0) 0 1))
      (lfc:tut-pause
        (strcat "FAULT 4 - an arc that attaches to nothing.\n"
                "  Both ends of this arc float free. LINFINCHECK wants every arc end\n"
                "  to land on the END of another object, so it offers to snap\n"
                "  each one - again with Move / Keep / Pick. An arc whose ends\n"
                "  actually moved turns MAGENTA so you can spot it afterwards."))

      ;; --- and now the report ------------------------------------
      (setq ss2 (ssadd))
      (foreach e made (if (entget e) (ssadd e ss2)))
      (command "_.ZOOM" "_Window"
               (trans (list (- ox 40.0) (- oy 40.0) 0.0) 0 1)
               (trans (list (+ ox 300.0) (+ oy 230.0) 0.0) 0 1))
      (princ (strcat "\n  " (itoa (sslength ss2))
                     " practice objects drawn. What LINFINCHECK would say about"
                     "\n  them is easiest to see as a report."))
      (if (cal:ask-yn "\n  Write a read-only LINFINSCAN report for the practice drawing?" "Yes")
        (progn
          (princ "\n  Running LINFINSCAN - it changes nothing, it only reports.")
          (princ "\n  (In the report, RED lines at full size are the problems;")
          (princ "\n   green lines at three-quarter size are the all-clears.)")
          (lfc:tut-pause
            (strcat "LINFINSCAN will ask you to highlight - window the practice\n"
                    "  drawing (or press Enter for the whole drawing). The report\n"
                    "  lands to the right of whatever you highlight."))
          (c:LINFINSCAN)))
      (if (cal:ask-yn "\n  Erase the practice drawing now?" "Yes")
        (progn
          (setq i 0)
          (repeat (sslength ss2)
            (if (entget (ssname ss2 i)) (entdel (ssname ss2 i)))
            (setq i (1+ i)))
          (setq ss2 (ssget "_X" (list (cons 8 *lfc-report-layer*))))
          (if ss2
            (progn
              (setq i 0)
              (repeat (sslength ss2) (entdel (ssname ss2 i)) (setq i (1+ i)))))
          (princ "\n  Practice drawing erased."))
        (princ "\n  Left in place - one U removes the whole tutorial."))
      (princ))))

(defun c:TUTORIALLINFINCHECK ( / *error* oldecho undo-open ans l ins h)
  (defun *error* (msg)
    (if undo-open (progn (setvar "CMDECHO" 0) (command "_.UNDO" "_End")))
    (if oldecho (setvar "CMDECHO" oldecho))
    (if (and msg (not (wcmatch (strcase msg) "*BREAK*,*CANCEL*,*QUIT*,*EXIT*")))
      (princ (strcat "\nTUTORIALLINFINCHECK error: " msg)))
    (princ))

  (princ (strcat "\n=================================================="
                 "\n  LINFINCHECK tutorial   [" *lfc-version* "]"
                 "\n=================================================="))
  ;; the tutorial selector of STANDARDS section 3; the old List stays
  ;; accepted typed in full, hidden
  (initget "Checks Demo Both LIST")
  (setq ans (getkword
              "\n  Read the Checks, Demo them on a practice drawing, or Both? [Checks/Demo/Both] <Both>: "))
  (if (null ans) (setq ans "Both"))
  (if (= ans "LIST") (setq ans "Checks"))
  (setq oldecho (getvar "CMDECHO"))
  (setvar "CMDECHO" 0)
  (command "_.UNDO" "_Begin")
  (setq undo-open T)

  (if (member ans '("Checks" "Both"))
    (progn
      (foreach l (lfc:tut-checklist) (princ (strcat "\n" l)))
      (princ "\n")
      (if (cal:ask-yn "\n  Drop that list into the drawing as a reference sheet?" "Yes")
        (progn
          (cal:ensure-layer *lfc-report-layer* *lfc-report-color*)
          (setq ins (getpoint "\n  Pick the top-left corner for the sheet: "))
          (if ins
            (progn
              (setq h   (getdist (strcat "\n  Text height <" (rtos 2.5) ">: "))
                    h   (if h h 2.5)
                    ins (trans ins 1 0))
              (lfc:mtext ins h (* 70.0 h)
                          (lfc:join (lfc:tut-checklist) "\\P")
                          *lfc-report-layer*)
              (princ "\n  Reference sheet placed (one U removes it)."))
            (princ "\n  No point picked - sheet skipped."))))))

  (if (member ans '("Demo" "Both"))
    (lfc:tut-demo))

  (command "_.UNDO" "_End")
  (setq undo-open nil)
  (setvar "CMDECHO" oldecho)
  (princ (strcat "\n\n--- Tutorial finished ---"
                 "\n  LINFINSCAN first if you want to look without touching anything;"
                 "\n  LINFINCHECK to review and fix; LINFINCHECKRESCUE to undo the marks."
                 "\n  One U undoes everything this tutorial drew."))
  (princ))

(defun c:TUTORIALLINFINSCAN () (c:TUTORIALLINFINCHECK))

(princ "\nlinfincheck.lsp loaded - LINFINCHECK reviews the whole title block one item at a")
(princ "\n  time (dims, arcs, overlaps, steps, wall height, liner, border); LINFINSCAN reports")
(princ "\n  it read-only; LINFINCHECKRESCUE undoes LINFINCHECK's marks. For just dims, arcs")
(princ "\n  and overlaps, load dimcheck.lsp instead and run DIMCHECK.")
(princ)


;;; ======================================================================
;;; >>> LINTXTCHK.lsp
;;; ======================================================================

;;; ==========================================================================
;;; LINTXTCHK.lsp  --  Liner Text Checklist
;;; --------------------------------------------------------------------------
;;; Places the vinyl pool-liner drawing checklist into the current drawing as
;;; a column of individual TEXT entities (one entity per line) starting at a
;;; point the user picks.  Text height is 12" and the lines are spaced out
;;; vertically automatically.  Sub-items are indented under their parent.
;;;
;;; Usage:  APPLOAD this file (or add it to your startup suite), then type
;;;         LINTXTCHK and pick the top-left point for the checklist.
;;; ==========================================================================

;;; SHARED BUILD: requires CALOFIN-LIB.lsp (load via CALOFIN-LOADER.lsp).
;;; Generic helpers live there under cal: - see STANDARDS.md.
;;;

(setq *lintxtchk-version* "v1.0")   ; announced on load; release_lisp.py
                                       ; stamps the dated twin in releases/

(defun c:LINTXTCHK ( / *error* items height spacing indent osm pt
                       startx y z x lvl txt )

  (defun *error* (msg)
    (if osm (setvar "OSMODE" osm))
    (if (and msg
             (not (member msg '("Function cancelled" "quit / exit abort"))))
      (princ (strcat "\nLINTXTCHK error: " msg)))
    (princ))

  ;; --- the checklist -------------------------------------------------------
  ;; Each entry is (indent-level . "line text").  Level 0 = main item,
  ;; level 1 = sub-item.  Inner double quotes and inch marks are escaped.
  (setq items
    (list
      (cons 0 "Read all WSN (White Screen Notes), Notes from Merlin, and Customer Info")
      (cons 1 "Does this job actually require a Tech drawing?")
      (cons 0 "Verify Finished Wall Ht & Pool Depth")
      (cons 1 "Finished Wall Ht should be a single value, or \"Varies\" if needed")
      (cons 0 "Place liner pattern block (GLP) - Delete \"Not Supplied\" text")
      (cons 0 "Verify the type of pool bead, or overlap for AG, etc")
      (cons 0 "Pool perimeter & overall dims")
      (cons 0 "Verify orientation: Shallow end to the RIGHT of page")
      (cons 0 "Report ALL cross dimensions provided by customer")
      (cons 0 "Pool corners with dimensions")
      (cons 1 "Look out special mfgrs like Esther Williams (3x3, 5x5) or Foxx (37\" Deep)")
      (cons 0 "Look for special bottom conditions:")
      (cons 1 "Does the shallow end have a Cove?")
      (cons 1 "Does the pool have a Safety Ledge?")
      (cons 1 "Did the customer provide various depths for the bottom?")
      (cons 1 "Does the pool require a side view?")
      (cons 0 "Are hopper corners radius?")
      (cons 0 "Did you draw trowel lines accurately?")
      (cons 0 "Are steps / bench Fiberglass?")
      (cons 1 "Place FGS note or draw step outline if dimensions were provided")
      (cons 1 "Is the step Straight or Radius? Ask if not given")
      (cons 0 "Are steps / bench Vinyl-covered?")
      (cons 1 "Verify step corner type & dimensions")
      (cons 1 "Place Step Attachment block - is the attachment type provided?")
      (cons 1 "Place side views for all steps and benches")
      (cons 0 "Did you scale the titleblock? REDVIEW!")
    )
  )

  ;; --- layout parameters ---------------------------------------------------
  (setq height  12.0)            ; text height  = 12"
  (setq spacing (* height 1.6))  ; automatic vertical distance between lines
  (setq indent  (* height 1.5))  ; horizontal indent per sub-level

  (setq osm (getvar "OSMODE"))
  (setq pt (getpoint "\nPick top-left point for LINTXTCHK checklist: "))

  (if pt
    (progn
      (setvar "OSMODE" 0)                 ; drop osnaps while placing text
      (setq startx (car pt)
            y      (cadr pt)
            z      (if (caddr pt) (caddr pt) 0.0))
      (foreach item items
        (setq lvl (car item)
              txt (cdr item)
              x   (+ startx (* indent lvl)))
        (entmake
          (list
            '(0 . "TEXT")
            (cons 10 (list x y z))        ; insertion point (baseline, left)
            (cons 11 (list x y z))
            (cons 40 height)             ; 12" text
            (cons 1 (strcat "- " txt))   ; each line is its own entity
            '(72 . 0)                     ; horizontal justify: left
            '(73 . 0)                     ; vertical justify:   baseline
          )
        )
        (setq y (- y spacing))            ; step down to the next line
      )
      (setvar "OSMODE" osm)
      (princ (strcat "\n" (itoa (length items))
                     " checklist lines placed at 12\" text."))
    )
    (princ "\nLINTXTCHK cancelled.")
  )
  (princ)
)

(princ "\nLINTXTCHK loaded.  Type LINTXTCHK to place the liner checklist.")
(princ)


;;; ======================================================================
;;; >>> PADDLE.lsp
;;; ======================================================================

;;; ===================================================================
;;; PADDLE.lsp
;;;
;;; Scans the perimeter of a drawing for concave features that require
;;; pads, and inserts 36" x 36" pad blocks ("Pad36x36") centered on
;;; the affected areas, always parallel to the X/Y axes.
;;;
;;; Pad specification:
;;;   * Any CONCAVE arc / fillet with a radius of 4'-6" (54") or less
;;;     -- all the way down to sharp 90-degree inside corners --
;;;     requires pads along the affected arc.
;;;   * Any CONCAVE intersection of straight segments (an inside
;;;     corner) requires a pad centered on the corner.
;;;   * Semi-straight geometry is left alone: a connection point or an
;;;     arc whose total bend is 10 degrees or less is not a feature.
;;;   * Convex features and concave arcs larger than 4'-6" radius do
;;;     NOT require pads.
;;;   * Pads never overlap: where features crowd together, a pad on a
;;;     sharp point stays dead-center on that point, and the pads
;;;     along curves do the dodging -- sliding over to sit flush
;;;     alongside, or dropping out when a neighbour covers their spot.
;;;
;;; Accepted perimeter input (generous):
;;;   * a closed LWPOLYLINE or 2D POLYLINE, or
;;;   * loose LINEs / ARCs (or a mix of all of the above) -- PADDLE
;;;     chains touching segments end-to-end into closed loops.
;;;
;;; Usage:
;;;   Command: PADDLE
;;;   Select the perimeter geometry, or press Enter to auto-detect
;;;   the perimeter (the largest closed loop found in the drawing).
;;;
;;; SHARED BUILD: requires CALOFIN-LIB.lsp (load via CALOFIN-LOADER.lsp).
;;; Generic helpers live there under cal: - see STANDARDS.md.
;;;
;;;   Command: TUTORIALPADDLE
;;;   Guided tour for new users: lists everything PADDLE checks, then
;;;   optionally draws a labelled sample perimeter and pads it step by
;;;   step so you can watch what happens.
;;;
;;; Versioning: see tools/release_lisp.py at the repo root. It reads
;;; *paddle-version* below and stamps a dated, REV-numbered twin of
;;; this file into releases/.
;;;
;;; Block resolution order for the chosen pad block:
;;;   1. A block definition already in the drawing.
;;;   2. Imported from "24inpad.dwg" found on the AutoCAD support
;;;      path (ships alongside this lisp -- add its folder to the
;;;      support file search path, or drop the dwg next to the
;;;      current drawing).
;;;   3. As a last resort a plain square block of the right size is
;;;      created so the command always works.
;;;
;;; Assumes drawing units are INCHES (architectural). Adjust the
;;; constants below for other setups.
;;; ===================================================================

(vl-load-com)

;; --------------------------- settings ------------------------------
(setq *paddle-version* "v1.4") ; printed on load and at command start
                             ; so a loaded routine and its releases/
                             ; twin can never disagree
(setq *paddle-blkname* "Pad36x36") ; the 3'x3' pad block
(setq *paddle-padsize* 36.0) ; pads are 36" x 36"
(setq *paddle-blkfile* "24inpad.dwg") ; dwg holding the pad blocks
(setq *paddle-maxrad* 54.0)  ; 4'-6" : largest concave radius needing pads
(setq *paddle-layer* "PADS") ; layer pads are inserted on
(setq *paddle-align* nil)    ; nil = pads stay parallel to the X/Y axes,
                             ; T = rotate pads with the perimeter edge
(setq *paddle-fuzz* 0.05)    ; max gap between segment ends when
                             ; chaining loose lines/arcs into a loop
(setq *paddle-angtol* (/ (* 10.0 pi) 180.0)) ; a connection point or an
                             ; arc whose total bend is 10 degrees or
                             ; less is semi-straight - no pad

(defun paddle--dir (a) (list (cos a) (sin a))) ; unit vector at angle a
(defun paddle--rot (v a) ; rotate vector v by angle a
  (list (- (* (car v) (cos a)) (* (cadr v) (sin a)))
        (+ (* (car v) (sin a)) (* (cadr v) (cos a)))))
(defun paddle--arcpt (cen r ang) (cal:v+ cen (cal:v* (paddle--dir ang) r)))
(defun paddle--cheb (v) (max (abs (car v)) (abs (cadr v)))) ; Chebyshev norm

;; Segment data for vertex A -> B with bulge b (b /= 0):
;; returns (theta radius center start-tangent end-tangent)
;; theta = signed included angle (CCW positive), tangents are angles.
(defun paddle--arcdata (a b blg / theta chord r phi ts cen)
  (setq theta (* 4.0 (atan blg))
        chord (distance a b)
        r     (/ chord (* 2.0 (sin (/ (abs theta) 2.0))))
        phi   (angle a b)
        ts    (- phi (/ theta 2.0))
        cen   (cal:v+ a (cal:v* (paddle--dir (+ ts (if (> blg 0.0) (/ pi 2.0) (/ pi -2.0)))) r)))
  (list theta r cen ts (+ phi (/ theta 2.0))))

;; Signed area of a closed vertex list (shoelace + circular segments).
;; vts = list of (x y bulge), bulge belongs to the segment leaving it.
(defun paddle--area (vts / n i a b blg area theta r seg)
  (setq n (length vts) i 0 area 0.0)
  (repeat n
    (setq a   (nth i vts)
          b   (nth (rem (1+ i) n) vts)
          blg (caddr a))
    (setq area (+ area (* 0.5 (- (* (car a) (cadr b)) (* (car b) (cadr a))))))
    (if (/= blg 0.0)
        (progn
          (setq seg   (paddle--arcdata a b blg)
                theta (abs (car seg))
                r     (cadr seg))
          (setq area (+ area (* (if (> blg 0.0) 1.0 -1.0)
                                0.5 r r (- theta (sin theta)))))))
    (setq i (1+ i)))
  area)

;; Next pad along an arc: starting from arc-parameter CUR (previous
;; pad center PREV), find the parameter where the pad center is
;; exactly PADSIZE away from PREV in Chebyshev distance -- axis-
;; aligned pads of that size then touch edge-to-edge without ever
;; overlapping. Returns (parameter center), or nil when the rest of
;; the arc is too short for another flush pad.
(defun paddle--next-flush (cen r sa sgn cur sweep prev padsize
                           / ds d p hit lo hi mid)
  (setq ds (/ padsize r 8.0))                ; ~1/8 pad per probe step
  (if (> ds (/ sweep 4.0)) (setq ds (/ sweep 4.0)))
  (setq d cur hit nil)
  (while (and (not hit) (< d (- sweep 1e-9))) ; walk until pads separate
    (setq lo d
          d  (min sweep (+ d ds))
          p  (paddle--arcpt cen r (+ sa (* sgn d))))
    (if (>= (paddle--cheb (cal:v- p prev)) padsize)
        (setq hit T)))
  (if hit
      (progn ; tighten the crossing between lo and d by bisection
        (setq hi d)
        (repeat 45
          (setq mid (/ (+ lo hi) 2.0)
                p   (paddle--arcpt cen r (+ sa (* sgn mid))))
          (if (>= (paddle--cheb (cal:v- p prev)) padsize)
              (setq hi mid)
              (setq lo mid)))
        (list hi (paddle--arcpt cen r (+ sa (* sgn hi)))))))

;; Pad centers for one concave arc: the fewest pads that matter most.
;; The first pad is centered on the MIDDLE of the arc (the part that
;; must be covered); further pads march outward toward both ends, each
;; exactly one pad-size on center from the last, so the row touches
;; edge-to-edge and stair-steps into a blocky representation of the
;; curve. Marching stops when the leftover end of the arc is too short
;; for another flush pad -- the extreme ends of the radius are allowed
;; to stay uncovered.
(defun paddle--arc-pads (cen r sa sgn sweep padsize
                         / mid amid pmid fwd bwd cur prev nxt)
  (setq mid  (/ sweep 2.0)
        amid (+ sa (* sgn mid))
        pmid (paddle--arcpt cen r amid))
  ;; march from the middle toward the arc's end...
  (setq cur 0.0 prev pmid fwd nil)
  (while (setq nxt (paddle--next-flush cen r amid sgn cur (- sweep mid) prev padsize))
    (setq cur (car nxt) prev (cadr nxt) fwd (cons prev fwd)))
  ;; ...and from the middle back toward the arc's start
  (setq cur 0.0 prev pmid bwd nil)
  (while (setq nxt (paddle--next-flush cen r amid (- sgn) cur mid prev padsize))
    (setq cur (car nxt) prev (cadr nxt) bwd (cons prev bwd)))
  (append bwd (list pmid) (reverse fwd)))

;; Direction (unit vector) of travel at the START / END of segment a->b.
(defun paddle--tan-start (a b blg)
  (if (= blg 0.0)
      (cal:unit (cal:v- b a))
      (paddle--dir (cadddr (paddle--arcdata a b blg)))))
(defun paddle--tan-end (a b blg)
  (if (= blg 0.0)
      (cal:unit (cal:v- b a))
      (paddle--dir (last (paddle--arcdata a b blg)))))

;; --------------------- entities -> segments ------------------------
;; A segment is (p1 p2 bulge) with 2D points.

;; LWPOLYLINE -> (closed-flag . vts)
(defun paddle--lwverts (ent / ed out grp)
  (setq ed (entget ent))
  (foreach grp ed
    (cond
      ((= (car grp) 10)
       (setq out (cons (list (cadr grp) (caddr grp) 0.0) out)))
      ((= (car grp) 42)
       (if out (setq out (cons (list (caar out) (cadr (car out)) (cdr grp)) (cdr out)))))))
  (cons (= 1 (logand 1 (cdr (assoc 70 ed)))) (reverse out)))

;; heavy 2D POLYLINE -> (closed-flag . vts), nil for 3D/mesh plines
(defun paddle--plverts (ent / ed flags e ved out p)
  (setq ed (entget ent) flags (cdr (assoc 70 ed)))
  (if (zerop (logand 112 flags)) ; skip 3D polylines / meshes / polyfaces
      (progn
        (setq e (entnext ent))
        (while (and e (= "VERTEX" (cdr (assoc 0 (setq ved (entget e))))))
          (if (zerop (logand 16 (cond ((cdr (assoc 70 ved))) (0)))) ; skip spline frame pts
              (progn
                (setq p (cdr (assoc 10 ved)))
                (setq out (cons (list (car p) (cadr p)
                                      (cond ((cdr (assoc 42 ved))) (0.0)))
                                out))))
          (setq e (entnext e)))
        (cons (= 1 (logand 1 flags)) (reverse out)))))

;; vertex list -> segments (wrapping when closed)
(defun paddle--vts->segs (closed vts / n i segs a b)
  (setq n (length vts) i 0)
  (repeat (if closed n (max 0 (1- n)))
    (setq a (nth i vts)
          b (nth (rem (1+ i) n) vts))
    (setq segs (cons (list (cal:2d a) (cal:2d b) (caddr a)) segs))
    (setq i (1+ i)))
  (reverse segs))

;; any supported entity -> list of segments
(defun paddle--ent-segs (ent / ed typ cen r sa ea sweep cv)
  (setq ed (entget ent) typ (cdr (assoc 0 ed)))
  (cond
    ((= typ "LINE")
     (list (list (cal:2d (cdr (assoc 10 ed)))
                 (cal:2d (cdr (assoc 11 ed))) 0.0)))
    ((= typ "ARC")
     (setq cen   (cal:2d (cdr (assoc 10 ed)))
           r     (cdr (assoc 40 ed))
           sa    (cdr (assoc 50 ed))
           ea    (cdr (assoc 51 ed))
           sweep (- ea sa))
     (if (<= sweep 0.0) (setq sweep (+ sweep pi pi)))
     (list (list (cal:v+ cen (cal:v* (paddle--dir sa) r))
                 (cal:v+ cen (cal:v* (paddle--dir ea) r))
                 (/ (sin (/ sweep 4.0)) (cos (/ sweep 4.0)))))) ; tan(sweep/4)
    ((= typ "LWPOLYLINE")
     (setq cv (paddle--lwverts ent))
     (paddle--vts->segs (car cv) (cdr cv)))
    ((= typ "POLYLINE")
     (setq cv (paddle--plverts ent))
     (if cv (paddle--vts->segs (car cv) (cdr cv))))))

;; ------------------- chain segments into loops ---------------------
;; Chains touching segments (ends within *paddle-fuzz*) end-to-end.
;; Returns (loops . open-count); each loop is a vertex list (x y bulge).
(defun paddle--chain (segs / loops nopen chain head tail done found rest s)
  (setq nopen 0)
  ;; drop degenerate slivers
  (setq segs (vl-remove-if
               '(lambda (s) (<= (distance (car s) (cadr s)) *paddle-fuzz*))
               segs))
  (while segs
    (setq chain (list (car segs))
          head  (car (car segs))
          tail  (cadr (car segs))
          segs  (cdr segs)
          done  nil)
    (while (not done)
      (cond
        ;; loop closed back onto its start?
        ((and (> (length chain) 1) (<= (distance tail head) *paddle-fuzz*))
         (setq loops (cons (mapcar '(lambda (s) (list (car (car s)) (cadr (car s)) (caddr s)))
                                   chain)
                           loops)
               done  T))
        (T ;; look for a segment continuing from the tail
         (setq found nil rest nil)
         (foreach s segs
           (if found
               (setq rest (cons s rest))
               (cond
                 ((<= (distance tail (car s)) *paddle-fuzz*)
                  (setq found s))
                 ((<= (distance tail (cadr s)) *paddle-fuzz*) ; reversed
                  (setq found (list (cadr s) (car s) (- (caddr s)))))
                 (T (setq rest (cons s rest))))))
         (if found
             (setq chain (append chain (list found))
                   tail  (cadr found)
                   segs  (reverse rest))
             (setq nopen (1+ nopen) done T)))))) ; dead end: open chain
  (cons (reverse loops) nopen))

;; ------------------------ feature detection ------------------------
;; Returns a list of pads: (center rotation kind), kind = "corner"/"arc".
;; PADSIZE sets the pad-grid pitch used to cover concave arcs.
(defun paddle--features (vts padsize / s n i a b c blg pads din dout turn
                             seg theta r cen sa sgn sweep)
  (setq s (if (< (paddle--area vts) 0.0) -1 1) ; -1 = clockwise
        n (length vts)
        i 0)
  (repeat n
    (setq a   (nth i vts)                     ; segment i : a -> b
          b   (nth (rem (1+ i) n) vts)
          c   (nth (rem (+ i (1- n)) n) vts)  ; previous vertex
          blg (caddr a))

    ;; --- concave vertex (inside corner) at a, between seg i-1 and i ---
    (setq din  (paddle--tan-end (cal:2d c) (cal:2d a) (caddr c))
          dout (paddle--tan-start (cal:2d a) (cal:2d b) blg))
    (if (and din dout)
        (progn
          (setq turn (atan (cal:cross din dout) (cal:dot din dout)))
          (if (< (* s turn) (- *paddle-angtol*)) ; turns away from interior
              (setq pads (cons (list (cal:2d a) (angle '(0.0 0.0) din) "corner")
                               pads)))))

    ;; --- concave arc segment with radius <= 4'-6" ---
    (if (and (/= blg 0.0)
             (< (* s blg) 0.0)) ; bulges into the interior
        (progn
          (setq seg   (paddle--arcdata (cal:2d a) (cal:2d b) blg)
                theta (car seg)
                r     (cadr seg)
                cen   (caddr seg))
          (if (and (<= r (+ *paddle-maxrad* 1e-6))
                   (> (abs theta) *paddle-angtol*)) ; total bend over 10
                                                    ; deg, else it's a
                                                    ; semi-straight line
              (progn
                (setq sa    (angle cen (cal:2d a))
                      sgn   (if (> theta 0.0) 1.0 -1.0)
                      sweep (abs theta))
                (foreach ctr (paddle--arc-pads cen r sa sgn sweep padsize)
                  (setq pads (cons (list ctr 0.0 "arc") pads)))))))
    (setq i (1+ i)))
  (reverse pads))

;; Keep pads from colliding where features crowd together, without
;; ever pulling a pad off a sharp point. Corner pads commit first,
;; dead-center on their vertex -- they NEVER slide; one that would
;; overlap an earlier corner pad is dropped (in a notch that tight,
;; the neighbour carries the area). Arc pads then dodge around
;; everything committed: one that would overlap a committed pad slides
;; along one axis to sit flush alongside it instead (pads are PADSIZE
;; x PADSIZE, so flush = exactly PADSIZE on center). An arc pad whose
;; center is already inside a committed pad -- or that cannot find a
;; clear flush spot within half a pad of where it wanted to be -- is
;; dropped: its area is covered by the neighbours it kept hitting.
;; Returns the committed pads, corner pads first.
(defun paddle--dodge (pads padsize / out ctr orig tries done hit d ax sgn)
  (foreach pad pads ; sharp points first: exact centers, never slid
    (if (= (caddr pad) "corner")
        (progn
          (setq hit nil)
          (foreach q out
            (if (and (not hit)
                     (< (paddle--cheb (cal:v- (car pad) (car q)))
                        (- padsize 1e-6)))
                (setq hit T)))
          (if (not hit) (setq out (cons pad out))))))
  (foreach pad pads ; arc pads dodge around what's committed
    (if (/= (caddr pad) "corner")
        (progn
          (setq ctr   (car pad)
                orig  ctr
                tries 0
                done  nil)
          (while (not done)
            (setq hit nil)
            (foreach q out
              (if (and (not hit)
                       (< (paddle--cheb (cal:v- ctr (car q)))
                          (- padsize 1e-6)))
                  (setq hit (car q))))
            (cond
              ((not hit) ; clear: commit it here
               (setq out  (cons (list ctr (cadr pad) (caddr pad)) out)
                     done T))
              ((or (< (paddle--cheb (cal:v- ctr hit)) (/ padsize 2.0))
                   (> tries 6)
                   (> (paddle--cheb (cal:v- ctr orig)) (/ padsize 2.0)))
               (setq done T)) ; already covered there, or stuck: drop it
              (T ; slide along the more-separated axis until flush
               (setq d   (cal:v- ctr hit)
                     ax  (if (>= (abs (car d)) (abs (cadr d))) 0 1)
                     sgn (if (< (nth ax d) 0.0) -1.0 1.0))
               (setq ctr (if (= ax 0)
                             (list (+ (car hit) (* sgn padsize)) (cadr ctr))
                             (list (car ctr) (+ (cadr hit) (* sgn padsize)))))
               (setq tries (1+ tries))))))))
  (reverse out))

;; ------------------------- block handling --------------------------
;; Make sure block NAME (a SIZE-inch pad) is defined in the drawing.
;; Returns T.
(defun paddle--ensure-block (doc name size / path oldcmd oldatt tmpname)
  (cond
    ((tblsearch "BLOCK" name) T)
    ;; pull the definitions in from the pad dwg if it can be found --
    ;; inserting the file (under a throwaway name, then cancelling)
    ;; imports every block definition it contains
    ((setq path (findfile *paddle-blkfile*))
     (setq oldcmd (getvar "CMDECHO") oldatt (getvar "ATTREQ")
           tmpname "PADDLE-TEMP-IMPORT")
     (setvar "CMDECHO" 0) (setvar "ATTREQ" 0)
     ;; the restore below must run even if the insert throws: oldcmd
     ;; and oldatt are locals of THIS helper, so c:PADDLE's *error*
     ;; handler cannot put them back and the user would be left with
     ;; no command echo and no attribute prompts
     (vl-catch-all-apply
       '(lambda ()
          (command "_.-INSERT" (strcat tmpname "=" path))
          (command)))   ; cancel the insert -- the definitions stay behind
     (setvar "CMDECHO" oldcmd) (setvar "ATTREQ" oldatt)
     (vl-catch-all-apply ; drop the unused throwaway definition
       '(lambda () (vla-Delete (vla-Item (vla-get-Blocks doc) tmpname))))
     (if (tblsearch "BLOCK" name)
         T
         (paddle--make-fallback-block name size)))
    (T (paddle--make-fallback-block name size))))

;; Last-resort pad: a plain size x size square block, base at center.
(defun paddle--make-fallback-block (name size / h)
  (setq h (/ size 2.0))
  (entmake (list '(0 . "BLOCK") (cons 2 name)
                 '(10 0.0 0.0 0.0) '(70 . 0)))
  (entmake (list '(0 . "LWPOLYLINE") '(100 . "AcDbEntity") '(8 . "0")
                 '(100 . "AcDbPolyline") '(90 . 4) '(70 . 1)
                 (list 10 (- h) (- h)) (list 10 h (- h))
                 (list 10 h h) (list 10 (- h) h)))
  (entmake '((0 . "ENDBLK")))
  (princ (strcat "\nPADDLE: block \"" name "\" not found; created a plain "
                 (rtos size 2 0) "x" (rtos size 2 0) " square block instead."))
  (tblsearch "BLOCK" name))

;; Offset from the block's insertion point to the center of its extents
;; (measured at 0 rotation), so pads land centered no matter where the
;; block's base point was drawn.
(defun paddle--block-delta (space name / tmp mn mx d)
  (setq tmp (vla-InsertBlock space (vlax-3d-point 0.0 0.0 0.0)
                             name 1.0 1.0 1.0 0.0))
  (vla-GetBoundingBox tmp 'mn 'mx)
  (setq mn (vlax-safearray->list mn)
        mx (vlax-safearray->list mx)
        d  (list (/ (+ (car mn) (car mx)) 2.0)
                 (/ (+ (cadr mn) (cadr mx)) 2.0)))
  (vla-Delete tmp)
  d)

(defun paddle--ensure-layer (doc)
  (vla-Add (vla-get-Layers doc) *paddle-layer*))

;; Insert one pad so that its extents are centered on CTR. Pads stay
;; parallel to the X/Y axes unless *paddle-align* is set.
(defun paddle--insert-pad (space name ctr rot delta / ip obj)
  (if (not *paddle-align*) (setq rot 0.0))
  (setq ip  (cal:v- ctr (paddle--rot delta rot))
        obj (vla-InsertBlock space
              (vlax-3d-point (car ip) (cadr ip) 0.0)
              name 1.0 1.0 1.0 rot))
  (vla-put-Layer obj *paddle-layer*)
  obj)

;; --------------------------- selection -----------------------------
;; Turns a selection set (or the whole current tab when SS is nil) into
;; a list of closed perimeter loops (vertex lists). Auto-detect keeps
;; only the largest loop.
(defun paddle--perimeters (ss / auto i segs res loops nopen best bestarea a)
  (setq auto (not ss))
  (if auto
      (setq ss (ssget "_X" (list '(0 . "LWPOLYLINE,POLYLINE,LINE,ARC")
                                 (cons 410 (getvar "CTAB"))))))
  (if ss
      (progn
        (setq i 0)
        (repeat (sslength ss)
          (setq segs (append segs (paddle--ent-segs (ssname ss i)))
                i    (1+ i)))
        (setq res   (paddle--chain segs)
              loops (car res)
              nopen (cdr res))
        (if (> nopen 0)
            (princ (strcat "\nPADDLE: ignored " (itoa nopen)
                           " open chain(s) that never close back on themselves"
                           " (check for gaps; chaining tolerance is "
                           (rtos *paddle-fuzz* 2 2) ").")))
        (if auto
            (progn ; keep only the biggest closed loop
              (setq bestarea 0.0)
              (foreach l loops
                (setq a (abs (paddle--area l)))
                (if (> a bestarea) (setq bestarea a best l)))
              (if best
                  (progn
                    (princ "\nPADDLE: auto-detected the largest closed loop as the perimeter.")
                    (list best))))
            loops))))

;; ---------------------------- command ------------------------------
(defun c:PADDLE (/ *error* doc space padsize blkname ss perims vts
                   allpads delta ndodge ncorner narc)
  (defun *error* (msg)
    (if doc (vla-EndUndoMark doc))
    (if (and msg (not (wcmatch (strcase msg) "*BREAK*,*CANCEL*,*QUIT*,*EXIT*")))
        (princ (strcat "\nPADDLE error: " msg)))
    (princ))

  (setq doc   (vla-get-ActiveDocument (vlax-get-acad-object))
        space (vla-get-Block (vla-get-ActiveLayout doc)))

  (princ (strcat "\nPADDLE " *paddle-version*))
  (princ (strcat "\nPADDLE - 36\" pads at concave perimeter features (R <= "
                 (rtos *paddle-maxrad* 4 0) " and inside corners)."))

  (setq padsize *paddle-padsize*
        blkname *paddle-blkname*)

  (princ "\nSelect perimeter (polylines, lines and arcs) or press Enter to auto-detect: ")
  (setq ss (ssget '((0 . "LWPOLYLINE,POLYLINE,LINE,ARC"))))
  (setq perims (paddle--perimeters ss))

  (if (not perims)
      (princ "\nPADDLE: no closed perimeter loop found.")
      (progn
        (vla-StartUndoMark doc)
        (paddle--ensure-block doc blkname padsize)
        (paddle--ensure-layer doc)
        (setq delta (paddle--block-delta space blkname))
        (foreach vts perims
          (if (> (length vts) 1)
              (setq allpads (append allpads (paddle--features vts padsize)))))
        (setq ndodge  (length allpads)
              allpads (paddle--dodge allpads padsize)
              ndodge  (- ndodge (length allpads)))
        (setq ncorner 0 narc 0)
        (foreach pad allpads
          (paddle--insert-pad space blkname (car pad) (cadr pad) delta)
          (if (= (caddr pad) "corner") (setq ncorner (1+ ncorner)) (setq narc (1+ narc))))
        (vla-EndUndoMark doc)
        (if allpads
            (progn
              (princ (strcat "\nPADDLE: inserted " (itoa (length allpads))
                             " 36\" pad(s) on layer \"" *paddle-layer* "\" ("
                             (itoa ncorner) " at inside corners, "
                             (itoa narc) " along concave arcs)."))
              (if (> ndodge 0)
                  (princ (strcat "\nPADDLE: " (itoa ndodge)
                                 " overlapping pad(s) merged into their"
                                 " neighbours where features crowd together."))))
            (princ "\nPADDLE: perimeter checked - no concave features need pads."))))
  (princ))

;; --------------------------- tutorial ------------------------------
;; TUTORIALPADDLE walks a new user through what PADDLE checks, then
;; (optionally) draws a sample perimeter containing every kind of
;; feature and pads it step by step.

(defun paddle--pause ()
  (getstring "\n  [ press ENTER to continue ]")
  (princ))

;; the sample perimeter: straight walls, a 2-degree kink (ignored),
;; convex corners (ignored), a rectangular slot with two >10-degree
;; inside corners (padded), a concave R4'-0" bite (padded row) and a
;; concave R6'-0" sweep (too big -- no pads)
(defun paddle--demo-pline (base lay / pts absv)
  (setq pts '((0 0 0) (150 3 0) (300 0 0) (300 168 0) (264 168 -1.0)
              (168 168 0) (132 168 0) (132 120 0) (84 120 0) (84 168 0)
              (0 168 0) (0 134 -0.4038) (0 34 0)))
  (setq absv (mapcar '(lambda (v) (list (+ (car base) (car v))
                                        (+ (cadr base) (cadr v))
                                        (caddr v)))
                     pts))
  (entmake (append
             (list '(0 . "LWPOLYLINE") '(100 . "AcDbEntity") (cons 8 lay)
                   '(100 . "AcDbPolyline") (cons 90 (length absv)) '(70 . 1))
             (apply 'append
                    (mapcar '(lambda (v) (list (list 10 (car v) (cadr v))
                                               (cons 42 (caddr v))))
                            absv))))
  (entlast))

(defun paddle--demo-text (base lay pt str)
  (entmake (list '(0 . "TEXT") (cons 8 lay)
                 (list 10 (+ (car base) (car pt)) (+ (cadr base) (cadr pt)) 0.0)
                 '(40 . 6.0) (cons 1 str)))
  (entlast))

(defun c:TUTORIALPADDLE (/ doc space base lay ents pl vts feats blk delta
                           pad ncorner narc)
  (setq doc   (vla-get-ActiveDocument (vlax-get-acad-object))
        space (vla-get-Block (vla-get-ActiveLayout doc)))
  (princ (strcat "\n=== PADDLE TUTORIAL " *paddle-version* " ==="))
  (princ "\nPADDLE looks at the perimeter of a drawing and inserts pad blocks")
  (princ "\nwherever the perimeter caves inward. Everything it checks:")
  (princ "\n")
  (princ "\n 1. THE PERIMETER. Select it, or press ENTER and PADDLE finds the")
  (princ "\n    largest closed loop by itself. A closed polyline is ideal, but")
  (princ "\n    loose lines and arcs work too - touching ends (within ")
  (princ (strcat (rtos *paddle-fuzz* 2 2) "\") are"))
  (princ "\n    chained together automatically.")
  (princ (strcat "\n 2. INSIDE CORNERS. A connection point that bends more than "
                 (rtos (/ (* *paddle-angtol* 180.0) pi) 2 0) " degrees"))
  (princ "\n    away from straight gets one pad centered on the corner. Gentler")
  (princ "\n    kinks - semi-straight lines - and all convex (outside) corners")
  (princ "\n    are passed over.")
  (princ (strcat "\n 3. CONCAVE CURVES. A concave radius of " (rtos *paddle-maxrad* 4 0)
                 " or less, bending more"))
  (princ "\n    than 10 degrees in total, gets a row of pads: the middle of the")
  (princ "\n    curve is always covered, then pads march flush toward both ends")
  (princ "\n    (exactly 36\" on center, touching, never overlapping) - a blocky")
  (princ "\n    version of the curve. The extreme ends of the radius may stay")
  (princ "\n    uncovered; that is by design. Bigger concave radii, and curves")
  (princ "\n    bending 10 degrees or less, need no pads at all.")
  (princ "\n 4. NO COLLISIONS. Where features crowd together, a pad on a sharp")
  (princ "\n    point stays dead-center on that point - it never moves. The pads")
  (princ "\n    along curves do the dodging: they slide over to sit flush")
  (princ "\n    alongside, or drop out when a neighbour already covers their spot.")
  (princ (strcat "\n 5. RESULT. 36\" x 36\" pads (block " *paddle-blkname*
                 ", imported from"))
  (princ (strcat "\n    " *paddle-blkfile* " if needed), always square to the"
                 " X/Y axes, on layer"))
  (princ (strcat "\n    \"" *paddle-layer* "\", as a single undo step."))
  (paddle--pause)
  (initget "Yes No")
  (if (/= (getkword "\nDraw a live demonstration in this drawing? [Yes/No] <Yes>: ") "No")
      (progn
        (setq lay "PADDLE-DEMO")
        (vla-put-Color (vla-Add (vla-get-Layers doc) lay) 3)
        (setq base (getpoint "\nPick a clear spot for the demo <0,0>: "))
        (if (not base) (setq base '(0.0 0.0 0.0)))
        (setq pl   (paddle--demo-pline base lay)
              ents (list pl))
        (command "_.ZOOM" "_W"
                 (list (- (car base) 40.0) (- (cadr base) 40.0))
                 (list (+ (car base) 340.0) (+ (cadr base) 210.0)))
        (princ "\nThis sample perimeter (green) has one of everything. Labelling it...")
        (paddle--pause)
        (setq ents (cons (paddle--demo-text base lay '(96 14)
                     "2-deg kink here: 10 deg or less = ignored") ents))
        (setq ents (cons (paddle--demo-text base lay '(140 100)
                     "slot corners bend >10 deg: pad on each") ents))
        (setq ents (cons (paddle--demo-text base lay '(166 108)
                     "concave R4'-0\" (<= R4'-6\"): row of pads") ents))
        (setq ents (cons (paddle--demo-text base lay '(30 84)
                     "concave R6'-0\" (> R4'-6\"): no pads") ents))
        (setq ents (cons (paddle--demo-text base lay '(230 180)
                     "convex corners: never padded") ents))
        (princ "\nRead the labels on the drawing.")
        (paddle--pause)
        ;; run the real PADDLE pipeline on the demo
        (setq vts   (cdr (paddle--lwverts pl))
              feats (paddle--dodge (paddle--features vts *paddle-padsize*)
                                   *paddle-padsize*)
              blk   *paddle-blkname*)
        (paddle--ensure-block doc blk *paddle-padsize*)
        (paddle--ensure-layer doc)
        (setq delta (paddle--block-delta space blk)
              ncorner 0 narc 0)
        (princ "\nStep 1 - inside corners: one pad centered on each corner of the slot.")
        (foreach pad feats
          (if (= (caddr pad) "corner")
              (progn (paddle--insert-pad space blk (car pad) (cadr pad) delta)
                     (setq ents (cons (entlast) ents) ncorner (1+ ncorner)))))
        (paddle--pause)
        (princ "\nStep 2 - the R4'-0\" curve: first pad centered on the middle of the")
        (princ "\nradius, the rest flush at 36\" on center, stair-stepping the curve.")
        (princ "\nNote the R6'-0\" curve and the kink get nothing.")
        (foreach pad feats
          (if (= (caddr pad) "arc")
              (progn (paddle--insert-pad space blk (car pad) (cadr pad) delta)
                     (setq ents (cons (entlast) ents) narc (1+ narc)))))
        (princ (strcat "\nDone: " (itoa ncorner) " corner pad(s) + " (itoa narc)
                       " pad(s) along the curve, on layer \"" *paddle-layer* "\"."))
        (paddle--pause)
        (initget "Yes No")
        (if (= (getkword "\nErase the demonstration? [Yes/No] <No>: ") "Yes")
            (foreach e ents (entdel e)))))
  (princ "\nEnd of tutorial. Type PADDLE to run it on a real drawing.")
  (princ))

(princ (strcat "\nPADDLE " *paddle-version*
               " loaded. Commands: PADDLE (place pads), TUTORIALPADDLE (guided demo)."))
(princ)


;;; ======================================================================
;;; >>> perp_points.lsp
;;; ======================================================================

;;; perp_points.lsp  --  AutoCAD 2018 (AutoLISP)
;;;
;;; Command: PERPPTS
;;;
;;; SHARED BUILD: requires CALOFIN-LIB.lsp (load via CALOFIN-LOADER.lsp).
;;; Generic helpers live there under cal: - see STANDARDS.md.
;;;
;;; Splits a selected line into N equally-spaced points (both endpoints
;;; included), then for each division point creates a new point offset
;;; perpendicular to the line by a user-supplied length.  The new points
;;; are joined with a polyline -- straight segments, arcs, or a mix of
;;; the two -- and an aligned dimension is drawn from each new point
;;; back to its base point on the line.
;;;
;;; The routine then offers to REPEAT on the polyline it just created:
;;; you are asked again for a number of points, which are spaced equally
;;; ALONG the new polyline; each is offset by a user length to build the
;;; next polyline.  The offset direction -- and therefore every dimension
;;; -- stays perpendicular to the ORIGINAL line, not to the new polyline,
;;; so all offsets accumulate in one consistent direction.  Repeat as
;;; many times as you like.
;;;
;;; Workflow
;;;   1. Select a LINE (a polyline is also accepted, so work started in
;;;      an earlier session can be resumed).
;;;   2. Say whether the overall width has changed: Grew, Shrank, New
;;;      or Unchanged.  The width meant is the distance straight across,
;;;      end to end, not the length of the object; half of any
;;;      difference is added to (or taken off) each end, and the line in
;;;      the drawing is resized to match.
;;;   3. Click a point to set the direction:
;;;        - the line end nearest the click becomes START, the far end
;;;          FINISH, fixing the order the lengths are entered in;
;;;        - the side of the line the click lands on is the side the new
;;;          points are offset toward.
;;;   4. Enter how many values (points) are required  (>= 2).
;;;   5. Enter a length for each point, in order START -> FINISH.
;;;      Press Enter to reuse the previous length when it repeats, or
;;;      type B (Back) to step back and re-enter the previous point
;;;      (U, the old keyword, is still accepted).
;;;   6. Say how the points are joined: Straight (every segment a
;;;      line, which is what the routine has always drawn), Arcs (every
;;;      segment an arc), or Mixed, which then asks which segment
;;;      numbers are arcs -- "1 3-5" -- and leaves the rest straight.
;;;      The question is only asked once there are three points or
;;;      more, and the answer becomes the default for the next round.
;;;   7. Choose whether to repeat on the new polyline.  If so, enter a
;;;      new point count and repeat from step 5 with the new polyline as
;;;      the path.
;;;   8. Pick the dimension style, STANDARD INCHES or SIDE STANDARD.
;;;      Every dimension is then drawn at once, on the DIMENSIONS layer.
;;;
;;; The offset side is fixed once from the direction click in step 3 and
;;; reused for every round, so all offsets stay on the same side of the
;;; original line and every dimension stays perpendicular to it.
;;;
;;; The overall width
;;;   Walls get re-measured, and the number that comes back is the
;;;   distance straight across, end to end.  That is what step 2 asks
;;;   for -- never the developed length of the OBJECT, which on anything
;;;   bowed runs further than the width it spans.  Grew and Shrank take
;;;   the difference, New takes the width itself, and Unchanged (the
;;;   default, and Enter) leaves everything exactly as it was.
;;;
;;;   A new width is made true by scaling the selected object about the
;;;   midpoint of its two ends, so exactly half the difference lands at
;;;   each end and the shape between them is carried along.  The object
;;;   in the drawing is resized too, not just the numbers behind it: the
;;;   offsets and their dimensions are measured off it, so leaving it at
;;;   the old width would put every base point somewhere the drawing
;;;   says nothing is.  The base points and dimensions then follow the
;;;   resized object, since they are spaced along it after the resize.
;;;   The whole thing sits inside the command's undo group, so one U
;;;   puts the width back.
;;;
;;; Straight lines, arcs, or both
;;;   A measured wall is rarely all one or all the other: a radiused
;;;   stretch reads as an arc, a straight run reads as a line, and one
;;;   profile often needs both -- which is why step 5 asks instead of
;;;   assuming.  An arc segment is a bulge written onto the same
;;;   LWPOLYLINE, so whatever the answer the round produces one
;;;   editable polyline through the measured points: never a spline and
;;;   never a curve-fit heavy polyline.  Every point takes a direction
;;;   from the circle through it and its two neighbours, and a segment
;;;   is bent to the angle its two ends agree on, so points taken off a
;;;   real radius come back as that radius and every arc still passes
;;;   exactly through the two points it joins.
;;;   Once a round has drawn arcs, the next round spaces its base
;;;   points along the drawn curve rather than along the chords -- the
;;;   arcs bow away from their chords, so chord spacing would put the
;;;   base points off the polyline they are dimensioned from.
;;;
;;; Properties
;;;   * The offset polylines take the layer, colour, linetype, lineweight
;;;     and linetype scale of the object they were offset from.
;;;   * The dimensions go on the DIMENSIONS layer (created if missing)
;;;     and use the dimension style picked in step 6 when the drawing
;;;     has it; otherwise the current style is used and a note is
;;;     printed.
;;;
;;; Robustness
;;;   * The whole run is one UNDO group: a single U reverses everything.
;;;   * Esc or an error at any prompt restores every system variable it
;;;     changed (OSMODE, CMDECHO, PDMODE, CLAYER, the CE* creation
;;;     defaults and the current dimension style), erases the temporary
;;;     guides and closes the UNDO group.
;;;   * Bad input re-prompts instead of aborting the command; zero and
;;;     negative lengths are rejected, as is a direction click that lands
;;;     on the line itself (where "which side" would be ambiguous).
;;;   * All geometry is handled in the current UCS, so the command works
;;;     in a rotated or shifted UCS.
;;;
;;; License: GPL-3.0-or-later
;;; ---------------------------------------------------------------------

(vl-load-com)

;; Version banner: tools/release_lisp.py reads it to stamp the dated
;; REV twin in releases/ (vN.M -> _MMDDYY_REVNM).
(setq *perp-version* "v0.5")

;; --- geometry helpers ------------------------------------------------

;; linear interpolation between two 3D points at parameter tt (0..1)
(defun perp:lerp (a b tt)
  (list (+ (car a)   (* tt (- (car b)   (car a))))
        (+ (cadr a)  (* tt (- (cadr b)  (cadr a))))
        (+ (caddr a) (* tt (- (caddr b) (caddr a))))))

;; total length of a polyline given as a list of points
(defun perp:pathlen (pts / total i)
  (setq total 0.0 i 0)
  (while (< (1+ i) (length pts))
    (setq total (+ total (distance (nth i pts) (nth (1+ i) pts)))
          i     (1+ i)))
  total)

;; point at arc-length distance d along the polyline pts
(defun perp:pt-at (pts d / i a b segd res)
  (cond
    ((<= d 0.0) (car pts))
    (t
     (setq i 0 res nil)
     (while (and (null res) (< (1+ i) (length pts)))
       (setq a    (nth i pts)
             b    (nth (1+ i) pts)
             segd (distance a b))
       (if (<= d segd)
         (setq res (perp:lerp a b (if (> segd 1e-12) (/ d segd) 0.0)))
         (setq d (- d segd) i (1+ i))))
     (if res res (last pts)))))

;; n points equally spaced by arc length along the polyline pts
;; (both endpoints included)
(defun perp:sample (pts n / total i out)
  (setq total (perp:pathlen pts) out '() i 0)
  (while (< i n)
    (setq out (cons (perp:pt-at pts
                                (if (> n 1)
                                  (* (/ (float i) (float (1- n))) total)
                                  0.0))
                    out)
          i   (1+ i)))
  (reverse out))

;; drop consecutive duplicate points (a polyline may carry them)
(defun perp:dedupe (pts / out)
  (setq out (list (car pts)))
  (foreach p (cdr pts)
    (if (> (distance p (car out)) 1e-10)
      (setq out (cons p out))))
  (reverse out))

;; vertices of a LINE / LWPOLYLINE / POLYLINE, in the current UCS.
;; Returns nil for anything else.
(defun perp:verts (e / d et el pts sub sd flg)
  (setq d  (entget e)
        et (cdr (assoc 0 d)))
  (cond
    ;; LINE group 10/11 are WCS
    ((= et "LINE")
     (list (trans (cdr (assoc 10 d)) 0 1)
           (trans (cdr (assoc 11 d)) 0 1)))
    ;; LWPOLYLINE group 10 are OCS 2D points at elevation 38
    ((= et "LWPOLYLINE")
     (setq el  (cond ((cdr (assoc 38 d))) (0.0))
           pts '())
     (foreach x d
       (if (= 10 (car x))
         (setq pts (cons (trans (list (cadr x) (caddr x) el) e 1) pts))))
     (reverse pts))
    ;; heavy POLYLINE: walk the VERTEX entities, OCS points
    ((= et "POLYLINE")
     (setq pts '() sub (entnext e))
     (while (and sub
                 (setq sd (entget sub))
                 (/= "SEQEND" (cdr (assoc 0 sd))))
       (setq flg (cond ((cdr (assoc 70 sd))) (0)))
       ;; skip spline-frame control points and mesh vertices
       (if (and (= "VERTEX" (cdr (assoc 0 sd)))
                (zerop (logand 16 flg))
                (zerop (logand 64 flg)))
         (setq pts (cons (trans (cdr (assoc 10 sd)) e 1) pts)))
       (setq sub (entnext sub)))
     (reverse pts))
    (t nil)))

;; colour of an entity as a CECOLOR string ("BYLAYER", "3", "12,34,56")
(defun perp:color (d / c tc)
  (cond
    ;; 24-bit true colour packed into one integer
    ((setq tc (cdr (assoc 420 d)))
     (strcat (itoa (logand (lsh tc -16) 255)) ","
             (itoa (logand (lsh tc -8) 255)) ","
             (itoa (logand tc 255))))
    ((setq c (cdr (assoc 62 d)))
     (cond ((= c 0) "BYBLOCK")
           ((= c 256) "BYLAYER")
           ;; a negative index means the layer is off; the colour still applies
           (t (itoa (abs c)))))
    (t "BYLAYER")))

;; --- arcs through the points -----------------------------------------
;; Straight segments need nothing: PLINE already draws them.  An arc
;; segment is a bulge (group 42) written onto the same LWPOLYLINE, so
;; the round's output is one polyline either way.  Each vertex is given
;; a travel tangent, read off the circle through it and its two
;; neighbours, and each segment is then bent to the angle its two ends
;; agree on.  Points sampled off a real radius therefore reproduce that
;; radius exactly, every arc passes through both of its own points, and
;; a run of points reversed end for end draws the same curve.

;; Unit tangent at pt for the circle centred on ctr, turned to face the
;; way the polyline travels (toward nxt).  nil when there is no circle
;; or pt sits on its centre -- both mean "draw this segment straight".
(defun perp:tan-at (pt ctr nxt / tx ty l)
  (if (null ctr)
    nil
    (progn
      ;; the radius turned 90 degrees is the tangent
      (setq tx (- (cadr ctr) (cadr pt))
            ty (- (car pt)   (car ctr))
            l  (sqrt (+ (* tx tx) (* ty ty))))
      (if (< l 1e-12)
        nil
        (progn
          (setq tx (/ tx l) ty (/ ty l))
          (if (< (+ (* tx (- (car nxt)  (car pt)))
                    (* ty (- (cadr nxt) (cadr pt))))
                 0.0)
            (setq tx (- tx) ty (- ty)))
          (list tx ty))))))

;; the point one more step along from a to b -- b's own heading, for the
;; last vertex, which has nothing in front of it to face
(defun perp:ahead (a b)
  (list (- (* 2.0 (car b))  (car a))
        (- (* 2.0 (cadr b)) (cadr a))
        (caddr b)))

;; Travel tangent at EVERY vertex, in travel order.  An interior vertex
;; takes its direction from the circle through it and its two
;; neighbours; the two end vertices borrow the circle of the triple they
;; sit in.  nil where that circle does not exist -- collinear
;; neighbours, or fewer than three points -- which is how "nothing to
;; curve to" is carried through the rest of the fit.
(defun perp:tangents (pts / n i a p1 p2 p3 nxt ctr out)
  (setq n (length pts) out '() i 0)
  (if (>= n 3)
    (while (< i n)
      ;; a is the first of the three points whose circle points this
      ;; vertex: itself and its neighbours, or the end triple it sits in
      (setq a   (cond ((= i 0) 0) ((= i (1- n)) (- n 3)) (t (1- i)))
            p1  (nth a pts)
            p2  (nth (1+ a) pts)
            p3  (nth (+ a 2) pts)
            ctr (cal:circumcenter p1 p2 p3)
            ;; the last vertex has nothing in front of it to face, so it
            ;; takes its heading from the point before it
            nxt (if (= i (1- n))
                  (perp:ahead (nth (- n 2) pts) (nth (1- n) pts))
                  (nth (1+ i) pts))
            out (cons (perp:tan-at (nth i pts) ctr nxt) out)
            i   (1+ i))))
  (reverse out))

;; signed angle from vector u to vector v, -pi..pi
(defun perp:vang (u v)
  (atan (- (* (car u) (cadr v)) (* (cadr u) (car v)))
        (+ (* (car u) (car v))  (* (cadr u) (cadr v)))))

;; Bulge of the arc from a to b, given the travel tangents at a and at
;; b: tan(alpha/2), where alpha is half the arc's included angle.  Each
;; end asks for an alpha of its own -- the angle from a's tangent to the
;; chord, and from the chord to b's tangent -- and the two agree exactly
;; when the points came off a real circle, so a sampled arc is returned
;; unchanged.  Where they disagree the average is taken, which keeps the
;; fit symmetric: reverse the run of points and every bulge does no more
;; than change sign.  Straight (bulge 0) when neither end has a tangent,
;; which is the middle of a straight run, or when there is no chord.
(defun perp:bulge (ta tb a b / cx cy n alpha lim)
  (setq cx (- (car b)  (car a))
        cy (- (cadr b) (cadr a))
        alpha 0.0
        n     0)
  (cond
    ((< (sqrt (+ (* cx cx) (* cy cy))) 1e-12) 0.0)
    (t
     (if ta (setq alpha (+ alpha (perp:vang ta (list cx cy))) n (1+ n)))
     (if tb (setq alpha (+ alpha (perp:vang (list cx cy) tb)) n (1+ n)))
     (cond
       ((= n 0) 0.0)
       (t
        (setq alpha (/ alpha (float n)))
        ;; a chord folding back on a tangent would blow the bulge up
        ;; toward infinity; cap the included angle at ~342 degrees
        (setq lim 2.98)
        (if (> alpha lim)     (setq alpha lim))
        (if (< alpha (- lim)) (setq alpha (- lim)))
        (/ (sin (/ alpha 2.0)) (cos (/ alpha 2.0))))))))

;; Write the bulges onto the straight LWPOLYLINE en drawn through pts.
;; tangs holds one tangent per vertex.  Segment i (numbered from 1) is
;; arced when picks is nil -- every segment -- or when its number is in
;; picks; the rest are written straight, so one call covers an all-arc
;; round and a mixed one alike.  The entity stays an LWPOLYLINE: only
;; bulges are written, and the vertices are left where they were
;; measured.
(defun perp:arcs (en pts tangs picks / d out g i b)
  (setq d (entget en) out '() i 0)
  (foreach g d
    (cond
      ((= 42 (car g)))                       ; drop existing bulges
      ((= 10 (car g))
       (setq b (if (and (< (1+ i) (length pts))
                        (or (null picks) (member (1+ i) picks)))
                 (perp:bulge (nth i tangs) (nth (1+ i) tangs)
                             (nth i pts) (nth (1+ i) pts))
                 0.0))
       (setq out (cons (cons 42 b) (cons g out))
             i   (1+ i)))
      (t (setq out (cons g out)))))
  (entmod (reverse out)))

;; n points equally spaced by TRUE arc length along an existing polyline
;; entity, in the current UCS (both endpoints included).  This is what a
;; round after an arc round measures along: perp:sample walks the chords
;; between the points, which is the same thing only while the segments
;; are straight.  nil if the entity cannot be measured, so the caller
;; can fall back to the chords.
(defun perp:ent-pts (en n / tot i d p out ok)
  (setq tot (vlax-curve-getDistAtParam en (vlax-curve-getEndParam en))
        out '() i 0 ok T)
  (while (and ok (< i n))
    (setq d (if (> n 1) (* (/ (float i) (float (1- n))) tot) 0.0))
    (if (> d tot) (setq d tot))
    (if (setq p (vlax-curve-getPointAtDist en d))
      (setq out (cons (trans p 0 1) out)
            i   (1+ i))
      (setq ok nil)))
  (if ok (reverse out)))

;; --- reading a typed segment list ------------------------------------

;; T when s is one or more digits and nothing else.
(defun perp:digits-p (s / i n ok)
  (setq n (strlen s) i 1 ok (> n 0))
  (while (and ok (<= i n))
    (if (null (member (substr s i 1)
                      '("0" "1" "2" "3" "4" "5" "6" "7" "8" "9")))
      (setq ok nil))
    (setq i (1+ i)))
  ok)

;; "3" -> (3 3), "3-5" -> (3 5), anything else -> nil.
(defun perp:range (tok / i n p lft rgt)
  (setq n (strlen tok) i 1 p nil)
  (while (and (null p) (<= i n))
    (if (= "-" (substr tok i 1)) (setq p i))
    (setq i (1+ i)))
  (cond
    ((null p)
     (if (perp:digits-p tok) (list (atoi tok) (atoi tok))))
    (t
     (setq lft (substr tok 1 (1- p))
           rgt (substr tok (1+ p)))
     (if (and (perp:digits-p lft) (perp:digits-p rgt))
       (list (atoi lft) (atoi rgt))))))

;; Read a typed segment list -- "1 3-5, 8" -- into a list of segment
;; numbers.  Spaces and commas both separate.  Returns nil for an empty
;; answer, a malformed token or a number outside 1..maxn, so a bad
;; answer re-asks instead of quietly drawing the wrong thing.
(defun perp:parse-segs (s maxn / i n ch tok toks out bad r a b)
  (setq n (strlen s) i 1 tok "" toks '())
  (while (<= i n)
    (setq ch (substr s i 1))
    (if (or (= ch " ") (= ch ","))
      (progn
        (if (/= tok "") (setq toks (cons tok toks)))
        (setq tok ""))
      (setq tok (strcat tok ch)))
    (setq i (1+ i)))
  (if (/= tok "") (setq toks (cons tok toks)))
  (setq out '() bad (null toks))
  (foreach tok toks
    (setq r (perp:range tok))
    (if (null r)
      (setq bad T)
      (progn
        (setq a (car r) b (cadr r))
        (if (or (< a 1) (> b maxn) (> a b))
          (setq bad T)
          (while (<= a b)
            (if (not (member a out)) (setq out (cons a out)))
            (setq a (1+ a)))))))
  (if bad nil out))

;; --- the overall width -----------------------------------------------
;; Widths get re-measured, and the number that comes back is the
;; distance straight across, end to end -- NOT the developed length of
;; the object on the drawing, which on anything bowed is the longer of
;; the two.  Making that width true is one scale about the midpoint of
;; the two ends: exactly half the difference lands at each end, the
;; direction of travel and the offset side are left alone, and the shape
;; between the ends is carried along with it.

;; Ask whether the overall width has changed.  Returns the width to work
;; to, or nil when it has not -- so an unchanged answer skips the resize
;; altogether and the command behaves exactly as it always did.  d is
;; the width the drawing carries now.
(defun perp:ask-width (d / kws ans v w)
  (princ (strcat "\nOverall width, end to end: " (rtos d) "."))
  (setq kws "Grew Shrank New Unchanged")
  (initget kws)
  (setq ans (getkword (strcat "\nHas that width changed? ["
                              (vl-string-translate " " "/" kws)
                              "] <Unchanged>: ")))
  (cond
    ((or (null ans) (= ans "Unchanged")) nil)
    ((= ans "Grew")
     (initget 7)                              ; a real, positive amount
     (+ d (getdist "\nHow much wider? ")))
    ((= ans "Shrank")
     (while (null w)
       (initget 7)
       (setq v (getdist "\nHow much narrower? "))
       (if (< v d)
         (setq w (- d v))
         (princ "\nThat is the whole width or more - nothing would be left.")))
     w)
    (t                                        ; New: the width itself
     (initget 6)                              ; Enter keeps what is drawn
     (setq v (getdist (strcat "\nNew overall width <" (rtos d) ">: ")))
     (if (or (null v) (equal v d 1e-9)) nil v))))

;; Scale en about ctr (a point in the current UCS) by k.  T when the
;; drawing took it, nil when it would not -- a locked, frozen or
;; switched-off layer is the usual reason, and the caller has to say so
;; rather than measure offsets against geometry the drawing does not
;; actually have.
(defun perp:rescale (en ctr k / r)
  (setq r (vl-catch-all-apply
            'vla-ScaleEntity
            (list (vlax-ename->vla-object en)
                  (vlax-3d-point (trans ctr 1 0))
                  k)))
  (not (vl-catch-all-error-p r)))

;; p scaled about ctr by k, in plan; z is carried through untouched
(defun perp:scale-pt (p ctr k)
  (list (+ (car ctr)  (* k (- (car p)  (car ctr))))
        (+ (cadr ctr) (* k (- (cadr p) (cadr ctr))))
        (caddr p)))

;; every point of pts scaled about ctr by k
(defun perp:scale-pts (pts ctr k / out p)
  (setq out '())
  (foreach p pts (setq out (cons (perp:scale-pt p ctr k) out)))
  (reverse out))

;; --- command ---------------------------------------------------------

(defun c:PERPPTS (/ *error* perp:kill perp:finish
                    os ce pd plt clay cec celt celw celts cdim undoOpen
                    tmpEnts
                    srcData srcLayer srcColor srcLtype srcLw srcLts
                    dimPairs dimStyle pr
                    sel ent etype verts p1 p2 pStart pFinish click
                    dx dy dlen ux uy cross fuzz nx ny sz
                    arlen hlen tailx taily ca sa bkx bky b1x b1y b2x b2y
                    path pathEnt n lastN basePts newPts guideEnts total
                    len lastLen i base np again ans iter p e seg
                    join lastJoin kws nseg picks reply tangs
                    wOld wNew mid fac)

  ;; erase one temporary entity and forget it
  (defun perp:kill (e)
    (if e
      (progn (if (entget e) (entdel e))
             (setq tmpEnts (vl-remove e tmpEnts)))))

  ;; single cleanup path shared by normal exit, Esc and errors
  (defun perp:finish (/ guard)
    ;; cancel any command left pending by an Esc mid-PLINE/DIMALIGNED
    (setq guard 0)
    (while (and (> (getvar "CMDACTIVE") 0) (< guard 10))
      (command)
      (setq guard (1+ guard)))
    (foreach e tmpEnts (if (and e (entget e)) (entdel e)))
    (setq tmpEnts nil)
    ;; leave the drawing's creation defaults exactly as they were found
    (if cec   (setvar "CECOLOR"   cec))
    (if celt  (setvar "CELTYPE"   celt))
    (if celw  (setvar "CELWEIGHT" celw))
    (if celts (setvar "CELTSCALE" celts))
    (if (and cdim (tblsearch "DIMSTYLE" cdim))
      (command "._-DIMSTYLE" "_Restore" cdim))
    (if clay (setvar "CLAYER"  clay))
    (if pd   (setvar "PDMODE"  pd))
    (if os   (setvar "OSMODE"  os))
    (if plt  (setvar "PLINETYPE" plt))
    (if ce   (setvar "CMDECHO" ce))
    (if undoOpen
      (progn (command "._UNDO" "_End") (setq undoOpen nil))))

  (defun *error* (msg)
    (perp:finish)
    (if (and msg (not (wcmatch (strcase msg) "*BREAK*,*CANCEL*,*QUIT*,*EXIT*")))
      (princ (strcat "\nError: " msg))
      (princ "\nCancelled."))
    (princ))

  ;; --- save state and open one undo group for the whole run -----------
  (setq os    (getvar "OSMODE")
        ce    (getvar "CMDECHO")
        pd    (getvar "PDMODE")
        plt   (getvar "PLINETYPE")
        clay  (getvar "CLAYER")
        cec   (getvar "CECOLOR")
        celt  (getvar "CELTYPE")
        celw  (getvar "CELWEIGHT")
        celts (getvar "CELTSCALE")
        cdim  (getvar "DIMSTYLE")
        tmpEnts '())
  (setvar "CMDECHO" 0)
  ;; PLINE must produce a lightweight polyline, the only kind an arc
  ;; bulge can be written onto
  (setvar "PLINETYPE" 2)
  (command "._UNDO" "_Begin")
  (setq undoOpen T)
  ;; guide points must be visible whatever the drawing's PDMODE is
  (if (member pd '(0 1)) (setvar "PDMODE" 3))

  ;; --- 1. select a line (re-prompts until valid) -----------------------
  (setq ent nil)
  (while (null ent)
    (setq sel (entsel "\nSelect a line or polyline: "))
    (cond
      ((null sel)
       (princ "\nNothing selected - try again, or press Esc to quit."))
      (t
       (setq etype (cdr (assoc 0 (entget (car sel))))
             verts (perp:verts (car sel)))
       (cond
         ((null verts)
          (princ (strcat "\nA " etype " is not a line or polyline.")))
         ((< (length (setq verts (perp:dedupe verts))) 2)
          (princ "\nThat object has no usable length."))
         ((<= (distance (car verts) (last verts)) 1e-9)
          (princ "\nStart and end coincide - a closed shape has no direction."))
         (t (setq ent (car sel)))))))

  (setq p1 (car verts)                       ; first endpoint (UCS)
        p2 (last verts))                     ; last endpoint  (UCS)

  ;; --- 2. has the overall width changed? -------------------------------
  ;; The width asked about is the distance straight across, end to end,
  ;; not the developed length of the object -- a bowed polyline runs
  ;; further than the width it spans, and it is the width that gets
  ;; re-measured.  Making a new one true is a scale about the midpoint of
  ;; the two ends, so exactly half the difference lands at each end.  The
  ;; drawing is resized too: the offsets and their dimensions are
  ;; measured off this object, so leaving it at the old width would put
  ;; every base point somewhere the drawing says nothing is.  It is all
  ;; inside the command's undo group, so one U puts the width back.
  (setq dx   (- (car p2)  (car p1))
        dy   (- (cadr p2) (cadr p1))
        wOld (sqrt (+ (* dx dx) (* dy dy)))
        ;; a plan projection with no width at all has nothing to
        ;; ask about; the direction click below is where that
        ;; gets reported
        wNew (if (> wOld 1e-9) (perp:ask-width wOld)))
  (if wNew
    (progn
      (setq mid (list (/ (+ (car p1)  (car p2))  2.0)
                      (/ (+ (cadr p1) (cadr p2)) 2.0)
                      (caddr p1))
            fac (/ wNew wOld))
      (if (not (perp:rescale ent mid fac))
        (progn
          (princ (strcat "\nThe line could not be resized - it is most"
                         " likely on a locked, frozen or switched-off"
                         " layer.  Free the layer and run PERPPTS again."))
          (perp:finish)
          (exit)))
      (setq verts (perp:scale-pts verts mid fac)
            p1    (car verts)
            p2    (last verts))
      (princ (strcat "\nWidth " (rtos wOld) " -> " (rtos wNew) ": "
                     (rtos (/ (abs (- wNew wOld)) 2.0))
                     (if (> wNew wOld) " added at" " taken off")
                     " each end."))))

  ;; --- properties to give the offset polylines -------------------------
  ;; The new polylines are drawn with the same layer, colour, linetype,
  ;; lineweight and linetype scale as the object they are offset from, so
  ;; they read as the same kind of object in the drawing.  Anything the
  ;; source does not carry explicitly is BYLAYER, which is also the
  ;; correct inherited value.
  (setq srcData  (entget ent)
        srcLayer (cdr (assoc 8 srcData))
        srcColor (perp:color srcData)
        srcLtype (cond ((cdr (assoc 6 srcData))) ("BYLAYER"))
        srcLw    (cond ((cdr (assoc 370 srcData))) (-1))
        srcLts   (cond ((cdr (assoc 48 srcData))) (1.0)))

  ;; --- 3. click to set direction (START/FINISH) and offset side -------
  ;; Snapping is off so the click cannot be pulled onto the line itself,
  ;; which would make "which side" ambiguous.
  (setvar "OSMODE" 0)
  (setq click nil)
  (while (null click)
    (setq click (getpoint "\nClick to pick direction / offset side: "))
    (cond
      ((null click)
       (princ "\nA point is required - click one side of the line."))
      (t
       ;; nearest endpoint to the click = START
       (if (<= (distance click p1) (distance click p2))
         (setq pStart p1 pFinish p2)
         (setq pStart p2 pFinish p1))
       (setq dx   (- (car pFinish)  (car pStart))
             dy   (- (cadr pFinish) (cadr pStart))
             dlen (sqrt (+ (* dx dx) (* dy dy))))
       (cond
         ((equal dlen 0.0 1e-9)
          (princ "\nSelected object has zero length.")
          (perp:finish)
          (exit))
         (t
          (setq ux (/ dx dlen)
                uy (/ dy dlen))
          ;; cross = signed distance from the infinite line;
          ;; >0 => click is on the left.
          (setq cross (- (* ux (- (cadr click) (cadr pStart)))
                         (* uy (- (car click)  (car pStart))))
                fuzz  (max 1e-8 (* dlen 1e-6)))
          (if (< (abs cross) fuzz)
            (progn
              (princ "\nThat point is on the line - click clearly to one side.")
              (setq click nil))))))))

  ;; perpendicular unit vector, chosen toward the clicked side.  This is
  ;; fixed for the whole command: every offset and dimension in every
  ;; round is measured along this direction, i.e. perpendicular to the
  ;; ORIGINAL line -- never to a later polyline.
  (if (>= cross 0.0)
    (setq nx (- uy) ny ux)          ; left normal
    (setq nx uy     ny (- ux)))     ; right normal

  ;; --- prepare the layers ---------------------------------------------
  ;; Guides live on their own layer so a locked current layer cannot stop
  ;; them being erased.  Offset polylines go on the source object's own
  ;; layer; dimensions go on DIMENSIONS.
  (cal:ensure-layer "PERPPTS-TEMP" 1)     ; guides, erased before the command ends
  (cal:ensure-layer "DIMENSIONS"   4)

  ;; --- draw an arrow pointing at the START end ------------------------
  ;; The arrow comes in from outside the line (along the FINISH->START
  ;; extension) with its tip on the START point.  Drawn in red so it is
  ;; visible on any background, and kept until the command finishes so the
  ;; entry order stays clear across repeat rounds.
  (setq sz (caddr pStart))
  (setq arlen (* dlen 0.15))                ; shaft length
  (if (< arlen 1e-6) (setq arlen 1.0))
  (setq hlen (* arlen 0.35))                ; arrowhead barb length
  ;; tail = START minus (shaft along the line direction), tip = START
  (setq tailx (- (car pStart)  (* ux arlen))
        taily (- (cadr pStart) (* uy arlen)))
  ;; barbs: rotate the "back" vector b = (-ux,-uy) by +/-25 degrees
  (setq ca 0.9063 sa 0.4226                 ; cos/sin 25 deg
        bkx (- ux) bky (- uy))
  (setq b1x (+ (car pStart)  (* hlen (- (* bkx ca) (* bky sa))))
        b1y (+ (cadr pStart) (* hlen (+ (* bkx sa) (* bky ca))))
        b2x (+ (car pStart)  (* hlen (+ (* bkx ca) (* bky sa))))
        b2y (+ (cadr pStart) (* hlen (+ (* (- bkx) sa) (* bky ca)))))
  ;; entmade LINE points are WCS, so convert from the current UCS
  (foreach seg (list (list (list tailx taily sz) pStart)
                     (list pStart (list b1x b1y sz))
                     (list pStart (list b2x b2y sz)))
    (entmake (list '(0 . "LINE") '(8 . "PERPPTS-TEMP") '(62 . 1)
                   (cons 10 (trans (car seg)  1 0))
                   (cons 11 (trans (cadr seg) 1 0))))
    (setq tmpEnts (cons (entlast) tmpEnts)))

  ;; --- offset rounds --------------------------------------------------
  ;; the path the points are spaced along.  Round 1 uses the selected
  ;; object, oriented START -> FINISH; each later round uses the polyline
  ;; the previous round built.
  (setq path (if (equal pStart (car verts) 1e-9) verts (reverse verts))
        again "Yes"
        iter  0
        total 0)

  (while (equal again "Yes")
    (setq iter (1+ iter))

    ;; --- how many values / points for this round ---------------------
    ;; Enter reuses the previous round's count.
    (setq n nil)
    (while (null n)
      (initget 6)                            ; no zero, no negative
      (setq n (getint (strcat "\nRound " (itoa iter)
                              " - how many values (points) are required?"
                              (if lastN (strcat " <" (itoa lastN) ">") "")
                              " ")))
      (if (null n) (setq n lastN))           ; Enter = same count as last round
      (cond
        ((null n)
         (princ "\nA number is required."))
        ((< n 2)
         (princ "\nNeed at least 2 points.")
         (setq n nil))
        ((> n 100)
         ;; guard against a mistyped count creating thousands of entities
         (initget "Yes No")
         (setq ans (getkword
                     (strcat "\n" (itoa n) " points means " (itoa n)
                             " dimensions. Continue? [Yes/No] <No>: ")))
         (if (not (equal ans "Yes")) (setq n nil)))))
    (setq lastN n)

    ;; base points, equally spaced along the current path.  The offset
    ;; side (nx,ny) was fixed from the direction click and is reused for
    ;; every round, so all rounds offset to the same side.  A path drawn
    ;; with arcs is measured along the curve itself (pathEnt); a
    ;; straight one is measured along its own points, which is the same
    ;; walk over the chords.
    (setq basePts (cond ((and pathEnt (perp:ent-pts pathEnt n)))
                        ((perp:sample path n))))

    ;; --- length per point + build the new perpendicular points -------
    ;; Enter reuses the last length entered (shown as the prompt
    ;; default), since runs of equal lengths are common; the last value
    ;; carries across rounds.  Back steps back a point (Undo is kept as
    ;; a hidden synonym for old habits).  Zero and negative lengths are
    ;; rejected, so a dimension is never degenerate and the offset can
    ;; never flip to the wrong side.
    (setvar "CLAYER" "PERPPTS-TEMP")
    (setq newPts '() guideEnts '() i 0)
    (while (< i n)
      (setq base (nth i basePts))
      (initget 6 "Back Undo")                ; no zero, no negative
      (setq len (getdist (strcat "\nLength for point " (itoa (1+ i))
                                 " of " (itoa n)
                                 (if lastLen
                                   (strcat " <" (rtos lastLen) ">")
                                   "")
                                 " [Back]: ")))
      (if (null len) (setq len lastLen))     ; Enter = same as last time
      (cond
        ;; step back one point and re-enter it (getdist returned "Back",
        ;; or "Undo" - the old keyword, kept as a synonym)
        ((eq (type len) 'STR)
         (if (> i 0)
           (progn
             (setq i (1- i))
             (perp:kill (car guideEnts))
             (setq guideEnts (cdr guideEnts)
                   newPts    (cdr newPts))
             (princ "\nStepping back one point."))
           (princ "\nAlready at the first point.")))
        ((null len)
         (princ "\nA length is required."))
        (t
         (setq lastLen len
               np      (list (+ (car base)  (* len nx))
                             (+ (cadr base) (* len ny))
                             (caddr base)))
         (setq newPts (cons np newPts))
         ;; temporary POINT node at the new location as a guide
         (command "._POINT" np)
         (setq guideEnts (cons (entlast) guideEnts)
               tmpEnts   (cons (entlast) tmpEnts))
         (setq i (1+ i)))))
    (setq newPts (reverse newPts))

    ;; --- straight lines, arcs, or both -------------------------------
    ;; Straight is what this routine has always drawn and stays the
    ;; opening default; Arcs curves every segment; Mixed asks which
    ;; segment numbers to curve and leaves the rest as lines.  Two
    ;; points make one segment with no neighbouring point to take a
    ;; curvature from, so below three points there is nothing to ask.
    ;; The answer carries across rounds as the offered default.
    (setq nseg  (1- n)
          kws   "Straight Arcs Mixed"
          picks nil)
    (if (null lastJoin) (setq lastJoin "Straight"))
    (if (< n 3)
      (progn
        (princ "\nTwo points make one straight segment - nothing to curve.")
        (setq join "Straight"))
      (setq join nil))
    (while (null join)
      (initget kws)
      (setq join (getkword (strcat "\nRound " (itoa iter)
                                   " - how should the points be joined? ["
                                   (vl-string-translate " " "/" kws)
                                   "] <" lastJoin ">: ")))
      (if (null join) (setq join lastJoin))   ; Enter = same as last round
      ;; Mixed is not an answer on its own - it needs the segment list,
      ;; and Back returns to the question above rather than guessing
      (if (equal join "Mixed")
        (while (and join (null picks))
          (setq reply (getstring T
                        (strcat "\nWhich segments are arcs (1 to "
                                (itoa nseg) ", e.g. 1 3-5)? (B = back): ")))
          (cond
            ((member (strcase reply) '("B" "BACK" "U" "UNDO"))
             (setq join nil))
            ((setq picks (perp:parse-segs reply nseg)))
            (t (princ (strcat "\nSegment numbers run 1 to " (itoa nseg)
                              " - single numbers, ranges like 3-5, or"
                              " both.")))))))
    (setq lastJoin join)

    ;; --- connect the new points with a polyline ----------------------
    ;; drawn with the source object's layer and line properties
    (setvar "CLAYER"    srcLayer)
    (setvar "CECOLOR"   srcColor)
    (setvar "CELTYPE"   srcLtype)
    (setvar "CELWEIGHT" srcLw)
    (setvar "CELTSCALE" srcLts)
    (command "._PLINE")
    (foreach p newPts (command p))
    (command "")
    ;; One tangent per vertex; perp:arcs turns the segments picks names
    ;; into arcs and writes the rest straight, so the same call draws an
    ;; all-arc round and a mixed one.  The polyline keeps its vertices,
    ;; so every arc still runs through the measured points and every
    ;; dimension still lands on the curve.
    (setq tangs (if (equal join "Straight") nil (perp:tangents newPts)))
    (if tangs (perp:arcs (entlast) newPts tangs picks))
    ;; a round that drew arcs is the next round's curve to measure along
    (setq pathEnt (if tangs (entlast)))
    (princ (strcat "\nRound " (itoa iter) ": polyline drawn "
                   (cond ((equal join "Straight") "with straight segments")
                         ((equal join "Arcs")     "with arcs through the points")
                         (t (strcat "with arcs on " (itoa (length picks))
                                    " of " (itoa nseg) " segments")))
                   "."))

    ;; --- erase this round's point guides -----------------------------
    (foreach e guideEnts (perp:kill e))
    (setq guideEnts nil)

    ;; --- remember the dimensions to draw -----------------------------
    ;; np = base + len*(nx,ny), so each dimension runs along the fixed
    ;; normal, i.e. perpendicular to the ORIGINAL line, no matter which
    ;; polyline `base` sits on.  They are drawn once at the end, after
    ;; the dimension style has been chosen.
    (setq i 0)
    (while (< i n)
      (setq dimPairs (cons (list (nth i basePts) (nth i newPts)) dimPairs)
            i        (1+ i)))
    (setq total (+ total n))

    ;; the polyline just built becomes the path for the next round
    (setq path newPts)

    ;; --- repeat? -----------------------------------------------------
    (initget "Yes No")
    (setq again (getkword "\nRepeat on the new polyline? [Yes/No] <No>: "))
    (if (null again) (setq again "No")))

  ;; --- 8. dimension style, then draw every dimension ------------------
  (initget "STandard SIde")
  (setq ans (getkword (strcat "\nDimension style - STANDARD INCHES or "
                              "SIDE STANDARD? [STandard/SIde] <STandard>: ")))
  (setq dimStyle (if (equal ans "SIde") "SIDE STANDARD" "STANDARD INCHES"))
  (if (tblsearch "DIMSTYLE" dimStyle)
    (command "._-DIMSTYLE" "_Restore" dimStyle)
    (princ (strcat "\nDimension style \"" dimStyle
                   "\" is not in this drawing - using the current style \""
                   cdim "\" instead.")))

  (setvar "CLAYER" "DIMENSIONS")
  (foreach pr (reverse dimPairs)
    (command "._DIMALIGNED" (car pr) (cadr pr) (cadr pr)))

  ;; --- restore everything and close the undo group --------------------
  (perp:finish)
  (princ (strcat "\nDone: " (itoa iter) " round(s), "
                 (itoa total) " points, "
                 (itoa iter) " polyline(s) on layer \"" srcLayer "\" and "
                 (itoa total) " dimensions on layer \"DIMENSIONS\"."))
  (princ))

(princ (strcat "\nperp_points.lsp " *perp-version*
               " loaded.  Type PERPPTS to run."))
(princ)


;;; ======================================================================
;;; >>> cperp_points.lsp
;;; ======================================================================

;;; cperp_points.lsp  --  AutoCAD 2018 (AutoLISP)
;;;
;;; Command: CPERPPTS   ("C" for curved)
;;;
;;; SHARED BUILD: requires CALOFIN-LIB.lsp (load via CALOFIN-LOADER.lsp).
;;; Generic helpers live there under cal: - see STANDARDS.md.
;;;
;;; The curved-geometry companion to PERPPTS (perp_points.lsp).  Same
;;; workflow and same pipeline, but the offsets are taken perpendicular
;;; to the TANGENT of the curve rather than to a straight line, so arcs,
;;; bulged polylines and splines can be offset with a different length
;;; at every point.
;;;
;;; Works on anything AutoCAD treats as a curve: LWPOLYLINE (including
;;; arc/bulge segments), POLYLINE, LINE, ARC, ELLIPSE and SPLINE.
;;;
;;; The offset points are joined into a single LWPOLYLINE whose
;;; segments are ARCS (bulges), each arc matched to the curve's tangent
;;; direction at its start point.  The result is a smooth POLYLINE
;;; curve passing exactly through every offset point -- a real
;;; lightweight polyline, never a spline and never a curve-fit heavy
;;; polyline.
;;;
;;; Points are spaced by true arc length along the curve, so spacing
;;; stays even through curved segments instead of bunching up.
;;;
;;; Workflow
;;;   1. Select a curve (open, i.e. not a closed loop).
;;;   2. Say whether the overall width has changed: Grew, Shrank, New
;;;      or Unchanged.  The width meant is the distance straight across,
;;;      end to end, not the length of the curve; half of any difference
;;;      is added to (or taken off) each end, and the curve in the
;;;      drawing is resized to match.
;;;   3. Click a point to set the direction:
;;;        - the curve end nearest the click becomes START, the far end
;;;          FINISH, fixing the order the lengths are entered in;
;;;        - the side of the curve the click lands on is the side the
;;;          new points are offset toward.
;;;   4. Enter how many values (points) are required  (>= 2).
;;;   5. Enter a length for each point, in order START -> FINISH.
;;;      Press Enter to reuse the previous length when it repeats, or
;;;      type B (Back) to step back and re-enter the previous point
;;;      (U, the old keyword, is still accepted).
;;;   6. Choose whether to repeat on the new polyline.  If so, enter a
;;;      new point count and repeat from step 5 with the new polyline as
;;;      the path.
;;;   7. Pick the dimension style, STANDARD INCHES or SIDE STANDARD.
;;;      Every dimension is then drawn at once, on the DIMENSIONS layer.
;;;
;;; The overall width
;;;   Walls get re-measured, and the number that comes back is the
;;;   distance straight across, end to end.  That is what step 2 asks
;;;   for -- never the developed length of the CURVE, which on anything
;;;   bowed runs further than the width it spans.  Grew and Shrank take
;;;   the difference, New takes the width itself, and Unchanged (the
;;;   default, and Enter) leaves everything exactly as it was.
;;;
;;;   A new width is made true by scaling the selected curve about the
;;;   midpoint of its two ends, so exactly half the difference lands at
;;;   each end and the curve keeps its shape: an arc stays that arc,
;;;   scaled.  The curve in the drawing is resized too, not just the
;;;   numbers behind it -- the offsets and their dimensions are measured
;;;   off it, so leaving it at the old width would put every base point
;;;   somewhere the drawing says nothing is.  The base points and
;;;   dimensions then follow the resized curve, since they are spaced
;;;   along it after the resize.  The whole thing sits inside the
;;;   command's undo group, so one U puts the width back.
;;;
;;; How the offset direction is found
;;;   Every round works from the NEWEST curve.  Round 1 offsets from the
;;;   selected curve; each later round offsets from the arc polyline
;;;   the previous round built.  Each base point sits on that
;;;   newest curve, and its offset runs along the normal of the curve's
;;;   tangent underneath it -- so both the offset and its dimension read
;;;   perpendicular to the line the point actually sits on, and each
;;;   round follows the shape its predecessor took.
;;;
;;;   Which side is used is fixed once, from the direction click,
;;;   relative to the direction of travel (START -> FINISH), so every
;;;   point in every round offsets to the same side however the curves
;;;   bend.
;;;
;;; Properties
;;;   * The offset polylines take the layer, colour, linetype, lineweight
;;;     and linetype scale of the curve they were offset from.
;;;   * The dimensions go on the DIMENSIONS layer (created if missing)
;;;     and use the dimension style picked in step 6 when the drawing
;;;     has it; otherwise the current style is used and a note is
;;;     printed.
;;;
;;; Robustness
;;;   * The whole run is one UNDO group: a single U reverses everything.
;;;   * Esc or an error at any prompt restores every system variable it
;;;     changed (OSMODE, CMDECHO, PDMODE, CLAYER, the CE* creation
;;;     defaults and the current dimension style), erases the temporary
;;;     guides and closes the UNDO group.
;;;   * Bad input re-prompts instead of aborting the command; zero and
;;;     negative lengths are rejected, as is a direction click that lands
;;;     on the curve itself (where "which side" would be ambiguous).
;;;   * All geometry is handled in the current UCS, so the command works
;;;     in a rotated or shifted UCS.
;;;
;;; Note: on a tight concave bend, normals converge and large offsets
;;; can make the new curve cross itself -- inherent to offsetting along
;;; normals, not a fault of the routine.  The arc segments pass exactly
;;; through every offset point, so each dimension's endpoint lies on
;;; the new curve.
;;;
;;; License: GPL-3.0-or-later
;;; ---------------------------------------------------------------------

(vl-load-com)

;; Version banner: tools/release_lisp.py reads it to stamp the dated
;; REV twin in releases/ (vN.M -> _MMDDYY_REVNM).
(setq *cperp-version* "v0.4")

;; --- generic helpers -------------------------------------------------

;; colour of an entity as a CECOLOR string ("BYLAYER", "3", "12,34,56")
(defun cperp:color (d / c tc)
  (cond
    ((setq tc (cdr (assoc 420 d)))
     (strcat (itoa (logand (lsh tc -16) 255)) ","
             (itoa (logand (lsh tc -8) 255)) ","
             (itoa (logand tc 255))))
    ((setq c (cdr (assoc 62 d)))
     (cond ((= c 0) "BYBLOCK")
           ((= c 256) "BYLAYER")
           (t (itoa (abs c)))))
    (t "BYLAYER")))

;; --- curve helpers ---------------------------------------------------
;; vlax-curve-* works on any curve entity and always speaks WCS, so the
;; results are converted into the current UCS as they come back.

;; is this entity something AutoCAD can measure along?
(defun cperp:curve-p (e / r)
  (setq r (vl-catch-all-apply 'vlax-curve-getEndParam (list e)))
  (and r (not (vl-catch-all-error-p r))))

;; total length of the curve
(defun cperp:curvelen (crv)
  (vlax-curve-getDistAtParam crv (vlax-curve-getEndParam crv)))

;; point at arc-length distance d along the curve, in the current UCS
(defun cperp:pt-at-dist (crv d tot / p)
  (setq d (cond ((< d 0.0) 0.0) ((> d tot) tot) (t d)))
  (if (setq p (vlax-curve-getPointAtDist crv d))
    (trans p 0 1)))

;; n points equally spaced by arc length along the curve, START first.
;; rev traverses the curve from its far end.
(defun cperp:curve-pts (crv n rev / tot i d out)
  (setq tot (cperp:curvelen crv) out '() i 0)
  (while (< i n)
    (setq d (* (/ (float i) (float (1- n))) tot))
    (if rev (setq d (- tot d)))
    (setq out (cons (cperp:pt-at-dist crv d tot) out)
          i   (1+ i)))
  (reverse out))

;; Unit tangent of the curve (current UCS) at the point of the curve
;; closest to pt, as a 2D (x y) vector.  rev flips it so the tangent
;; follows the direction of travel when the curve is being traversed
;; from its far end.  Returns nil at a cusp.
(defun cperp:tangent (crv pt rev / w p prm d dx dy dl)
  (setq w   (trans pt 1 0)
        p   (vlax-curve-getClosestPointTo crv w))
  (if (null p)
    nil
    (progn
      (setq prm (vlax-curve-getParamAtPoint crv p))
      ;; floating point can put the projected point a hair off the curve
      (if (null prm)
        (setq prm (vlax-curve-getParamAtDist
                    crv (vlax-curve-getDistAtPoint crv p))))
      (if (null prm)
        nil
        (progn
          ;; a derivative is a direction, so transform it as a displacement
          (setq d  (trans (vlax-curve-getFirstDeriv crv prm) 0 1 T)
                dx (car d)
                dy (cadr d)
                dl (sqrt (+ (* dx dx) (* dy dy))))
          (if (< dl 1e-12)
            nil
            (progn
              (if rev (setq dx (- dx) dy (- dy)))
              (list (/ dx dl) (/ dy dl)))))))))

;; Bulge of the arc from a to b whose tangent at a is tg: tan(alpha/2)
;; where alpha is the signed angle from the tangent to the chord (the
;; arc's included angle is 2*alpha).  Sampling a circle this way
;; reproduces the circle exactly.  Falls back to a straight segment
;; (bulge 0) when there is no tangent or no chord.
(defun cperp:bulge (tg a b / cx cy dot crs alpha lim)
  (setq cx (- (car b) (car a))
        cy (- (cadr b) (cadr a)))
  (if (or (null tg)
          (< (sqrt (+ (* cx cx) (* cy cy))) 1e-12))
    0.0
    (progn
      (setq dot   (+ (* (car tg) cx) (* (cadr tg) cy))
            crs   (- (* (car tg) cy) (* (cadr tg) cx))
            alpha (atan crs dot))
      ;; a chord folding back on the tangent would blow the bulge up
      ;; toward infinity; cap the included angle at ~342 degrees
      (setq lim 2.98)
      (if (> alpha lim)     (setq alpha lim))
      (if (< alpha (- lim)) (setq alpha (- lim)))
      (/ (sin (/ alpha 2.0)) (cos (/ alpha 2.0))))))

;; Turn the straight LWPOLYLINE en (drawn through pts, whose travel
;; tangents are tangs) into an arc polyline: every segment becomes an
;; arc matched to the tangent at its start point.  The entity stays an
;; LWPOLYLINE -- only bulge values are written.
(defun cperp:arcs (en pts tangs / d out g i b)
  (setq d (entget en) out '() i 0)
  (foreach g d
    (cond
      ((= 42 (car g)))                       ; drop existing bulges
      ((= 10 (car g))
       (setq b (if (< (1+ i) (length pts))
                 (cperp:bulge (nth i tangs) (nth i pts) (nth (1+ i) pts))
                 0.0))
       (setq out (cons (cons 42 b) (cons g out))
             i   (1+ i)))
      (t (setq out (cons g out)))))
  (entmod (reverse out)))

;; --- the overall width -----------------------------------------------
;; Widths get re-measured, and the number that comes back is the
;; distance straight across, end to end -- NOT the developed length of
;; the object on the drawing, which on anything bowed is the longer of
;; the two.  Making that width true is one scale about the midpoint of
;; the two ends: exactly half the difference lands at each end, the
;; direction of travel and the offset side are left alone, and the shape
;; between the ends is carried along with it.

;; Ask whether the overall width has changed.  Returns the width to work
;; to, or nil when it has not -- so an unchanged answer skips the resize
;; altogether and the command behaves exactly as it always did.  d is
;; the width the drawing carries now.
(defun cperp:ask-width (d / kws ans v w)
  (princ (strcat "\nOverall width, end to end: " (rtos d) "."))
  (setq kws "Grew Shrank New Unchanged")
  (initget kws)
  (setq ans (getkword (strcat "\nHas that width changed? ["
                              (vl-string-translate " " "/" kws)
                              "] <Unchanged>: ")))
  (cond
    ((or (null ans) (= ans "Unchanged")) nil)
    ((= ans "Grew")
     (initget 7)                              ; a real, positive amount
     (+ d (getdist "\nHow much wider? ")))
    ((= ans "Shrank")
     (while (null w)
       (initget 7)
       (setq v (getdist "\nHow much narrower? "))
       (if (< v d)
         (setq w (- d v))
         (princ "\nThat is the whole width or more - nothing would be left.")))
     w)
    (t                                        ; New: the width itself
     (initget 6)                              ; Enter keeps what is drawn
     (setq v (getdist (strcat "\nNew overall width <" (rtos d) ">: ")))
     (if (or (null v) (equal v d 1e-9)) nil v))))

;; Scale en about ctr (a point in the current UCS) by k.  T when the
;; drawing took it, nil when it would not -- a locked, frozen or
;; switched-off layer is the usual reason, and the caller has to say so
;; rather than measure offsets against geometry the drawing does not
;; actually have.
(defun cperp:rescale (en ctr k / r)
  (setq r (vl-catch-all-apply
            'vla-ScaleEntity
            (list (vlax-ename->vla-object en)
                  (vlax-3d-point (trans ctr 1 0))
                  k)))
  (not (vl-catch-all-error-p r)))

;; --- command ---------------------------------------------------------

(defun c:CPERPPTS (/ *error* cperp:kill cperp:finish
                     os ce pd clay cec celt celw celts cdim undoOpen tmpEnts
                     srcData srcLayer srcColor srcLtype srcLw srcLts
                     dimPairs dimStyle pr
                     sel crv etype sp ep click rev side tot
                     tng prj cross fuzz nrm sz
                     arlen hlen p2 tx ty tailx taily ca sa bkx bky
                     b1x b1y b2x b2y
                     curCrv curRev n lastN basePts newPts usedBases idxs
                     tangs tg guideEnts total len lastLen i base np again
                     ans iter plt p e seg
                     wOld wNew mid fac)

  ;; erase one temporary entity and forget it
  (defun cperp:kill (e)
    (if e
      (progn (if (entget e) (entdel e))
             (setq tmpEnts (vl-remove e tmpEnts)))))

  ;; single cleanup path shared by normal exit, Esc and errors
  (defun cperp:finish (/ guard)
    (setq guard 0)
    (while (and (> (getvar "CMDACTIVE") 0) (< guard 10))
      (command)
      (setq guard (1+ guard)))
    (foreach e tmpEnts (if (and e (entget e)) (entdel e)))
    (setq tmpEnts nil)
    (if cec   (setvar "CECOLOR"   cec))
    (if celt  (setvar "CELTYPE"   celt))
    (if celw  (setvar "CELWEIGHT" celw))
    (if celts (setvar "CELTSCALE" celts))
    (if (and cdim (tblsearch "DIMSTYLE" cdim))
      (command "._-DIMSTYLE" "_Restore" cdim))
    (if clay (setvar "CLAYER"  clay))
    (if pd   (setvar "PDMODE"  pd))
    (if os   (setvar "OSMODE"  os))
    (if plt  (setvar "PLINETYPE" plt))
    (if ce   (setvar "CMDECHO" ce))
    (if undoOpen
      (progn (command "._UNDO" "_End") (setq undoOpen nil))))

  (defun *error* (msg)
    (cperp:finish)
    (if (and msg (not (wcmatch (strcase msg) "*BREAK*,*CANCEL*,*QUIT*,*EXIT*")))
      (princ (strcat "\nError: " msg))
      (princ "\nCancelled."))
    (princ))

  ;; --- save state and open one undo group for the whole run -----------
  (setq os    (getvar "OSMODE")
        ce    (getvar "CMDECHO")
        pd    (getvar "PDMODE")
        clay  (getvar "CLAYER")
        cec   (getvar "CECOLOR")
        celt  (getvar "CELTYPE")
        celw  (getvar "CELWEIGHT")
        celts (getvar "CELTSCALE")
        cdim  (getvar "DIMSTYLE")
        plt   (getvar "PLINETYPE")
        tmpEnts '())
  (setvar "CMDECHO" 0)
  ;; PLINE must produce a lightweight polyline so the arc bulges can be
  ;; written into it and the result stays a plain LWPOLYLINE
  (setvar "PLINETYPE" 2)
  (command "._UNDO" "_Begin")
  (setq undoOpen T)
  (if (member pd '(0 1)) (setvar "PDMODE" 3))

  ;; --- 1. select a curve (re-prompts until valid) ----------------------
  (setq crv nil)
  (while (null crv)
    (setq sel (entsel "\nSelect a curve (polyline, arc, spline...): "))
    (cond
      ((null sel)
       (princ "\nNothing selected - try again, or press Esc to quit."))
      (t
       (setq etype (cdr (assoc 0 (entget (car sel)))))
       (cond
         ((not (cperp:curve-p (car sel)))
          (princ (strcat "\nA " etype " is not a curve.")))
         ((< (cperp:curvelen (car sel)) 1e-9)
          (princ "\nThat curve has no length."))
         ((equal (vlax-curve-getStartPoint (car sel))
                 (vlax-curve-getEndPoint (car sel)) 1e-9)
          (princ (strcat "\nThat curve is closed, so it has no start or"
                         " end - use an open curve.")))
         (t (setq crv (car sel)))))))

  (setq tot (cperp:curvelen crv)
        sp  (trans (vlax-curve-getStartPoint crv) 0 1)
        ep  (trans (vlax-curve-getEndPoint crv) 0 1))

  ;; --- 2. has the overall width changed? -------------------------------
  ;; The width asked about is the distance straight across, end to end --
  ;; NOT the length of the curve, which on anything bowed runs a good
  ;; deal further than the width it spans, and it is the width that gets
  ;; re-measured.  Making a new one true is a scale about the midpoint of
  ;; the two ends, so exactly half the difference lands at each end and
  ;; the curve keeps its shape: an arc stays that arc, scaled.  The
  ;; drawing is resized too -- the offsets and their dimensions are
  ;; measured off this curve, so leaving it at the old width would put
  ;; every base point somewhere the drawing says nothing is.  It is all
  ;; inside the command's undo group, so one U puts the width back.
  (setq tx   (- (car ep)  (car sp))
        ty   (- (cadr ep) (cadr sp))
        wOld (sqrt (+ (* tx tx) (* ty ty)))
        ;; a plan projection with no width at all has nothing to
        ;; ask about; the direction click below is where that
        ;; gets reported
        wNew (if (> wOld 1e-9) (cperp:ask-width wOld)))
  (if wNew
    (progn
      (setq mid (list (/ (+ (car sp)  (car ep))  2.0)
                      (/ (+ (cadr sp) (cadr ep)) 2.0)
                      (caddr sp))
            fac (/ wNew wOld))
      (if (not (cperp:rescale crv mid fac))
        (progn
          (princ (strcat "\nThe curve could not be resized - it is most"
                         " likely on a locked, frozen or switched-off"
                         " layer.  Free the layer and run CPERPPTS again."))
          (cperp:finish)
          (exit)))
      ;; re-read: the curve itself is what every round measures along
      (setq tot (cperp:curvelen crv)
            sp  (trans (vlax-curve-getStartPoint crv) 0 1)
            ep  (trans (vlax-curve-getEndPoint crv) 0 1))
      (princ (strcat "\nWidth " (rtos wOld) " -> " (rtos wNew) ": "
                     (rtos (/ (abs (- wNew wOld)) 2.0))
                     (if (> wNew wOld) " added at" " taken off")
                     " each end."))))

  ;; --- properties to give the offset polylines -------------------------
  (setq srcData  (entget crv)
        srcLayer (cdr (assoc 8 srcData))
        srcColor (cperp:color srcData)
        srcLtype (cond ((cdr (assoc 6 srcData))) ("BYLAYER"))
        srcLw    (cond ((cdr (assoc 370 srcData))) (-1))
        srcLts   (cond ((cdr (assoc 48 srcData))) (1.0)))

  ;; --- 3. click to set direction (START/FINISH) and offset side -------
  ;; The side is measured against the direction of travel (START ->
  ;; FINISH), so later rounds -- whose curves are built in travel order
  ;; -- inherit the same side directly.
  (setvar "OSMODE" 0)
  (setq click nil)
  (while (null click)
    (setq click (getpoint "\nClick to pick direction / offset side: "))
    (cond
      ((null click)
       (princ "\nA point is required - click one side of the curve."))
      (t
       ;; nearest end of the curve to the click = START
       (setq rev (> (distance click sp) (distance click ep)))
       (cond
         ((null (setq tng (cperp:tangent crv click rev)))
          (princ "\nCannot read the curve direction there - click elsewhere.")
          (setq click nil))
         (t
          ;; signed offset of the click from the tangent line at the
          ;; projection of the click onto the curve
          (setq prj (trans (vlax-curve-getClosestPointTo
                             crv (trans click 1 0))
                           0 1))
          (setq cross (- (* (car tng)  (- (cadr click) (cadr prj)))
                         (* (cadr tng) (- (car click)  (car prj))))
                fuzz  (max 1e-8 (* tot 1e-6)))
          (if (< (abs cross) fuzz)
            (progn
              (princ "\nThat point is on the curve - click clearly to one side.")
              (setq click nil))))))))

  (setq side (if (>= cross 0.0) 1.0 -1.0))

  ;; --- prepare the layers ---------------------------------------------
  (cal:ensure-layer "PERPPTS-TEMP" 1)
  (cal:ensure-layer "DIMENSIONS"   4)

  ;; --- draw an arrow pointing at the START end ------------------------
  ;; The shaft runs back from START along the curve's tangent there, so
  ;; the arrow sits outside the curve pointing at the end the lengths
  ;; are entered from.
  (setq p  (if rev ep sp)
        sz (caddr p))
  ;; a point a little way along the traversal gives the start tangent
  (setq p2 (cperp:pt-at-dist crv
                             (if rev (- tot (* tot 0.001)) (* tot 0.001))
                             tot))
  (setq tx (- (car p2)  (car p))
        ty (- (cadr p2) (cadr p)))
  (if (< (distance p p2) 1e-9)
    (setq tx 1.0 ty 0.0)
    (setq tx (/ tx (distance p p2))
          ty (/ ty (distance p p2))))
  (setq arlen (* tot 0.15))
  (if (< arlen 1e-6) (setq arlen 1.0))
  (setq hlen  (* arlen 0.35)
        tailx (- (car p)  (* tx arlen))
        taily (- (cadr p) (* ty arlen)))
  (setq ca 0.9063 sa 0.4226                 ; cos/sin 25 deg
        bkx (- tx) bky (- ty))
  (setq b1x (+ (car p)  (* hlen (- (* bkx ca) (* bky sa))))
        b1y (+ (cadr p) (* hlen (+ (* bkx sa) (* bky ca))))
        b2x (+ (car p)  (* hlen (+ (* bkx ca) (* bky sa))))
        b2y (+ (cadr p) (* hlen (+ (* (- bkx) sa) (* bky ca)))))
  (foreach seg (list (list (list tailx taily sz) p)
                     (list p (list b1x b1y sz))
                     (list p (list b2x b2y sz)))
    (entmake (list '(0 . "LINE") '(8 . "PERPPTS-TEMP") '(62 . 1)
                   (cons 10 (trans (car seg)  1 0))
                   (cons 11 (trans (cadr seg) 1 0))))
    (setq tmpEnts (cons (entlast) tmpEnts)))

  ;; --- offset rounds --------------------------------------------------
  ;; Every round samples and offsets from the NEWEST curve: the selected
  ;; curve in round 1 (traversed from the clicked end), then the
  ;; arc polyline each round builds.  Later curves are built in travel
  ;; order, so their traversal is never reversed.
  (setq curCrv crv
        curRev rev
        again  "Yes"
        iter   0
        total  0)

  (while (equal again "Yes")
    (setq iter (1+ iter))

    ;; --- how many values / points for this round ---------------------
    (setq n nil)
    (while (null n)
      (initget 6)
      (setq n (getint (strcat "\nRound " (itoa iter)
                              " - how many values (points) are required?"
                              (if lastN (strcat " <" (itoa lastN) ">") "")
                              " ")))
      (if (null n) (setq n lastN))
      (cond
        ((null n)
         (princ "\nA number is required."))
        ((< n 2)
         (princ "\nNeed at least 2 points.")
         (setq n nil))
        ((> n 100)
         (initget "Yes No")
         (setq ans (getkword
                     (strcat "\n" (itoa n) " points means " (itoa n)
                             " dimensions. Continue? [Yes/No] <No>: ")))
         (if (not (equal ans "Yes")) (setq n nil)))))
    (setq lastN n)

    ;; base points, equally spaced by true arc length along the newest
    ;; curve, START first
    (setq basePts (cperp:curve-pts curCrv n curRev))

    ;; --- length per point + build the new perpendicular points -------
    ;; usedBases collects the base of each created point so bases and
    ;; new points stay paired even when a point is skipped; tangs holds
    ;; the travel tangent under each created point (it becomes the arc
    ;; direction of the new polyline there); idxs records each created
    ;; point's position so Back returns to the right prompt even across
    ;; skipped points.
    (setvar "CLAYER" "PERPPTS-TEMP")
    (setq newPts '() usedBases '() tangs '() idxs '() guideEnts '() i 0)
    (while (< i n)
      (setq base (nth i basePts)
            tg   (cperp:tangent curCrv base curRev)
            nrm  (if tg (list (* side (- (cadr tg))) (* side (car tg)))))
      (cond
        ;; no readable tangent under this point - skip it rather than
        ;; place the offset in an arbitrary direction
        ((null nrm)
         (princ (strcat "\nSkipping point " (itoa (1+ i))
                        ": the curve direction cannot be read there."))
         (setq i (1+ i)))
        (t
         (initget 6 "Back Undo")     ; Undo kept as a hidden synonym
         (setq len (getdist (strcat "\nLength for point " (itoa (1+ i))
                                    " of " (itoa n)
                                    (if lastLen
                                      (strcat " <" (rtos lastLen) ">")
                                      "")
                                    " [Back]: ")))
         (if (null len) (setq len lastLen))
         (cond
           ((eq (type len) 'STR)
            (if newPts
              (progn
                (setq i (car idxs))          ; back to that point's prompt
                (cperp:kill (car guideEnts))
                (setq guideEnts (cdr guideEnts)
                      newPts    (cdr newPts)
                      usedBases (cdr usedBases)
                      tangs     (cdr tangs)
                      idxs      (cdr idxs))
                (princ "\nStepping back one point."))
              (princ "\nAlready at the first point.")))
           ((null len)
            (princ "\nA length is required."))
           (t
            (setq lastLen len
                  np      (list (+ (car base)  (* len (car nrm)))
                                (+ (cadr base) (* len (cadr nrm)))
                                (caddr base)))
            (setq newPts    (cons np newPts)
                  usedBases (cons base usedBases)
                  tangs     (cons tg tangs)
                  idxs      (cons i idxs))
            (command "._POINT" np)
            (setq guideEnts (cons (entlast) guideEnts)
                  tmpEnts   (cons (entlast) tmpEnts))
            (setq i (1+ i)))))))
    (setq newPts    (reverse newPts)
          usedBases (reverse usedBases)
          tangs     (reverse tangs))

    ;; --- connect the new points with a polyline ----------------------
    ;; drawn with the source curve's layer and line properties.  If
    ;; skipped points left fewer than 2, there is nothing to join and
    ;; nothing for the next round to follow.
    (if (< (length newPts) 2)
      (progn
        (princ "\nToo few points were placed to build a polyline.")
        (cperp:finish)
        (exit)))
    (setvar "CLAYER"    srcLayer)
    (setvar "CECOLOR"   srcColor)
    (setvar "CELTYPE"   srcLtype)
    (setvar "CELWEIGHT" srcLw)
    (setvar "CELTSCALE" srcLts)
    (command "._PLINE")
    (foreach p newPts (command p))
    (command "")
    ;; Curve it: every straight segment becomes an arc whose direction
    ;; at its start point matches the source curve's tangent there (an
    ;; offset curve runs parallel to its source, so the tangent carries
    ;; over).  The entity stays a plain LWPOLYLINE -- smooth, passing
    ;; exactly through every offset point, and never a spline.
    (cperp:arcs (entlast) newPts tangs)

    ;; the curve just built becomes the source for the next round; it
    ;; was drawn in travel order, so it is never traversed reversed
    (setq curCrv (entlast)
          curRev nil)

    ;; --- erase this round's point guides -----------------------------
    (foreach e guideEnts (cperp:kill e))
    (setq guideEnts nil)

    ;; --- remember the dimensions to draw -----------------------------
    ;; each pair runs along the normal of the curve the base point sits
    ;; on, so the dimension reads perpendicular to that curve
    (setq i 0)
    (while (< i (length newPts))
      (setq dimPairs (cons (list (nth i usedBases) (nth i newPts)) dimPairs)
            i        (1+ i)))
    (setq total (+ total (length newPts)))

    ;; --- repeat? -----------------------------------------------------
    (initget "Yes No")
    (setq again (getkword "\nRepeat on the new polyline? [Yes/No] <No>: "))
    (if (null again) (setq again "No")))

  ;; --- 6. dimension style, then draw every dimension ------------------
  (initget "STandard SIde")
  (setq ans (getkword (strcat "\nDimension style - STANDARD INCHES or "
                              "SIDE STANDARD? [STandard/SIde] <STandard>: ")))
  (setq dimStyle (if (equal ans "SIde") "SIDE STANDARD" "STANDARD INCHES"))
  (if (tblsearch "DIMSTYLE" dimStyle)
    (command "._-DIMSTYLE" "_Restore" dimStyle)
    (princ (strcat "\nDimension style \"" dimStyle
                   "\" is not in this drawing - using the current style \""
                   cdim "\" instead.")))

  (setvar "CLAYER" "DIMENSIONS")
  (foreach pr (reverse dimPairs)
    (command "._DIMALIGNED" (car pr) (cadr pr) (cadr pr)))

  ;; --- restore everything and close the undo group --------------------
  (cperp:finish)
  (princ (strcat "\nDone: " (itoa iter) " round(s), "
                 (itoa total) " points, "
                 (itoa iter) " polyline(s) on layer \"" srcLayer "\" and "
                 (itoa total) " dimensions on layer \"DIMENSIONS\"."))
  (princ))

(princ (strcat "\ncperp_points.lsp " *cperp-version*
               " loaded.  Type CPERPPTS to run."))
(princ)


;;; ======================================================================
;;; >>> tutorial_perp_points.lsp
;;; ======================================================================

;;; tutorial_perp_points.lsp  --  AutoCAD 2018 (AutoLISP)
;;;
;;; Command: TUTORIALPERPPTS
;;;
;;; SHARED BUILD: requires CALOFIN-LIB.lsp (load via CALOFIN-LOADER.lsp).
;;; Generic helpers live there under cal: - see STANDARDS.md.
;;;
;;; Interactive tutorial for the PERPPTS command (perp_points.lsp),
;;; aimed at first-time users.  Offers three modes:
;;;
;;;   Checks - lists everything PERPPTS validates and guards against,
;;;            for readers who want the rules up front
;;;   Demo   - draws a worked example one stage at a time, narrating
;;;            what PERPPTS does and what the drawing looks like at
;;;            each step
;;;   Both   - the checklist first, then the demo
;;;
;;; The demo asks for an insertion point and a size, then builds the
;;; sample: the selected line, the direction click and its red arrow,
;;; the division points, the offset points, the connecting polyline,
;;; the dimensions, and a repeat round on the new polyline.  At the end
;;; the demo drawing can be kept for reference or erased.  The whole
;;; tutorial is one UNDO group either way.
;;;
;;; License: GPL-3.0-or-later
;;; ---------------------------------------------------------------------

;; arc-length helpers (they match perp_points.lsp)
;; Version banner: tools/release_lisp.py reads it to stamp the dated
;; REV twin in releases/ (vN.M -> _MMDDYY_REVNM).
(setq *tutperp-version* "v0.4")

(defun tutp:lerp (a b tt)
  (list (+ (car a)   (* tt (- (car b)   (car a))))
        (+ (cadr a)  (* tt (- (cadr b)  (cadr a))))
        (+ (caddr a) (* tt (- (caddr b) (caddr a))))))

(defun tutp:pathlen (pts / total i)
  (setq total 0.0 i 0)
  (while (< (1+ i) (length pts))
    (setq total (+ total (distance (nth i pts) (nth (1+ i) pts)))
          i     (1+ i)))
  total)

(defun tutp:pt-at (pts d / i a b segd res)
  (cond
    ((<= d 0.0) (car pts))
    (t
     (setq i 0 res nil)
     (while (and (null res) (< (1+ i) (length pts)))
       (setq a    (nth i pts)
             b    (nth (1+ i) pts)
             segd (distance a b))
       (if (<= d segd)
         (setq res (tutp:lerp a b (if (> segd 1e-12) (/ d segd) 0.0)))
         (setq d (- d segd) i (1+ i))))
     (if res res (last pts)))))

(defun tutp:sample (pts n / total i out)
  (setq total (tutp:pathlen pts) out '() i 0)
  (while (< i n)
    (setq out (cons (tutp:pt-at pts
                                (if (> n 1)
                                  (* (/ (float i) (float (1- n))) total)
                                  0.0))
                    out)
          i   (1+ i)))
  (reverse out))

(defun c:TUTORIALPERPPTS (/ *error* tutp:say tutp:pause tutp:track
                            tutp:finish
                            os ce pd undoOpen ents mode ans p sz z
                            n i tt bx q d lens len base np
                            basePts newPts bases2 new2 e s)

  (defun tutp:say (lines)
    (foreach s lines (princ (strcat "\n" s)))
    (princ))

  (defun tutp:pause ()
    (getstring "\n      --- press Enter to continue --- ")
    (princ))

  ;; remember the entity just created so the demo can be erased
  (defun tutp:track ()
    (setq ents (cons (entlast) ents)))

  (defun tutp:finish ()
    (if pd (setvar "PDMODE"  pd))
    (if os (setvar "OSMODE"  os))
    (if ce (setvar "CMDECHO" ce))
    (if undoOpen
      (progn (command "._UNDO" "_End") (setq undoOpen nil))))

  (defun *error* (msg)
    (tutp:finish)
    (if (and msg (not (wcmatch (strcase msg) "*BREAK*,*CANCEL*,*QUIT*,*EXIT*")))
      (princ (strcat "\nError: " msg)))
    (princ))

  (setq os (getvar "OSMODE")
        ce (getvar "CMDECHO")
        pd (getvar "PDMODE")
        ents '())
  (setvar "CMDECHO" 0)
  (command "._UNDO" "_Begin")
  (setq undoOpen T)

  (tutp:say '("======================================================="
              " TUTORIALPERPPTS - a guided tour of the PERPPTS command"
              "======================================================="
              "PERPPTS divides a line into equally spaced points, offsets"
              "each point perpendicular to the line by a length you type,"
              "joins the offset points with a polyline, and dimensions"
              "every offset.  It can then repeat on the polyline it just"
              "built, as many times as you like."))
  (initget "Checks Demo Both")
  (setq mode (getkword "\nWhat would you like? [Checks/Demo/Both] <Both>: "))
  (if (null mode) (setq mode "Both"))

  ;; --- the checklist ---------------------------------------------------
  (if (member mode '("Checks" "Both"))
    (progn
      (tutp:say '(""
                  "----- What PERPPTS checks and guarantees -----"
                  ""
                  "Selection"
                  "  * only a LINE or an open polyline is accepted; anything"
                  "    else re-prompts instead of cancelling the command"
                  "  * zero-length and closed objects are rejected"
                  ""
                  "Overall width"
                  "  * right after the selection you are asked whether the"
                  "    overall width has changed: Grew, Shrank, New, or"
                  "    Unchanged (the default, and Enter)"
                  "  * the width meant is the distance straight ACROSS, end"
                  "    to end - never the length of the OBJECT, which on"
                  "    anything bowed runs further than the width it spans"
                  "  * half of any difference is added to, or taken off,"
                  "    EACH end: the OBJECT in the drawing is resized to"
                  "    match, so the base points and their dimensions still"
                  "    land on it.  One U puts the width back"
                  "  * shrinking away the whole width is rejected, and a"
                  "    resize the drawing will not take - a locked, frozen"
                  "    or switched-off layer - stops the command rather"
                  "    than measuring off geometry that is not there"
                  ""
                  "Direction click"
                  "  * the end nearest your click becomes START - lengths are"
                  "    then entered in order START -> FINISH (a red arrow"
                  "    marks START for the whole run)"
                  "  * the side of the line you click is the side every round"
                  "    offsets toward"
                  "  * a click landing on the line itself is rejected (the"
                  "    side would be ambiguous); object snap is off for this"
                  "    click so it cannot be pulled onto the line"
                  ""
                  "Counts and lengths"
                  "  * the point count must be a whole number of at least 2;"
                  "    Enter reuses the previous round's count"
                  "  * a count over 100 asks for confirmation first"
                  "  * lengths must be positive - zero and negative values"
                  "    are rejected"
                  "  * Enter repeats the previous length (handy for runs of"
                  "    equal values); typing B (Back) steps back one point"
                  ""
                  "Joining the points"
                  "  * Straight, Arcs or Mixed, asked once a round has three"
                  "    points or more; the default is the previous round's"
                  "    answer, and Straight to begin with"
                  "  * Mixed then asks which segment numbers are arcs, as"
                  "    single numbers or ranges - 1 3-5 - and leaves the"
                  "    rest straight; a list it cannot read re-asks, and B"
                  "    goes back to the question"
                  "  * an arc is a bulge on the same polyline, running"
                  "    through the measured points - never a spline, and"
                  "    never a curve-fit heavy polyline"
                  ""
                  "Output"
                  "  * the offset polyline takes the layer, colour, linetype,"
                  "    lineweight and linetype scale of the source line"
                  "  * dimensions are drawn at the very end, all at once, on"
                  "    the DIMENSIONS layer (created if missing)"
                  "  * you pick STANDARD INCHES or SIDE STANDARD; if the"
                  "    drawing lacks that style the current style is used"
                  "    and a note is printed"
                  ""
                  "Safety net"
                  "  * the whole run is one UNDO group - a single U reverses"
                  "    everything, however many rounds were done"
                  "  * Esc at any prompt cleans up: temporary guides erased;"
                  "    OSMODE, CMDECHO, PDMODE, CLAYER, the colour/linetype/"
                  "    lineweight defaults and the dimension style restored"
                  "  * works correctly in a rotated or shifted UCS"))
      (if (equal mode "Both") (tutp:pause))))

  ;; --- the drawn demo --------------------------------------------------
  (if (member mode '("Demo" "Both"))
    (progn
      (tutp:say '(""
                  "----- Worked example -----"
                  "The demo now draws what PERPPTS produces, one stage at a"
                  "time.  Pick an empty spot with room to the upper right."))
      (setq p (getpoint "\nInsertion point for the demo: "))
      (while (null p)
        (setq p (getpoint "\nA point is required - insertion point: ")))
      (setq sz (getdist p "\nDemo size <100>: "))
      (if (null sz) (setq sz 100.0))
      (setvar "OSMODE" 0)
      (if (member pd '(0 1)) (setvar "PDMODE" 3))
      (setq z (caddr p))

      ;; stage 1: the selected line
      (entmake (list '(0 . "LINE")
                     (cons 10 (trans p 1 0))
                     (cons 11 (trans (list (+ (car p) sz) (cadr p) z) 1 0))))
      (tutp:track)
      (tutp:say '(""
                  "STAGE 1 - the line."
                  "You start PERPPTS and select this line.  Wrong picks just"
                  "re-prompt, so a missed click costs nothing."))
      (tutp:pause)

      ;; stage 2: the direction click, marked with a red X, and the
      ;; red arrow at the START end
      (setq q (list (+ (car p) (* 0.20 sz)) (+ (cadr p) (* 0.30 sz)) z)
            d (* 0.03 sz))
      (foreach s (list (list (list (- (car q) d) (- (cadr q) d) z)
                             (list (+ (car q) d) (+ (cadr q) d) z))
                       (list (list (- (car q) d) (+ (cadr q) d) z)
                             (list (+ (car q) d) (- (cadr q) d) z)))
        (entmake (list '(0 . "LINE") '(62 . 1)
                       (cons 10 (trans (car s)  1 0))
                       (cons 11 (trans (cadr s) 1 0))))
        (tutp:track))
      ;; arrow: shaft into START from outside, plus two barbs
      (foreach s (list (list (list (- (car p) (* 0.15 sz)) (cadr p) z) p)
                       (list p (list (- (car p) (* 0.048 sz))
                                     (- (cadr p) (* 0.022 sz)) z))
                       (list p (list (- (car p) (* 0.048 sz))
                                     (+ (cadr p) (* 0.022 sz)) z)))
        (entmake (list '(0 . "LINE") '(62 . 1)
                       (cons 10 (trans (car s)  1 0))
                       (cons 11 (trans (cadr s) 1 0))))
        (tutp:track))
      (tutp:say '(""
                  "STAGE 2 - the direction click."
                  "You click once beside the line (the red X).  Two things"
                  "are decided by that single click:"
                  "  * the line end nearest the click becomes START - the red"
                  "    arrow marks it - and lengths are entered START to"
                  "    FINISH;"
                  "  * the side you clicked (here: above) is the side all"
                  "    offsets go, in every round."
                  "A click exactly on the line is rejected as ambiguous."))
      (tutp:pause)

      ;; stage 3: the division points
      (setq n 5 basePts '() i 0)
      (while (< i n)
        (setq tt (/ (float i) (float (1- n)))
              bx (+ (car p) (* tt sz)))
        (setq basePts (cons (list bx (cadr p) z) basePts))
        (command "._POINT" (list bx (cadr p) z))
        (tutp:track)
        (setq i (1+ i)))
      (setq basePts (reverse basePts))
      (tutp:say '(""
                  "STAGE 3 - the division points."
                  "You enter how many values are required - here 5.  The"
                  "line is divided into that many equally spaced points,"
                  "both ends included.  (At least 2; over 100 asks first.)"))
      (tutp:pause)

      ;; stage 4: the offset points
      (setq lens (list (* 0.20 sz) (* 0.30 sz) (* 0.45 sz)
                       (* 0.35 sz) (* 0.25 sz))
            newPts '() i 0)
      (foreach base basePts
        (setq len (nth i lens)
              np  (list (car base) (+ (cadr base) len) z))
        (setq newPts (cons np newPts))
        (command "._POINT" np)
        (tutp:track)
        (setq i (1+ i)))
      (setq newPts (reverse newPts))
      (tutp:say '(""
                  "STAGE 4 - the offset points."
                  "You type a length for each point, START to FINISH - here"
                  "20, 30, 45, 35 and 25 (per 100 of demo size).  Each point"
                  "moves perpendicular to the line by its length, toward the"
                  "clicked side.  Enter repeats the previous length; Back"
                  "steps back one point; zero and negatives are refused."))
      (tutp:pause)

      ;; stage 5: the connecting polyline
      (command "._PLINE")
      (foreach np newPts (command np))
      (command "")
      (tutp:track)
      (tutp:say '(""
                  "STAGE 5 - the polyline."
                  "The offset points are joined with a polyline.  In the"
                  "real command it takes the layer, colour, linetype,"
                  "lineweight and linetype scale of the line you selected,"
                  "so it reads as the same kind of object."))
      (tutp:pause)

      ;; stage 6: the dimensions
      (setq i 0)
      (while (< i n)
        (command "._DIMALIGNED" (nth i basePts) (nth i newPts) (nth i newPts))
        (tutp:track)
        (setq i (1+ i)))
      (tutp:say '(""
                  "STAGE 6 - the dimensions."
                  "One aligned dimension per point, from the line to its"
                  "offset point.  In the real command these are drawn at the"
                  "very end, all at once, on the DIMENSIONS layer, in the"
                  "style you pick: STANDARD INCHES or SIDE STANDARD."))
      (tutp:pause)

      ;; stage 7: a repeat round on the new polyline
      (setq bases2 (tutp:sample newPts n)
            new2   '())
      (foreach base bases2
        (setq np (list (car base) (+ (cadr base) (* 0.15 sz)) z))
        (setq new2 (cons np new2))
        (command "._POINT" np)
        (tutp:track))
      (setq new2 (reverse new2))
      (command "._PLINE")
      (foreach np new2 (command np))
      (command "")
      (tutp:track)
      (setq i 0)
      (while (< i n)
        (command "._DIMALIGNED" (nth i bases2) (nth i new2) (nth i new2))
        (tutp:track)
        (setq i (1+ i)))
      (tutp:say '(""
                  "STAGE 7 - repeating."
                  "After each polyline PERPPTS asks: Repeat on the new"
                  "polyline?  Answering Yes spaces a fresh set of points by"
                  "arc length ALONG that polyline and offsets them again -"
                  "same side, dimensions still perpendicular to the original"
                  "line.  Here a second round of 15s was added.  Repeat as"
                  "many times as you like; a single U undoes the whole run."))
      (tutp:pause)

      ;; keep or erase the demo
      (initget "Keep Erase")
      (setq ans (getkword "\nKeep the demo drawing? [Keep/Erase] <Keep>: "))
      (if (equal ans "Erase")
        (progn
          (foreach e ents (if (and e (entget e)) (entdel e)))
          (setq ents nil)))))

  (tutp:finish)
  (tutp:say '(""
              "Tutorial finished.  Type PERPPTS to try it for real."))
  (princ))

(princ (strcat "\ntutorial_perp_points.lsp " *tutperp-version*
               " loaded.  Type TUTORIALPERPPTS to run."))
(princ)


;;; ======================================================================
;;; >>> tutorial_cperp_points.lsp
;;; ======================================================================

;;; tutorial_cperp_points.lsp  --  AutoCAD 2018 (AutoLISP)
;;;
;;; Command: TUTORIALCPERPPTS
;;;
;;; SHARED BUILD: requires CALOFIN-LIB.lsp (load via CALOFIN-LOADER.lsp).
;;; Generic helpers live there under cal: - see STANDARDS.md.
;;;
;;; Interactive tutorial for the CPERPPTS command (cperp_points.lsp),
;;; the curved companion to PERPPTS.  Offers three modes:
;;;
;;;   Checks - lists everything CPERPPTS validates and guards against
;;;   Demo   - draws a worked example on a curved polyline, one stage
;;;            at a time, narrating what happens at each step
;;;   Both   - the checklist first, then the demo
;;;
;;; The demo asks for an insertion point and a size, draws a sample
;;; arched polyline, then walks through the direction click, the
;;; arc-length division points, the tangent-perpendicular offsets, the
;;; smooth arc-polyline result, the dimensions, and a repeat round from
;;; the newest curve.  At the end the demo drawing can be kept or
;;; erased.  The whole tutorial is one UNDO group either way.
;;;
;;; License: GPL-3.0-or-later
;;; ---------------------------------------------------------------------

(vl-load-com)

;; Version banner: tools/release_lisp.py reads it to stamp the dated
;; REV twin in releases/ (vN.M -> _MMDDYY_REVNM).
(setq *tutcperp-version* "v0.4")

;; curve helpers (they match cperp_points.lsp)

;; unit tangent of the curve (current UCS) at the point closest to pt;
;; rev flips it to follow the direction of travel
(defun tutc:tangent (crv pt rev / w cp prm dv dx dy dl)
  (setq w  (trans pt 1 0)
        cp (vlax-curve-getClosestPointTo crv w))
  (if (null cp)
    nil
    (progn
      (setq prm (vlax-curve-getParamAtPoint crv cp))
      (if (null prm)
        (setq prm (vlax-curve-getParamAtDist
                    crv (vlax-curve-getDistAtPoint crv cp))))
      (if (null prm)
        nil
        (progn
          (setq dv (trans (vlax-curve-getFirstDeriv crv prm) 0 1 T)
                dx (car dv)
                dy (cadr dv)
                dl (sqrt (+ (* dx dx) (* dy dy))))
          (if (< dl 1e-12)
            nil
            (progn
              (if rev (setq dx (- dx) dy (- dy)))
              (list (/ dx dl) (/ dy dl)))))))))

;; bulge of the arc a->b whose start tangent is tg (tan of half the
;; tangent-to-chord angle); straight fallback on degenerate input
(defun tutc:bulge (tg a b / cx cy dot crs alpha lim)
  (setq cx (- (car b) (car a))
        cy (- (cadr b) (cadr a)))
  (if (or (null tg)
          (< (sqrt (+ (* cx cx) (* cy cy))) 1e-12))
    0.0
    (progn
      (setq dot   (+ (* (car tg) cx) (* (cadr tg) cy))
            crs   (- (* (car tg) cy) (* (cadr tg) cx))
            alpha (atan crs dot)
            lim   2.98)
      (if (> alpha lim)     (setq alpha lim))
      (if (< alpha (- lim)) (setq alpha (- lim)))
      (/ (sin (/ alpha 2.0)) (cos (/ alpha 2.0))))))

;; write arc bulges into the LWPOLYLINE en (drawn through pts with
;; travel tangents tangs); the entity stays an LWPOLYLINE
(defun tutc:arcs (en pts tangs / d out g i b)
  (setq d (entget en) out '() i 0)
  (foreach g d
    (cond
      ((= 42 (car g)))
      ((= 10 (car g))
       (setq b (if (< (1+ i) (length pts))
                 (tutc:bulge (nth i tangs) (nth i pts) (nth (1+ i) pts))
                 0.0))
       (setq out (cons (cons 42 b) (cons g out))
             i   (1+ i)))
      (t (setq out (cons g out)))))
  (entmod (reverse out)))

(defun c:TUTORIALCPERPPTS (/ *error* tutc:say tutc:pause tutc:track
                             tutc:finish tutc:round
                             os ce pd plt undoOpen ents mode ans p sz z
                             w1 w2 w3 crv tot n i dd q d tg nrm
                             lens base np basePts newPts tangs e s)

  (defun tutc:say (lines)
    (foreach s lines (princ (strcat "\n" s)))
    (princ))

  (defun tutc:pause ()
    (getstring "\n      --- press Enter to continue --- ")
    (princ))

  (defun tutc:track ()
    (setq ents (cons (entlast) ents)))

  (defun tutc:finish ()
    (if pd  (setvar "PDMODE"    pd))
    (if os  (setvar "OSMODE"    os))
    (if plt (setvar "PLINETYPE" plt))
    (if ce  (setvar "CMDECHO"   ce))
    (if undoOpen
      (progn (command "._UNDO" "_End") (setq undoOpen nil))))

  (defun *error* (msg)
    (tutc:finish)
    (if (and msg (not (wcmatch (strcase msg) "*BREAK*,*CANCEL*,*QUIT*,*EXIT*")))
      (princ (strcat "\nError: " msg)))
    (princ))

  ;; one demo round: sample n points along crv by arc length, offset
  ;; each along the left travel normal by (nth i lens), draw guides,
  ;; the arc polyline and the dimensions; returns the new curve entity
  (defun tutc:round (crv lens / tot i dd base tg nrm np
                                basePts newPts tangs n)
    (setq n   (length lens)
          tot (vlax-curve-getDistAtParam crv (vlax-curve-getEndParam crv))
          basePts '() newPts '() tangs '() i 0)
    (while (< i n)
      (setq dd   (* (/ (float i) (float (1- n))) tot)
            base (trans (vlax-curve-getPointAtDist crv dd) 0 1)
            tg   (tutc:tangent crv base nil))
      (if (null tg) (setq tg (list 1.0 0.0)))     ; demo-safe fallback
      (setq nrm  (list (- (cadr tg)) (car tg))    ; left of travel
            np   (list (+ (car base)  (* (nth i lens) (car nrm)))
                       (+ (cadr base) (* (nth i lens) (cadr nrm)))
                       (caddr base)))
      (setq basePts (cons base basePts)
            newPts  (cons np newPts)
            tangs   (cons tg tangs))
      (command "._POINT" np)
      (tutc:track)
      (setq i (1+ i)))
    (setq basePts (reverse basePts)
          newPts  (reverse newPts)
          tangs   (reverse tangs))
    (command "._PLINE")
    (foreach np newPts (command np))
    (command "")
    (tutc:arcs (entlast) newPts tangs)
    (tutc:track)
    (setq i 0)
    (while (< i n)
      (command "._DIMALIGNED" (nth i basePts) (nth i newPts) (nth i newPts))
      (tutc:track)
      (setq i (1+ i)))
    (entlast))

  (setq os  (getvar "OSMODE")
        ce  (getvar "CMDECHO")
        pd  (getvar "PDMODE")
        plt (getvar "PLINETYPE")
        ents '())
  (setvar "CMDECHO" 0)
  (command "._UNDO" "_Begin")
  (setq undoOpen T)

  (tutc:say '("========================================================="
              " TUTORIALCPERPPTS - a guided tour of the CPERPPTS command"
              "========================================================="
              "CPERPPTS is PERPPTS for curves.  It divides an open curve"
              "into points spaced by true arc length, offsets each point"
              "PERPENDICULAR TO THE TANGENT of the curve underneath it by"
              "a length you type, joins the offsets into a smooth arc"
              "polyline, and dimensions every offset.  It can then repeat"
              "from the curve it just built."))
  (initget "Checks Demo Both")
  (setq mode (getkword "\nWhat would you like? [Checks/Demo/Both] <Both>: "))
  (if (null mode) (setq mode "Both"))

  ;; --- the checklist ---------------------------------------------------
  (if (member mode '("Checks" "Both"))
    (progn
      (tutc:say '(""
                  "----- What CPERPPTS checks and guarantees -----"
                  ""
                  "Selection"
                  "  * accepts any OPEN curve AutoCAD can measure along:"
                  "    polylines (with arc segments), arcs, splines,"
                  "    ellipse arcs and plain lines; anything else"
                  "    re-prompts"
                  "  * zero-length and closed curves are rejected"
                  ""
                  "Overall width"
                  "  * right after the selection you are asked whether the"
                  "    overall width has changed: Grew, Shrank, New, or"
                  "    Unchanged (the default, and Enter)"
                  "  * the width meant is the distance straight ACROSS, end"
                  "    to end - never the length of the CURVE, which on"
                  "    anything bowed runs further than the width it spans"
                  "  * half of any difference is added to, or taken off,"
                  "    EACH end: the CURVE in the drawing is resized to"
                  "    match, so the base points and their dimensions still"
                  "    land on it.  One U puts the width back"
                  "  * shrinking away the whole width is rejected, and a"
                  "    resize the drawing will not take - a locked, frozen"
                  "    or switched-off layer - stops the command rather"
                  "    than measuring off geometry that is not there"
                  ""
                  "Direction click"
                  "  * the curve end nearest your click becomes START; a red"
                  "    arrow marks it for the whole run"
                  "  * the side you click - relative to the direction of"
                  "    travel - is the side every round offsets toward,"
                  "    however the curve bends"
                  "  * a click landing on the curve is rejected as ambiguous"
                  ""
                  "Counts and lengths"
                  "  * point count: whole number, at least 2; Enter reuses"
                  "    the previous round's count; over 100 asks first"
                  "  * lengths must be positive; Enter repeats the previous"
                  "    length; B (Back) steps back one point"
                  "  * a point where the curve direction cannot be read"
                  "    (a cusp) is skipped with a message, never offset in"
                  "    an arbitrary direction"
                  ""
                  "Geometry"
                  "  * points are spaced by TRUE ARC LENGTH, so they never"
                  "    bunch up in tight curvature"
                  "  * each offset runs perpendicular to the curve tangent"
                  "    under its point, so offsets follow the bend"
                  "  * every round works from the NEWEST curve - round 2"
                  "    offsets from the curve round 1 built, and so on"
                  ""
                  "Output"
                  "  * the result is a plain LIGHTWEIGHT POLYLINE whose"
                  "    segments are arcs (bulges) - never a spline, and"
                  "    never a curve-fit heavy polyline; it passes exactly"
                  "    through every offset point"
                  "  * the polyline takes the layer, colour, linetype,"
                  "    lineweight and linetype scale of the source curve"
                  "  * dimensions are drawn at the end, all at once, on the"
                  "    DIMENSIONS layer, in STANDARD INCHES or SIDE"
                  "    STANDARD (current style if the drawing lacks it)"
                  ""
                  "Safety net"
                  "  * one UNDO group - a single U reverses everything"
                  "  * Esc at any prompt cleans up: guides erased and every"
                  "    changed system variable restored"
                  "  * works correctly in a rotated or shifted UCS"
                  ""
                  "Worth knowing: on a tight concave bend, normals converge,"
                  "so a large offset there can make the new curve cross"
                  "itself - inherent to offsetting along normals."))
      (if (equal mode "Both") (tutc:pause))))

  ;; --- the drawn demo --------------------------------------------------
  (if (member mode '("Demo" "Both"))
    (progn
      (tutc:say '(""
                  "----- Worked example -----"
                  "The demo draws what CPERPPTS produces on a curved"
                  "polyline, one stage at a time.  Pick an empty spot with"
                  "room above."))
      (setq p (getpoint "\nInsertion point for the demo: "))
      (while (null p)
        (setq p (getpoint "\nA point is required - insertion point: ")))
      (setq sz (getdist p "\nDemo size <100>: "))
      (if (null sz) (setq sz 100.0))
      (setvar "OSMODE" 0)
      (setvar "PLINETYPE" 2)
      (if (member pd '(0 1)) (setvar "PDMODE" 3))
      (setq z (caddr p))

      ;; stage 1: the source curve - an arched polyline with arc
      ;; segments (negative bulges = clockwise when traveling left to
      ;; right over the top)
      (setq w1 (trans p 1 0)
            w2 (trans (list (+ (car p) (* 0.5 sz))
                            (+ (cadr p) (* 0.30 sz)) z) 1 0)
            w3 (trans (list (+ (car p) sz) (cadr p) z) 1 0))
      (entmake (list '(0 . "LWPOLYLINE")
                     '(100 . "AcDbEntity")
                     '(100 . "AcDbPolyline")
                     '(90 . 3) '(70 . 0)
                     (cons 38 (caddr w1))
                     (cons 10 (list (car w1) (cadr w1))) '(42 . -0.25)
                     (cons 10 (list (car w2) (cadr w2))) '(42 . -0.25)
                     (cons 10 (list (car w3) (cadr w3))) '(42 . 0.0)))
      (setq crv (entlast))
      (tutc:track)
      (tutc:say '(""
                  "STAGE 1 - the curve."
                  "You start CPERPPTS and select this arched polyline.  Any"
                  "OPEN curve works: polylines with arcs, plain arcs,"
                  "splines, ellipse arcs, even straight lines."))
      (tutc:pause)

      ;; stage 2: the direction click (red X above the left end) and
      ;; the red arrow at START, drawn back along the start tangent
      (setq q (list (+ (car p) (* 0.10 sz)) (+ (cadr p) (* 0.35 sz)) z)
            d (* 0.03 sz))
      (foreach s (list (list (list (- (car q) d) (- (cadr q) d) z)
                             (list (+ (car q) d) (+ (cadr q) d) z))
                       (list (list (- (car q) d) (+ (cadr q) d) z)
                             (list (+ (car q) d) (- (cadr q) d) z)))
        (entmake (list '(0 . "LINE") '(62 . 1)
                       (cons 10 (trans (car s)  1 0))
                       (cons 11 (trans (cadr s) 1 0))))
        (tutc:track))
      (setq tg (tutc:tangent crv p nil))
      (entmake (list '(0 . "LINE") '(62 . 1)
                     (cons 10 (trans (list (- (car p)  (* 0.15 sz (car tg)))
                                           (- (cadr p) (* 0.15 sz (cadr tg)))
                                           z) 1 0))
                     (cons 11 (trans p 1 0))))
      (tutc:track)
      (tutc:say '(""
                  "STAGE 2 - the direction click."
                  "You click once beside the curve (the red X).  The end"
                  "nearest the click becomes START (the red arrow), and the"
                  "side you clicked - relative to the direction of travel -"
                  "is the side every round offsets toward, all the way"
                  "around the bend."))
      (tutc:pause)

      ;; stage 3 + 4 + 5 + 6: division points, offsets, arc polyline,
      ;; dimensions - drawn by the shared round routine
      (setq lens (list (* 0.22 sz) (* 0.30 sz) (* 0.26 sz)
                       (* 0.34 sz) (* 0.24 sz)))
      (tutc:say '(""
                  "STAGES 3 to 6 - one full round, drawn now:"
                  "  * 5 division points spaced by TRUE ARC LENGTH along the"
                  "    curve (they never bunch up in tight curvature);"
                  "  * each offset by its own typed length, PERPENDICULAR TO"
                  "    THE TANGENT underneath it - watch the directions fan"
                  "    with the bend;"
                  "  * the offsets joined into a smooth ARC POLYLINE - a"
                  "    plain lightweight polyline with arc segments, never a"
                  "    spline - passing exactly through every point;"
                  "  * one aligned dimension per point (in the real command"
                  "    these land on the DIMENSIONS layer at the end, in the"
                  "    style you pick)."))
      (setq crv (tutc:round crv lens))
      (tutc:pause)

      ;; stage 7: a repeat round from the newest curve
      (setq lens (list (* 0.12 sz) (* 0.12 sz) (* 0.12 sz)
                       (* 0.12 sz) (* 0.12 sz)))
      (setq crv (tutc:round crv lens))
      (tutc:say '(""
                  "STAGE 7 - repeating."
                  "Answering Yes to the repeat prompt runs the next round"
                  "FROM THE NEWEST CURVE: fresh arc-length points along the"
                  "curve just built, offset perpendicular to ITS tangents -"
                  "here a uniform round of 12s.  Each round follows the"
                  "shape its predecessor took.  Repeat as often as needed;"
                  "one U undoes the whole run."))
      (tutc:pause)

      ;; keep or erase the demo
      (initget "Keep Erase")
      (setq ans (getkword "\nKeep the demo drawing? [Keep/Erase] <Keep>: "))
      (if (equal ans "Erase")
        (progn
          (foreach e ents (if (and e (entget e)) (entdel e)))
          (setq ents nil)))))

  (tutc:finish)
  (tutc:say '(""
              "Tutorial finished.  Type CPERPPTS to try it for real."))
  (princ))

(princ (strcat "\ntutorial_cperp_points.lsp " *tutcperp-version*
               " loaded.  Type TUTORIALCPERPPTS to run."))
(princ)


;;; ======================================================================
;;; >>> SMARTFILLET.lsp
;;; ======================================================================

;;; ======================================================================
;;; SMARTFILLET.lsp  --  show what every rounded corner would look like,
;;;                      then cut the one that is clicked
;;; ----------------------------------------------------------------------
;;; For AutoCAD 2018 and later (plain AutoLISP, no external libraries).
;;;
;;; Commands:  SMARTFILLET     preview the radii that fit a corner, cut
;;;                            the one that is clicked, dimension it, and
;;;                            offer the rest of the corners at that size
;;;            SMARTFILLETVER  print the loaded version
;;;
;;; SHARED BUILD: requires CALOFIN-LIB.lsp (load via CALOFIN-LOADER.lsp).
;;; Generic helpers live there under cal: - see STANDARDS.md.
;;;
;;;  FILLET wants the radius BEFORE it shows anything, so the answer is
;;;  guessed, looked at, undone, and guessed again.  This turns that
;;;  round.  Pick the two lines and every radius that actually fits the
;;;  corner is drawn dashed, all at once, in 6-inch steps; click the one
;;;  that looks right and that is the corner you get.
;;;
;;;    1. Select the two lines that make the corner.  Click each one on
;;;       the side you want KEPT -- exactly how FILLET reads a pick:
;;;       what lies beyond the corner is trimmed away.
;;;    2. Every radius from 6 up, in 6s, that leaves both legs something
;;;       to stand on is drawn as a dashed arc labelled R6, R12, R18 ...
;;;       (at most sf:*maxshown* of them; when more fit, the routine
;;;       says how many it left out rather than silently stopping).
;;;    3. Click the arc you want.  The previews go, the corner is
;;;       filleted for real at that radius, and the arc gets its radius
;;;       dimension -- the number the shop needs, not just the shape.
;;;    4. It then offers the SAME radius for the rest of the corners:
;;;       two lines per corner until Done.  As soon as one repeat is
;;;       cut, the single dimension becomes "R12 Typ.", which is how the
;;;       radius would be lettered by hand.
;;;
;;;  The whole run is one undo group: a single U puts every corner back
;;;  and takes the dimension away.
;;;
;;;  Usage
;;;    Command: SMARTFILLET
;;;    Command: SMARTFILLETVER   prints the version
;;;
;;;  Tunables (setq them after loading if a drawing needs different
;;;  sizes or names, e.g. in a startup file):
;;;    sf:*first*      smallest radius previewed          (6.0)
;;;    sf:*step*       step between previews              (6.0)
;;;    sf:*maxshown*   most previews drawn at once        (8)
;;;    sf:*fit*        fraction of a leg a fillet may eat (0.98)
;;;    sf:*layer*      layer the previews are drawn on
;;;    sf:*color*      their colour
;;;    sf:*ltype*      their linetype, created if missing ("DASHED")
;;;    sf:*ltscale*    per-arc linetype scale, nil = the drawing's
;;;    sf:*label*      T to letter each preview R6, R12 ...
;;;    sf:*txthgt*     height of those labels
;;;    sf:*dimlayer*   layer the radius dimension goes on ("DIMENSION")
;;;    sf:*smalldim*   radii under this are dimensioned in ...
;;;    sf:*smallstyle* ... this dim style, when the drawing has it
;;;    sf:*dimoff*     how far past the arc the dimension text sits,
;;;                    nil = one radius, and never less than 12
;;;    sf:*dimrepeat*  T to dimension every repeat corner too
;;;    sf:*typ*        T to re-letter the one dimension "<> Typ." once
;;;                    a repeat has been cut at the same radius
;;;
;;;  Notes
;;;    * Two straight LINEs only.  A polyline corner is not filleted --
;;;      the routine says so and asks again; explode it first.
;;;    * Which side of each line survives comes from where it was
;;;      clicked, as in FILLET.  Click near the corner and both legs
;;;      keep the end you clicked toward.
;;;    * A radius only makes the list when its tangent point lands on
;;;      both legs (times sf:*fit*, so a fillet never eats a leg whole).
;;;      A corner too short for even R6 is reported, not filleted.
;;;    * The preview arcs are real entities on their own layer, erased
;;;      on the way out -- on a clean finish, on Esc, and on an error.
;;;      The empty layer is left behind; deleting it is a PURGE away.
;;;    * OSMODE, CMDECHO, CLAYER, FILLETRAD, TRIMMODE and the current
;;;      dimension style are all put back the way they were.
;;; ======================================================================

(setq *smartfillet-version* "v1.0")  ; announced on load; release_lisp.py
                                     ; reads this banner and stamps the
                                     ; dated twin in releases/ from it

;;; -------------------- tunables ------------------------------------

(setq sf:*first*      6.0)   ; the smallest radius offered, and the step
(setq sf:*step*       6.0)   ; between the ones after it -- 6" of radius
                             ; is the smallest difference that reads on
                             ; a pool plan
(setq sf:*maxshown*   8)     ; how many previews may be on screen at
                             ; once; nil = every radius that fits, which
                             ; on a long wall is a great many
(setq sf:*fit*        0.98)  ; how much of the shorter leg a fillet may
                             ; use up: 1.0 would put the tangent point
                             ; exactly on the far end and leave a
                             ; zero-length line behind
(setq sf:*layer*      "SMART FILLET PREVIEW")
(setq sf:*color*      3)     ; green, so a preview reads as a preview
                             ; whatever the layer was set to by hand
(setq sf:*ltype*      "DASHED")
(setq sf:*ltscale*    0.25)  ; the stock DASHED pattern is 18 units
                             ; long, so a 6" fillet arc (9 units of it)
                             ; would come out as one unbroken dash; a
                             ; quarter-scale pattern puts real gaps in
                             ; even the smallest preview.  nil = leave
                             ; the arcs at the drawing's own LTSCALE
(setq sf:*label*      t)
(setq sf:*txthgt*     6.0)
(setq sf:*dimlayer*   "DIMENSION")
(setq sf:*smalldim*   24.0)             ; POOL's small-dimension rule,
(setq sf:*smallstyle* "STANDARD INCHES"); kept so a fillet callout
                                        ; matches the dims beside it
(setq sf:*dimoff*     nil)   ; nil = one radius past the arc
(setq sf:*dimrepeat*  nil)   ; one callout plus "Typ." is how the sheet
                             ; reads; set T to dimension every corner
(setq sf:*typ*        t)
(setq sf:*minang*     0.02)  ; how far off straight (radians) two legs
                             ; must be before there is a corner at all

(setq sf:*preview*    nil)   ; every entity drawn as a preview
(setq sf:*picks*      nil)   ; (preview-arc . radius), what a click means
(setq sf:*smallwarned* nil)  ; the missing-style note is said once

;;; -------------------- shared helpers ------------------------------
;;; The generic CALOFIN-LIB helpers this tool leans on.  Here they are
;;; copies under this file's own prefix, so it loads alone with
;;; APPLOAD; in the shared/ twin they are gone and every call site
;;; reads cal: instead.  Bodies identical to the library's.

;;; -------------------- small local helpers -------------------------

;; A number without AutoLISP's trailing zeros: 12, not 12.000000.
(defun sf:num (x)
  (cond ((null x) "?")
        ((= x (fix x)) (rtos x 2 0))
        (t (rtos x 2 2))))

;; "R12", the way a radius is lettered
(defun sf:rlabel (r) (strcat "R" (sf:num r)))

;; Make sure the preview linetype exists, with dashes sized for a
;; drawing in inches so they read at pool scale (pf:ensure-dashed,
;; abhd.lsp:1566).  A drawing that already has one by that name keeps
;; its own.
(defun sf:ensure-ltype ()
  (if (and sf:*ltype* (not (tblsearch "LTYPE" sf:*ltype*)))
    (entmake (list '(0 . "LTYPE") '(100 . "AcDbSymbolTableRecord")
                   '(100 . "AcDbLinetypeTableRecord")
                   (cons 2 sf:*ltype*) '(70 . 0)
                   '(3 . "Dashed __ __ __ __ __")
                   '(72 . 65) '(73 . 2) '(40 . 18.0)
                   '(49 . 12.0) '(74 . 0)
                   '(49 . -6.0) '(74 . 0))))
  (if (tblsearch "LTYPE" sf:*ltype*) sf:*ltype* "CONTINUOUS"))

;; the two endpoints of a LINE, in WCS (the entity's own OCS may be
;; tilted, so go through the entity coordinate system)
(defun sf:ends (en / ed)
  (setq ed (entget en))
  (list (cal:2d (trans (cdr (assoc 10 ed)) en 0))
        (cal:2d (trans (cdr (assoc 11 ed)) en 0))))

;;; -------------------- the corner ----------------------------------

;; One leg of the corner: which way the line runs from the crossing
;; point X on the side that was CLICKED -- the side FILLET keeps -- and
;; how far it reaches that way.  Returns (unit-direction reach), or nil
;; when the line has no length.  The pick decides the direction and the
;; far endpoint decides the reach, so a line whose crossing point lies
;; off its own end (the case FILLET handles by extending it) is
;; measured the same way as one the corner sits inside.
(defun sf:leg (en x pk / ends a b d s u av)
  (setq ends (sf:ends en)
        a    (car  ends)
        b    (cadr ends)
        d    (cal:unit (cal:v- b a)))
  (if d
    (progn
      (setq s (cal:dot d (cal:v- pk x)))
      ;; clicked on the corner itself, where neither side is nearer:
      ;; take the end with more line behind it, the only one a fillet
      ;; could stand on
      (if (< (abs s) 1e-6)
        (setq s (if (>= (cal:dist a x) (cal:dist b x))
                  (cal:dot d (cal:v- a x))
                  (cal:dot d (cal:v- b x)))))
      (setq u  (if (< s 0.0) (cal:v* d -1.0) d)
            av (max (cal:dot u (cal:v- a x)) (cal:dot u (cal:v- b x))))
      (if (> av 1e-9) (list u av)))))

;; Everything about the corner two picked lines make, worked out once:
;;   (X u1 reach1 u2 reach2 half-angle)
;; X is where the two lines cross (extended if they have to be, as
;; FILLET extends them), each u runs from X along the side that was
;; clicked, and half-angle is half the turn between them -- the one
;; number the whole fillet is built from.  nil when there is no corner:
;; parallel lines, the same line twice, or two legs so nearly straight
;; through that no arc could join them.
(defun sf:corner (e1 pk1 e2 pk2 / a b x l1 l2 th)
  (setq a (sf:ends e1)
        b (sf:ends e2)
        x (inters (car a) (cadr a) (car b) (cadr b) nil))
  (if x
    (progn
      (setq x  (cal:2d x)
            l1 (sf:leg e1 x pk1)
            l2 (sf:leg e2 x pk2))
      (if (and l1 l2)
        (progn
          (setq th (abs (cal:signed-dang (angle '(0.0 0.0) (car l1))
                                        (angle '(0.0 0.0) (car l2)))))
          (if (and (> th sf:*minang*) (< th (- pi sf:*minang*)))
            (list x (car l1) (cadr l1) (car l2) (cadr l2) (/ th 2.0))))))))

;; how far back from the corner a fillet of radius R starts
(defun sf:tanlen (half r) (/ r (cal:tan half)))

;; The biggest radius this corner can take: the tangent point has to
;; land on both legs, and sf:*fit* keeps it clear of the far end so a
;; fillet never eats a leg whole.
(defun sf:rmax (geo)
  (* sf:*fit* (min (caddr geo) (nth 4 geo)) (cal:tan (nth 5 geo))))

;; centre and the two tangent points of the fillet arc of radius R
(defun sf:arcpts (geo r / x u1 u2 half tl)
  (setq x    (car geo)
        u1   (cadr geo)
        u2   (cadddr geo)
        half (nth 5 geo)
        tl   (sf:tanlen half r))
  (list (cal:v+ x (cal:v* (cal:unit (cal:v+ u1 u2)) (/ r (sin half))))
        (cal:v+ x (cal:v* u1 tl))
        (cal:v+ x (cal:v* u2 tl))))

;; every radius that fits, from sf:*first* up in sf:*step*s, capped at
;; sf:*maxshown*
(defun sf:candidates (rmax / r out)
  (setq r sf:*first*)
  (while (and (<= r rmax)
              (or (null sf:*maxshown*) (< (length out) sf:*maxshown*)))
    (setq out (cons r out)
          r   (+ r sf:*step*)))
  (reverse out))

;; how many would have fitted if nothing capped the list -- what the
;; cap hid has to be said out loud, or 8 previews read as "that is all
;; this corner takes"
(defun sf:howmany (rmax / r n)
  (setq r sf:*first* n 0)
  (while (<= r rmax) (setq n (1+ n) r (+ r sf:*step*)))
  n)

;;; -------------------- previews ------------------------------------

;; Remember what was drawn: everything goes on the erase list, and an
;; arc also goes on the list a click is looked up in.
(defun sf:mark (en r)
  (if en
    (progn
      (setq sf:*preview* (cons en sf:*preview*))
      (if r (setq sf:*picks* (cons (cons en r) sf:*picks*)))))
  en)

;; the radius a preview arc stands for, nil for anything else in the
;; drawing
(defun sf:radof (en / p)
  (setq p (assoc en sf:*picks*))
  (if p (cdr p)))

;; Take every preview back out of the drawing.  Called on the way out
;; of the command however it ends -- a preview left behind would be
;; read as drawn work by every other tool in the toolset.
(defun sf:clear ( / e)
  (foreach e sf:*preview* (if (and e (entget e)) (entdel e)))
  (setq sf:*preview* nil
        sf:*picks*   nil))

;; one dashed preview arc, drawn the short way round between its two
;; tangent points (a fillet arc is always less than a half circle)
(defun sf:draw-arc (c r p1 p2 / a1 a2 dxf)
  (setq a1 (angle c p1)
        a2 (angle c p2))
  (if (> (cal:angnorm (- a2 a1)) pi)
    (setq a1 (angle c p2)
          a2 (angle c p1)))
  (setq dxf (list '(0 . "ARC") '(100 . "AcDbEntity")
                  (cons 8 sf:*layer*) (cons 62 sf:*color*)
                  (cons 6 (sf:ensure-ltype))
                  '(100 . "AcDbCircle")
                  (list 10 (car c) (cadr c) 0.0)
                  (cons 40 r)
                  '(100 . "AcDbArc")
                  (cons 50 a1) (cons 51 a2)))
  (if sf:*ltscale* (setq dxf (append dxf (list (cons 48 sf:*ltscale*)))))
  (if (entmake dxf) (entlast)))

;; the radius, lettered beside a preview.  Middle-centre justified, so
;; the text sits on the point it is given whatever it says.
(defun sf:draw-label (p str / h)
  (setq h (if sf:*txthgt* sf:*txthgt* 6.0))
  (if (entmake (list '(0 . "TEXT") '(100 . "AcDbEntity")
                     (cons 8 sf:*layer*) (cons 62 sf:*color*)
                     '(100 . "AcDbText")
                     (list 10 (car p) (cadr p) 0.0)
                     (cons 40 h) (cons 1 str)
                     '(72 . 1)                       ; centred across
                     (list 11 (car p) (cadr p) 0.0)
                     '(100 . "AcDbText")
                     '(73 . 2)))                     ; and down
    (entlast)))

;; Draw the whole fan of previews.  Labels alternate between the two
;; legs: consecutive tangent points sit one step apart along one leg,
;; which is not room enough for two labels side by side.
(defun sf:preview (geo rads / i r a c t1 t2 anchor)
  (setq i 0)
  (cal:ensure-layer sf:*layer* sf:*color*)
  (foreach r rads
    (setq a  (sf:arcpts geo r)
          c  (car   a)
          t1 (cadr  a)
          t2 (caddr a))
    (sf:mark (sf:draw-arc c r t1 t2) r)
    (if sf:*label*
      (progn
        (setq anchor (if (= 0 (rem i 2)) t1 t2))
        ;; pushed straight off the arc, away from its centre, so the
        ;; label never lands on the line it belongs to
        (sf:mark (sf:draw-label
                   (cal:v+ anchor
                          (cal:v* (cal:unit (cal:v- anchor c))
                                 (* 0.9 (if sf:*txthgt* sf:*txthgt* 6.0))))
                   (sf:rlabel r))
                 nil)))
    (setq i (1+ i))))

;;; -------------------- asking --------------------------------------

;; One entsel that insists on a LINE.  KW is the single keyword the
;; prompt offers as its way out, and it is also what Enter does -- the
;; bracket text is the keyword itself, so a click on it sends exactly
;; what is tested for, and the <default> says what an empty answer
;; means.  OTHER is the line already picked for this corner, which
;; cannot be picked twice.  Returns (ename pick-point-in-WCS), or nil
;; when the way out is taken.  Nothing has been drawn at this point, so
;; a click that lands on empty paper costing the loop is a fair trade
;; for Enter meaning what it says.
(defun sf:askline (msg kw other / sel ans typ)
  (while (not ans)
    (initget kw)
    (setq sel (entsel (strcat "\n" msg " [" kw "] <" kw ">: ")))
    (cond
      ((= (type sel) 'STR) (setq ans 'SF-NONE))
      ((null sel) (setq ans 'SF-NONE))
      ((and other (eq (car sel) other))
       (princ "\n  (that is the line you just picked -- click the OTHER leg)"))
      ((not (= "LINE" (setq typ (cdr (assoc 0 (entget (car sel)))))))
       (princ (strcat "\n  (that is a " typ " -- SMARTFILLET rounds the"
                      " corner between two straight LINEs; explode a"
                      " polyline first)")))
      (t (setq ans (list (car sel) (cal:2d (trans (cadr sel) 1 0)))))))
  (if (eq ans 'SF-NONE) nil ans))

;; Which preview was clicked, as its radius.  nil when the user gives
;; up on the corner.  This one has no <default>, so Enter re-asks
;; (STANDARDS.md section 1 rule 5): the arcs are thin and the near-miss
;; that would throw a whole fan of them away is exactly the click this
;; prompt invites.  Cancel is in the bracket, so there is a mouse-only
;; way out that does not depend on hitting anything.
(defun sf:pickpreview ( / sel ans r)
  (while (not ans)
    (initget "Cancel")
    (setq sel (entsel "\nClick the rounded corner you want [Cancel]: "))
    (cond
      ((= (type sel) 'STR) (setq ans 'SF-NONE))
      ((null sel)
       (princ (strcat "\n  (nothing there -- click one of the dashed"
                      " corners, or type Cancel)")))
      ((setq r (sf:radof (car sel))) (setq ans r))
      (t (princ (strcat "\n  (that is not one of the previews -- click a"
                        " dashed corner)")))))
  (if (eq ans 'SF-NONE) nil ans))

;;; -------------------- cutting and dimensioning --------------------

;; Cut the corner for real.  The two picks go to FILLET exactly as the
;; user made them, so the side each line keeps is the side clicked.
;; Returns the arc FILLET made, or nil when it refused.
(defun sf:dofillet (e1 pk1 e2 pk2 r / pre new ed)
  (setq pre (entlast))
  (setvar "FILLETRAD" r)
  (command "_.FILLET" (list e1 (trans pk1 0 1)) (list e2 (trans pk2 0 1)))
  (setq new (entlast))
  (if (and new (not (eq new pre))
           (setq ed (entget new))
           (= "ARC" (cdr (assoc 0 ed))))
    new))

;; Switch to the small-dimension style for a measurement under
;; sf:*smalldim*, POOL's rule (pool:dimsbegin, POOL.LSP:370), so a
;; fillet callout matches the dims beside it.  Returns the style to go
;; back to, nil when nothing moved.
(defun sf:dimsbegin (d / od)
  (if (< d sf:*smalldim*)
    (if (tblsearch "DIMSTYLE" sf:*smallstyle*)
      (progn
        (setq od (getvar "DIMSTYLE"))
        (if (= (strcase od) (strcase sf:*smallstyle*))
          (setq od nil)                    ; already current
          (command "_.-DIMSTYLE" "_Restore" sf:*smallstyle*))
        od)
      (progn
        (if (not sf:*smallwarned*)
          (progn
            (princ (strcat "\n(no \"" sf:*smallstyle* "\" dim style in"
                           " this drawing -- the radius is dimensioned"
                           " in the current style)"))
            (setq sf:*smallwarned* t)))
        nil))))

(defun sf:dimsend (od)
  (if (and od (tblsearch "DIMSTYLE" od))
    (command "_.-DIMSTYLE" "_Restore" od)))

;; DIMSTYLE is read-only to setvar, so it goes back through a command,
;; and command-s so the same call is legal from inside *error*.
(defun sf:restyle (odim)
  (if (and odim (tblsearch "DIMSTYLE" odim)
           (not (equal odim (getvar "DIMSTYLE"))))
    (vl-catch-all-apply 'command-s
                        (list "_.-DIMSTYLE" "_Restore" odim))))

;; Put the radius dimension on the arc just cut: leader out from the
;; arc along the line from its centre through the corner, which is the
;; one direction that is clear of both legs.  The centre comes from the
;; geometry the arc was cut to rather than back out of the arc -- they
;; are the same point, and the one we already hold cannot be read out
;; of a tilted OCS wrong.  Returns the dimension.
(defun sf:dimarc (arc r geo / c x out on loc od pre new)
  (setq c   (car (sf:arcpts geo r))
        x   (car geo)
        out (cal:unit (cal:v- x c)))
  (if out
    (progn
      (setq on  (cal:v+ c (cal:v* out r))
            loc (cal:v+ c (cal:v* out (+ r (if sf:*dimoff*
                                           sf:*dimoff*
                                           (max r 12.0)))))
            pre (entlast))
      (setvar "CLAYER" (cal:ensure-layer sf:*dimlayer* 2))
      (setq od (sf:dimsbegin r))
      (command "_.DIMRADIUS" (list arc (trans on 0 1))
               "_non" (trans loc 0 1))
      (sf:dimsend od)
      (setq new (entlast))
      (if (and new (not (eq new pre))) new))))

;; Re-letter a radius callout as typical.  The radius is called out
;; once and the repeats read "Typ.", the way a drafter letters it -- and
;; whether there WERE repeats is not known until the loop has run, so
;; the note is added afterwards rather than guessed at.  "<>" is
;; AutoCAD's stand-in for the measurement, so the dimension goes on
;; measuring itself.
(defun sf:typit (dim / ed)
  (if (and dim (setq ed (entget dim)))
    (progn
      (setq ed (if (assoc 1 ed)
                 (subst (cons 1 "<> Typ.") (assoc 1 ed) ed)
                 (append ed (list (cons 1 "<> Typ.")))))
      (entmod ed)
      (entupd dim))))

;; The rest of the corners, at the radius already settled on: two lines
;; each until Done.  Returns how many were cut.
(defun sf:repeat (r / n go a b geo arc)
  (setq n 0 go t)
  (while go
    (setq a (sf:askline "Select the first line of the next corner"
                        "Done" nil))
    (setq b (if a (sf:askline "Select the second line of that corner"
                              "Done" (car a))))
    (if (or (null a) (null b))
      (setq go nil)
      (progn
        (setq geo (sf:corner (car a) (cadr a) (car b) (cadr b)))
        (cond
          ((null geo)
           (princ (strcat "\n  (those two never meet at an angle --"
                          " left alone)")))
          ((< (sf:rmax geo) r)
           (princ (strcat "\n  (too short a corner for "
                          (sf:rlabel r) " -- left alone)")))
          ((setq arc (sf:dofillet (car a) (cadr a) (car b) (cadr b) r))
           (setq n (1+ n))
           (if sf:*dimrepeat* (sf:dimarc arc r geo)))
          (t (princ (strcat "\n  (AutoCAD would not fillet that corner"
                            " -- left alone)")))))))
  n)

;;; -------------------- the command ---------------------------------

(defun c:SMARTFILLET ( / *error* olderr odim undo-open
                         one two geo rmax rads extra r arc dim1 made)

  ;; -- restore drawing state on error / Esc.  The previews go first:
  ;;    they are entities like any other, and a run cut short partway
  ;;    would otherwise leave a fan of dashed arcs in the drawing for
  ;;    the next tool to read as work.  Then the user's settings, then
  ;;    the undo group -- left open, the next U would swallow the
  ;;    user's own work
  (setq olderr *error*)
  (defun *error* (m)
    (sf:clear)
    (cal:sysrestore)
    (sf:restyle odim)
    (if undo-open
      (vl-catch-all-apply 'command-s (list "_.UNDO" "_End")))
    (setq *error* olderr)
    (if (and m (not (wcmatch (strcase m)
                             "*BREAK*,*CANCEL*,*QUIT*,*EXIT*")))
      (princ (strcat "\nSMARTFILLET error: " m)))
    (princ))

  (vl-load-com)
  (cal:syssave '("OSMODE" "CMDECHO" "CLAYER" "FILLETRAD" "TRIMMODE"))
  (setq odim (getvar "DIMSTYLE")
        made 0)
  (setvar "CMDECHO" 0)
  (setvar "OSMODE"  0)
  (setvar "TRIMMODE" 1)                    ; a fillet that leaves the
                                           ; old corner standing is not
                                           ; what anyone means by one

  ;; -- 1. the corner: two lines, each clicked on the side to keep
  (setq one (sf:askline "Select the first line of the corner" "Cancel" nil))
  (if one
    (setq two (sf:askline "Select the second line of the corner"
                          "Cancel" (car one))))
  (setq geo (if (and one two)
              (sf:corner (car one) (cadr one) (car two) (cadr two))))

  (cond
    ((not (and one two))
     (princ "\nSMARTFILLET cancelled -- nothing drawn."))

    ((null geo)
     (princ (strcat "\nThose two lines make no corner -- they are"
                    " parallel, or they run straight through one"
                    " another.  Nothing to round.")))

    ((< (setq rmax (sf:rmax geo)) sf:*first*)
     (princ (strcat "\nThe shorter leg of that corner only allows "
                    (sf:rlabel rmax) " -- less than the smallest"
                    " preview (" (sf:rlabel sf:*first*) ").  Nothing"
                    " drawn; lower sf:*first* to work at that size.")))

    (t
     ;; -- 2. one undo group over the previews and everything they lead
     ;;       to, so a single U undoes the lot
     (command "_.UNDO" "_Begin")
     (setq undo-open t
           rads      (sf:candidates rmax)
           extra     (- (sf:howmany rmax) (length rads)))
     (sf:preview geo rads)
     (princ (strcat "\n" (itoa (length rads)) " corner"
                    (if (= 1 (length rads)) "" "s")
                    " that fit, dashed: " (sf:rlabel (car rads))
                    (if (cdr rads)
                      (strcat " to " (sf:rlabel (last rads)))
                      "")
                    "."))
     ;; a cap that says nothing reads as "that is all this corner
     ;; takes", which is a different fact
     (if (> extra 0)
       (princ (strcat "\n" (itoa extra) " larger radi"
                      (if (= 1 extra) "us" "i") " also fit"
                      (if (= 1 extra) "s" "") " and "
                      (if (= 1 extra) "is" "are") " not shown"
                      " -- raise sf:*maxshown* to see "
                      (if (= 1 extra) "it" "them") ".")))

     ;; -- 3. the one that gets cut
     (setq r (sf:pickpreview))
     (sf:clear)
     (cond
       ((null r)
        (princ "\nNothing picked -- the corner is as it was."))
       ((null (setq arc (sf:dofillet (car one) (cadr one)
                                     (car two) (cadr two) r)))
        (princ (strcat "\nAutoCAD would not fillet that corner at "
                       (sf:rlabel r) " -- the lines are as they were.")))
       (t
        (setq made 1
              dim1 (sf:dimarc arc r geo))
        (princ (strcat "\n" (sf:rlabel r) " corner cut and dimensioned"
                       (if dim1 (strcat " on layer " sf:*dimlayer*) "")
                       "."))

        ;; -- 4. the same radius, for the rest of the corners
        (if (cal:askyn (strcat "Fillet other corners at "
                              (sf:rlabel r) "?")
                      "Yes" nil)
          (setq made (+ made (sf:repeat r))))
        (if (and sf:*typ* dim1 (> made 1)) (sf:typit dim1))

        (princ (strcat "\n" (itoa made) " corner"
                       (if (= 1 made) "" "s") " filleted at "
                       (sf:rlabel r)
                       (if (and sf:*typ* (> made 1) dim1)
                         " -- the one dimension now reads Typ."
                         "")
                       "."))))

     (command "_.UNDO" "_End")
     (setq undo-open nil)))

  ;; every path out drops the snapshot, the quiet ones included: a run
  ;; that found nothing to do and kept its snapshot would hand it to the
  ;; NEXT run, which would then put the user's settings back to what
  ;; they were two commands ago
  (sf:restyle odim)
  (cal:sysrestore)
  (setq *error* olderr)
  (princ))

(defun c:SMARTFILLETVER ()
  (princ (strcat "\nSMARTFILLET " *smartfillet-version*))
  (princ))

(princ (strcat "\nSMARTFILLET " *smartfillet-version*
               " loaded -- type SMARTFILLET, pick two lines, and click"
               " the rounded corner you want."))
(princ)


;;; ======================================================================
;;; >>> SPACHECK.lsp
;;; ======================================================================

;;; ======================================================================
;;; SPACHECK.lsp  --  audit a finished spa drawing against what SPA draws
;;; ----------------------------------------------------------------------
;;; For AutoCAD 2018 and later (plain AutoLISP, no external libraries).
;;;
;;; Commands:  SPACHECK        guided review of everything it flags
;;;            SPACHECKSCAN    the same audits, read-only
;;;            LITESPACHECKSCAN  the scan minus the dimension audit
;;;            SPACHECKVER     print the loaded version
;;;            SPACHECKRESCUE  put back every colour, remove the markers
;;;            TUTORIALSPACHECK   the checklist, a worked demo, or both
;;; ======================================================================
;;;
;;; SHARED BUILD: requires CALOFIN-LIB.lsp (load via CALOFIN-LOADER.lsp).
;;; Generic helpers live there under cal: - see STANDARDS.md.
;;;
;;;  Highlight the spa drawing TOGETHER WITH its "Spa Cover Details"
;;;  block; SPACHECK reads the block for the grade and taper, then holds
;;;  the drawing against the rules SPA.LSP builds to.  Every audit is
;;;  derived from what SPA actually draws, so a drawing SPA produced
;;;  passes and a hand-edited one shows exactly where it drifted.
;;;
;;;  THE CHECKS
;;;
;;;   1. SPA COVER DETAILS BLOCK.  One must be in the selection, with a
;;;      readable TAPER tag; GRADE may be absent (Standard is assumed,
;;;      as SPA assumes it).  Everything in section 5 depends on it.
;;;
;;;   2. THE COVER OUTLINE.  Exactly one, on layer COVER, and it must be
;;;      a single CLOSED bounded entity -- one LWPOLYLINE, or a CIRCLE /
;;;      ELLIPSE for a round spa.  Loose lines and arcs are the old
;;;      pre-bounded output and are reported as such.
;;;
;;;   3. THE WATER'S EDGE OUTLINE.  Optional -- a drawing may show one
;;;      outline only.  When present it must also be a single closed
;;;      entity, on layer POOL, drawn dashed, and it must lie INSIDE the
;;;      cover: the cover is always the larger of the two.
;;;
;;;   4. THE DIMENSIONS.  First the roster-wide verdict: every
;;;      dimension must sit on the DIMENSION layer, and any that do
;;;      not are counted, their layers named, and CDIM suggested to
;;;      move them -- the one dimension check LITESPACHECKSCAN keeps.
;;;      Then every dimension is checked for
;;;        - the right layer (DIMENSION),
;;;        - the right style: STANDARD INCHES for the cover's, and
;;;          STANDARD INCHES 0.5 for the water's edge's,
;;;        - agreement with the geometry: a dimension whose measurement
;;;          does not match what it spans is reported with both numbers,
;;;        - definition points that actually sit on the outline.
;;;      Then the roster: the two overalls must be present and must read
;;;      the cover's true size; each must carry its Cover Size / Water's
;;;      Edge note; with both outlines drawn there must be an Overlap
;;;      dimension and it must read the true lap; and the overall
;;;      standoffs must be SPA's (2 ft above, 3 ft to the left).
;;;
;;;   5. THE HINGES.  Hinges are the LINEs on layer COVER (the outline
;;;      itself is a polyline, so the two never confuse).  Checked
;;;      against the block's grade and taper:
;;;        - the piece count must be one the taper allows,
;;;        - no piece wider than the foam width,
;;;        - no hinge longer than the foam length,
;;;        - the fold/velcro arrangement must match the Hinge
;;;          Arrangement Chart for that piece count,
;;;        - every hinge must carry its label on layer TEXT.
;;;      Hardware called for by the longest hinge -- velcro hinges,
;;;      double C channel, hold down kit -- is reported as advice.
;;;
;;;   6. FEET AND INCHES.  Every text box in the selection -- TEXT,
;;;      MTEXT and the ATTRIB values on blocks -- must state its
;;;      inches wherever it states feet: 5' is flagged, 5'-0", 3'-2"
;;;      and a plain 40" are fine.  A feet mark is an apostrophe
;;;      straight after a digit, so "Water's Edge" is prose and never
;;;      flagged.  LITESPACHECKSCAN keeps this one.
;;;
;;;   7. THE TECH TITLE DATE.  The Date attribute of the "Tech Title"
;;;      block must read TODAY, written MM/DD/YYYY -- a sheet going
;;;      out under an old date is the mistake this catches.  The block
;;;      is looked for in the selection and then across the drawing;
;;;      with none in reach the report says the date was not checked
;;;      rather than flagging it.  LITESPACHECKSCAN keeps this one.
;;;
;;;   8. THE TITLE BLOCK.  Everything on the border layer is measured
;;;      together, so a frame drawn as one polyline and one drawn as
;;;      four lines both measure the same.  A spa sheet's title block is
;;;      exactly 0.6x the liner block: the liner nominal is 704 x
;;;      543.625, so the spa nominal is 422.4 x 326.175.  Anything else
;;;      is reported with the factor it actually came out at, and a
;;;      border out of proportion is reported separately as STRETCHED.
;;;
;;;   9. A SPACHECK REPORT (MTEXT) is placed to the RIGHT of the
;;;      drawing, sized to scale with it: a large title, the date and
;;;      version under it, an ALL CLEAR / problem-count verdict, then
;;;      the SPA-specific findings under underlined section headings.
;;;      The mechanical per-dimension audit (each dimension's layer,
;;;      style and span agreement) is set apart in a DIMENSION AUDIT
;;;      column to the RIGHT of the main sheet, since DIMCHECK covers
;;;      the same ground; LITESPACHECKSCAN skips that audit entirely,
;;;      for drawings DIMCHECK already went over.  Problems in RED at
;;;      full size, advice in CYAN, all-clear in green at 75%.
;;;
;;;  SPACHECK walks whatever it flagged one item at a time -- greying
;;;  the rest out, zooming to each, and colouring the ones you confirm
;;;  are wrong -- while SPACHECKSCAN runs the identical audits and
;;;  writes nothing but the report.  SPACHECKRESCUE puts every colour
;;;  back and removes the markers.
;;; ======================================================================

;;; -------------------- version -----------------------------------------
;;;  The banner form tools/release_lisp.py reads (lowercase name, "v",
;;;  one dot).  Bump it with every change and regenerate releases/.

(setq *spacheck-version* "v1.6")

;; vlax-* is used for bounding boxes, so load Visual LISP once here
;; rather than inside a command body.
(vl-load-com)

;;; -------------------- tunables ----------------------------------------

;; Layers SPA draws on -- the audit is only as right as these are.
(setq spachk:*lay-cover*  "COVER")      ; the cover outline and the hinges
(setq spachk:*lay-water*  "POOL")       ; the water's edge outline
(setq spachk:*lay-dim*    "DIMENSION")  ; every dimension
(setq spachk:*lay-text*   "TEXT")       ; the hinge labels
(setq spachk:*lay-notes*  "SPA-NOTES")  ; corner letters, mode note, report

;; CDIM is the command that moves stray dimensions onto *lay-dim*, and
;; is what the report tells you to run when it finds any.
(setq spachk:*dimfix-cmd* "CDIM")

;; The sheet's title block, and the attribute in it carrying the date.
;; This is the Tech Title BLOCK, not the drawn border section 7 checks.
(setq spachk:*techtitle-block* "Tech Title")  ; spaces optional in the name
(setq spachk:*date-tag*        "Date")

;; Dimension styles, one per outline (SPA's spa:*ds-cover* / *ds-water*).
(setq spachk:*ds-cover*   "STANDARD INCHES")
(setq spachk:*ds-water*   "STANDARD INCHES 0.5")

;; The notes SPA stacks under an overall's measurement.
(setq spachk:*sfx-cover*  "Cover Size")
(setq spachk:*sfx-water*  "Water's Edge")
(setq spachk:*sfx-lap*    "Overlap")

;; SPA's standoffs (spa:*topoff* / *dimoff* / *flatoff*), and how far a
;; dimension line may sit from them before it is worth reporting.
(setq spachk:*topoff*     24.0)   ; 2 ft: cover -> the TOP overall dim
(setq spachk:*dimoff*     36.0)   ; 3 ft: cover -> the LEFT overall dim
(setq spachk:*off-tol*    2.0)    ; inches of slack on either standoff

;; The block SPA reads the grade and taper out of.
(setq spachk:*details-block* "Spa Cover Details")

;; TITLE BLOCK.  The liner block is linfincheck's nominal border
;; (*lfc-border-w* / *lfc-border-h*); a spa sheet's title block is
;; exactly this fraction of it.
(setq spachk:*liner-w*    704.0)     ; 58'-8"     in drawing units
(setq spachk:*liner-h*    543.625)   ; 45'-3 5/8" in drawing units
(setq spachk:*title-frac* 0.6)       ; spa title block = 0.6 x the liner
(setq spachk:*border-layer* "border")
(setq spachk:*border-tol* 0.005)     ; 0.5% slack on the factor and the aspect

;; How close a dimension's measurement must be to the geometry it spans,
;; and how close a definition point must sit to the outline.
(setq spachk:*meas-tol*   0.0625)    ; 1/16" -- a fractional dim rounds
(setq spachk:*pt-tol*     1.0e-4)

;; Marking and report.
(setq spachk:*sysold*      nil)      ; saved sysvars, restored on the way out
(setq spachk:*demo-ents*   nil)      ; what TUTORIALSPACHECK's demo drew
(setq spachk:*grey-color*  8)
(setq spachk:*flag-color*  1)        ; red: what you confirmed is wrong
(setq spachk:*report-layer* "SPACHECK-REPORT")
(setq spachk:*report-color* 3)
(setq spachk:*green-scale* 0.75)     ; all-clear text height vs the red
(setq spachk:*advice-color* 4)       ; cyan: advice, not a failure
(setq spachk:*report-chars* 48.0)    ; report column width, in text heights
(setq spachk:*zoom-margin* 0.75)

;; Foam sheets, copied from SPA (spa:*foamtab*) so the audit measures
;; against the same rules the drawing was built to:
;;   (grade taper ((foamWidth . foamLength) ...) (piece counts, 5 = 5+))
(setq spachk:*foamtab*
  (list
    (list "ECONOMY"     "3-2"   (list (cons 48.0 96.0))                    (list 2))
    (list "STANDARD"    "3-2"   (list (cons 48.0 144.0) (cons 49.5 102.0)) (list 2))
    (list "STANDARD"    "4-2"   (list (cons 48.0 96.0)  (cons 49.5 102.0)) (list 2 3 4))
    (list "STANDARD"    "4-3"   (list (cons 48.0 144.0))                   (list 2 3 4))
    (list "STANDARD"    "5-3"   (list (cons 48.0 96.0))                    (list 2 3 4 5))
    (list "STANDARD"    "5-4"   (list (cons 48.0 96.0))                    (list 2 3 4 5))
    (list "STANDARD"    "3-3"   (list (cons 48.0 144.0))                   (list 2 3 4 5))
    (list "ULTRA"       "3-2"   (list (cons 48.0 144.0))                   (list 2))
    (list "ULTRA"       "4-3"   (list (cons 48.0 96.0))                    (list 2 3 4))
    (list "ULTRA"       "3-3"   (list (cons 48.0 144.0))                   (list 2 3 4 5))
    (list "THERMOLIGHT" "1-3/8" (list (cons 53.0 nil))                     (list 2 3 4 5))))

;; Hardware called for by the LONGEST hinge, per grade:
;;   (grade velcro doubleC holddown), each (OVER n) | (ALWAYS) | (NEVER)
;;   | (REQUEST)
(setq spachk:*hardtab*
  (list
    (list "ECONOMY"     '(REQUEST)    '(REQUEST)    '(REQUEST))
    (list "STANDARD"    '(OVER 120.0) '(OVER 108.0) '(OVER 120.0))
    (list "ULTRA"       '(OVER 108.0) '(NEVER)      '(OVER 96.0))
    (list "THERMOLIGHT" '(ALWAYS)     '(NEVER)      '(NEVER))))

;;; -------------------- small helpers -----------------------------------

(defun spachk:join (lst sep / out s)
  (foreach s lst
    (setq out (if out (strcat out sep s) s)))
  (if out out ""))

;; Everything after the last colon, trimmed: "Taper: 4-2" -> "4-2".
(defun spachk:aftercolon (s / i out)
  (setq i (strlen s) out s)
  (while (> i 0)
    (if (= ":" (substr s i 1))
        (progn (setq out (substr s (1+ i))) (setq i 0))
        (setq i (1- i))))
  (cal:trim out))

;; Does s contain sub?  Case-sensitive, plain AutoLISP.
(defun spachk:has (s sub / n m i found)
  ;; nil-safe: an absent label or text override is simply "no match"
  (if (or (null s) (null sub)) (setq s "" sub "x"))
  (setq n (strlen s) m (strlen sub) i 1 found nil)
  (if (> m 0)
      (while (and (not found) (<= i (- n m -1)))
        (if (= sub (substr s i m)) (setq found t))
        (setq i (1+ i))))
  found)

;;; -------------------- report text -------------------------------------
;;;  A report row is (text . level): level nil = all clear, 1 = a
;;;  problem, 2 = advice, 3 = a section heading.  The four render
;;;  differently in the MTEXT.

;; A report row is (text . level): nil = all clear, 1 = a problem,
;; 2 = advice, 3 = a section heading.  spachk:lvl-p compares
;; nil-safely -- (= nil 1) is not something to rely on.
(defun spachk:row (s lvl) (cons s lvl))
(defun spachk:row-txt (r) (car r))
(defun spachk:row-lvl (r) (cdr r))
(defun spachk:lvl-p (r n) (and (spachk:row-lvl r) (= (spachk:row-lvl r) n)))

(defun spachk:red (s)
  (strcat "{\\C" (itoa spachk:*flag-color*) ";" s "}"))

(defun spachk:cyan (s)
  (strcat "{\\C" (itoa spachk:*advice-color*) ";" s "}"))

(defun spachk:small (s)
  (strcat "{\\H" (rtos spachk:*green-scale* 2 2) "x;" s "}"))

;; The report's title line: half again the base height.
(defun spachk:big (s)
  (strcat "{\\H1.5x;" s "}"))

;; A section heading: underlined, with a thin blank line above it so
;; the sections read as blocks.  The braces scope both codes, and the
;; \P inside the first group is a paragraph break at 0.4x height --
;; a narrow gap, not a full empty line.
(defun spachk:hdg (s)
  (strcat "{\\H0.4x;\\P}{\\L" s "}"))

;; Findings are indented two spaces under their heading; the indent
;; sits INSIDE the colour/height wrap so a problem row still starts
;; with its colour code.
(defun spachk:render (r)
  (cond ((spachk:lvl-p r 3) (spachk:hdg (spachk:row-txt r)))
        ((spachk:lvl-p r 1) (spachk:red (strcat "  " (spachk:row-txt r))))
        ((spachk:lvl-p r 2) (spachk:cyan (strcat "  " (spachk:row-txt r))))
        (t (spachk:small (strcat "  " (spachk:row-txt r))))))

;;; -------------------- layers ------------------------------------------
;;;  The canonical ensure-layer: create, or when it already exists make
;;;  sure it is on, thawed and unlocked -- without this a successful run
;;;  onto a frozen layer looks like the command did nothing.

;;; -------------------- entity helpers ----------------------------------

(defun spachk:dxf (code ent) (cdr (assoc code (entget ent))))

(defun spachk:etype (ent) (spachk:dxf 0 ent))

(defun spachk:layer (ent) (spachk:dxf 8 ent))

(defun spachk:on-layer-p (ent name)
  (= (strcase (spachk:layer ent)) (strcase name)))

;; Overall extents of a list of entities: ((minx miny) (maxx maxy)).
(defun spachk:bbox-of (ents / e bb lo hi)
  (foreach e ents
    (if (setq bb (cal:bbox-ent e))
      (setq lo (if lo (list (min (car lo) (caar bb))
                            (min (cadr lo) (cadar bb)))
                   (list (caar bb) (cadar bb)))
            hi (if hi (list (max (car hi) (caadr bb))
                            (max (cadr hi) (cadadr bb)))
                   (list (caadr bb) (cadadr bb))))))
  (if (and lo hi) (list lo hi)))

(defun spachk:bw (bb) (- (car (cadr bb)) (car (car bb))))
(defun spachk:bh (bb) (- (cadr (cadr bb)) (cadr (car bb))))

;; Is inner's bounding box wholly inside outer's, with slack?
(defun spachk:inside-p (inner outer slack)
  (and (>= (- (caar inner) (caar outer)) (- slack))
       (>= (- (cadar inner) (cadar outer)) (- slack))
       (>= (- (caadr outer) (caadr inner)) (- slack))
       (>= (- (cadadr outer) (cadadr inner)) (- slack))))

(defun spachk:closed-p (ent / f)
  (cond ((member (spachk:etype ent) '("CIRCLE" "ELLIPSE")) t)
        ((= (spachk:etype ent) "LWPOLYLINE")
         (setq f (spachk:dxf 70 ent))
         (and f (numberp f) (= 1 (logand 1 f))))
        (t nil)))

;; A bounded outline: one closed entity of a type SPA emits.
(defun spachk:outline-ents (ss layer / i e out)
  (setq i 0)
  (if ss
    (repeat (sslength ss)
      (setq e (ssname ss i) i (1+ i))
      (if (and (entget e)
               (spachk:on-layer-p e layer)
               (member (spachk:etype e)
                       '("LWPOLYLINE" "POLYLINE" "CIRCLE" "ELLIPSE")))
        (setq out (cons e out)))))
  (reverse out))

;; The loose lines and arcs on a layer -- on COVER these are the hinges;
;; on POOL they are the pre-bounded output that should be a polyline.
(defun spachk:loose-ents (ss layer / i e out)
  (setq i 0)
  (if ss
    (repeat (sslength ss)
      (setq e (ssname ss i) i (1+ i))
      (if (and (entget e)
               (spachk:on-layer-p e layer)
               (member (spachk:etype e) '("LINE" "ARC")))
        (setq out (cons e out)))))
  (reverse out))

(defun spachk:ents-of-type (ss etype / i e out)
  (setq i 0)
  (if ss
    (repeat (sslength ss)
      (setq e (ssname ss i) i (1+ i))
      (if (and (entget e) (= (spachk:etype e) etype))
        (setq out (cons e out)))))
  (reverse out))

;;; -------------------- blocks ------------------------------------------

;; Attributes of a block reference, as (("TAG" . value) ...).
(defun spachk:attribs (ename / e ed out)
  (setq e (entnext ename))
  (while (and e (setq ed (entget e)) (= "ATTRIB" (cdr (assoc 0 ed))))
    (setq out (cons (cons (strcase (cdr (assoc 2 ed))) (cdr (assoc 1 ed))) out)
          e (entnext e)))
  (reverse out))

;; The Spa Cover Details block in the selection: the one whose name
;; matches, else any INSERT carrying a TAPER tag.
(defun spachk:find-details (ss / ins e best fallback nm)
  (setq ins (spachk:ents-of-type ss "INSERT"))
  (foreach e ins
    (setq nm (strcase (spachk:dxf 2 e)))
    (cond
      ((and (not best) (= nm (strcase spachk:*details-block*))) (setq best e))
      ((and (not fallback) (cdr (assoc "TAPER" (spachk:attribs e))))
       (setq fallback e))))
  (if best best fallback))

(defun spachk:tapernorm (v / u)
  (setq u (strcase v))
  (cond ((spachk:has u "3-2") "3-2")
        ((spachk:has u "4-2") "4-2")
        ((spachk:has u "4-3") "4-3")
        ((spachk:has u "5-3") "5-3")
        ((spachk:has u "5-4") "5-4")
        ((spachk:has u "3-3") "3-3")
        ((spachk:has u "3/8") "1-3/8")))

(defun spachk:gradenorm (v / u)
  (setq u (strcase (if v v "")))
  (cond ((spachk:has u "ECON") "ECONOMY")
        ((or (spachk:has u "ULTRA") (spachk:has u "FRP")) "ULTRA")
        ((spachk:has u "THERMO") "THERMOLIGHT")
        (t "STANDARD")))

(defun spachk:gradeshort (g)
  (cond ((= g "ECONOMY") "ECO") ((= g "STANDARD") "STD")
        ((= g "ULTRA") "ULTRA") (t "THERMO")))

;;; -------------------- dimensions --------------------------------------

(defun spachk:dim-style (ent / s)
  (setq s (spachk:dxf 3 ent))
  (if s s ""))

;; The measurement AutoCAD stores on the dimension (DXF 42).
(defun spachk:dim-meas (ent) (spachk:dxf 42 ent))

;; The text override, if any (DXF 1) -- SPA puts its note there.
(defun spachk:dim-text (ent / s)
  (setq s (spachk:dxf 1 ent))
  (if s s ""))

;; The two extension-line origins of a linear/aligned dimension.
(defun spachk:dim-pts (ent / ed)
  (setq ed (entget ent))
  (list (cdr (assoc 13 ed)) (cdr (assoc 14 ed))))

;; Is this a linear or aligned dimension (the kinds SPA places)?  A
;; dimension with no DXF 70 at all is not one we can classify, so it is
;; left out rather than guessed at -- reading nil into logand would take
;; the whole audit down over one malformed entity.
(defun spachk:linear-p (ent / f)
  (setq f (spachk:dxf 70 ent))
  (and f (numberp f) (member (logand 7 f) '(0 1))))

;; The dimension line's own location (DXF 10).
(defun spachk:dim-loc (ent) (spachk:dxf 10 ent))

;; Every dimension in the selection, whatever layer it sits on.
(defun spachk:dims (ss) (spachk:ents-of-type ss "DIMENSION"))

;; The dimensions whose text carries a given note.
(defun spachk:dims-noted (dims note / e out)
  (foreach e dims
    (if (spachk:has (spachk:dim-text e) note) (setq out (cons e out))))
  (reverse out))

;;; -------------------- the hinge arrangement chart ----------------------
;;;  Copied from SPA (spa:hingetypes) so the audit measures against the
;;;  same rule the drawing was built to: fold hinges on even positions
;;;  and velcro on odd, across the whole row when pieces mod 4 is 0 or
;;;  2, and only to the chart's cutoff when it is odd, the rest
;;;  mirroring the left half.  Returns a list of "H" / "V", west to east.

(defun spachk:hingetypes (n allvel / hc m zone p out)
  (setq hc (1- n)
        m (rem n 4)
        zone (cond ((or (= m 0) (= m 2)) hc)
                   ((= m 1) (/ hc 2))
                   (t (/ (+ hc 2) 2)))
        p 0 out nil)
  (while (< p hc)
    (setq out (append out
                      (list (cond (allvel "V")
                                  ((< p zone) (if (= 0 (rem p 2)) "H" "V"))
                                  (t (nth (- hc 1 p) out)))))
          p (1+ p)))
  out)

(defun spachk:hallow (n allowed)
  (if (>= n 5) (member 5 allowed) (member n allowed)))

;; A rule against the longest hinge -> (needed . reason).  An OVER rule
;; with nothing to measure says so rather than guessing: the answer
;; depends entirely on a length, and inventing one would be worse than
;; admitting it is unknown.
(defun spachk:hardverdict (rule len / k v)
  (setq k (car rule) v (cadr rule))
  (cond
    ((eq k 'ALWAYS)  (cons t   "always for this grade"))
    ((eq k 'NEVER)   (cons nil "not used on this grade"))
    ((eq k 'REQUEST) (cons t   "upon request only"))
    ((not (and (numberp len) (numberp v)))
     (cons t "no hinge length to check - verify by hand"))
    ((> len v)       (cons t   (strcat "hinge " (rtos len 2 1)
                                       " over " (rtos v 2 0))))
    (t               (cons nil (strcat "hinge " (rtos len 2 1)
                                       " not over " (rtos v 2 0))))))

;;; -------------------- the title block ---------------------------------

;; A spa sheet's title block is exactly spachk:*title-frac* of the liner
;; block.  Returns the report sentence.
(defun spachk:title-verdict (bb / bw bh tw th sw sh sc)
  (setq tw (* spachk:*title-frac* spachk:*liner-w*)
        th (* spachk:*title-frac* spachk:*liner-h*))
  (if (null bb)
    (strcat "NO BORDER found on layer '" spachk:*border-layer* "'")
    (progn
      (setq bw (spachk:bw bb) bh (spachk:bh bb))
      (if (or (<= bw 1.0e-6) (<= bh 1.0e-6))
        "border has no measurable size"
        (progn
          (setq sw (/ bw tw) sh (/ bh th) sc (min sw sh))
          (cond
            ;; out of proportion is wrong whatever its size
            ((> (abs (- sw sh)) (* spachk:*border-tol* (max sw sh)))
             (strcat (rtos bw) " x " (rtos bh)
                     " - STRETCHED out of proportion (" (rtos sw 2 3)
                     "x wide but " (rtos sh 2 3) "x tall); a spa title"
                     " block is " (rtos tw) " x " (rtos th)))
            ;; the size the user asked for by name
            ((and (> sc (- 1.0 spachk:*border-tol*))
                  (< sc (+ 1.0 spachk:*border-tol*)))
             (strcat (rtos bw) " x " (rtos bh) " - "
                     (rtos spachk:*title-frac* 2 2)
                     "x the liner block, OK"))
            (t
             (strcat (rtos bw) " x " (rtos bh) " is "
                     (rtos (* sc spachk:*title-frac*) 2 3)
                     "x the liner block "
                     (rtos spachk:*liner-w*) " x " (rtos spachk:*liner-h*)
                     " - a spa title block must be exactly "
                     (rtos spachk:*title-frac* 2 2) "x it ("
                     (rtos tw) " x " (rtos th) ")"))))))))

;; Everything on the border layer, from the selection when it holds the
;; border and from the whole drawing when it does not.
(defun spachk:border-box (ss / ents ss2 i e out)
  (setq ents nil i 0)
  (if ss
    (repeat (sslength ss)
      (setq e (ssname ss i) i (1+ i))
      (if (and (entget e) (spachk:on-layer-p e spachk:*border-layer*))
        (setq ents (cons e ents)))))
  (if (null ents)
    (progn
      (setq ss2 (ssget "_X" (list (cons 8 spachk:*border-layer*))) i 0)
      (if ss2
        (repeat (sslength ss2)
          (setq e (ssname ss2 i) i (1+ i) ents (cons e ents))))))
  (if ents (spachk:bbox-of ents)))

;;; ======================================================================
;;;  THE AUDIT
;;; ----------------------------------------------------------------------
;;;  One function per section.  Each takes what it needs and returns
;;;  ((row ...) . (flagged-entity ...)) -- the rows go into the report,
;;;  the entities are what SPACHECK offers to walk you through.
;;; ======================================================================

(defun spachk:res (rows ents) (cons rows ents))
(defun spachk:res-rows (r) (car r))
(defun spachk:res-ents (r) (cdr r))

;;; --- 1. the Spa Cover Details block ------------------------------------

(defun spachk:audit-block (ss / blk att g tp rows)
  (setq blk (spachk:find-details ss))
  (if (null blk)
    (spachk:res
      (list (spachk:row (strcat "Spa Cover Details: NO BLOCK named '"
                                spachk:*details-block*
                                "' in the selection - highlight it with the"
                                " drawing; the hinge checks need its taper")
                        1))
      nil)
    (progn
      (setq att (spachk:attribs blk)
            g   (cdr (assoc "GRADE" att))
            tp  (cdr (assoc "TAPER" att))
            g   (spachk:gradenorm (if g (spachk:aftercolon g) nil))
            tp  (if tp (spachk:tapernorm (spachk:aftercolon tp)) nil))
      (setq rows
            (list (spachk:row (strcat "Spa Cover Details: grade "
                                      (spachk:gradeshort g)
                                      ", taper " (if tp tp "NOT READABLE"))
                              (if tp nil 1))))
      (if (and tp (= g "THERMOLIGHT") (/= tp "1-3/8"))
        (setq rows (append rows
                    (list (spachk:row
                            (strcat "Spa Cover Details: Thermo-Light is"
                                    " always 1-3/8 flat, not " tp)
                            1)))))
      (spachk:res rows (if tp nil (list blk))))))

;;; --- 2/3. the outlines --------------------------------------------------

(defun spachk:audit-outline (ss layer what required
                             / outs loose rows ents e)
  (setq outs  (spachk:outline-ents ss layer)
        loose (spachk:loose-ents ss layer)
        rows nil ents nil)
  ;; hinges live on COVER as LINEs, so only ARCs count as loose there
  (if (= (strcase layer) (strcase spachk:*lay-cover*))
    (setq loose (vl-remove-if '(lambda (e) (= (spachk:etype e) "LINE")) loose)))
  (cond
    ((null outs)
     (if required
       (setq rows (list (spachk:row
                          (strcat what ": NO OUTLINE on layer " layer
                                  " - nothing to check against")
                          1)))
       (setq rows (list (spachk:row
                          (strcat what ": not drawn (one outline only)")
                          nil)))))
    ((> (length outs) 1)
     (setq rows (list (spachk:row
                        (strcat what ": " (itoa (length outs))
                                " outlines on layer " layer
                                " - there must be exactly one")
                        1))
           ents outs))
    (t
     (setq e (car outs))
     (if (spachk:closed-p e)
       (setq rows (list (spachk:row
                          (strcat what ": one closed "
                                  (spachk:etype e) ", OK")
                          nil)))
       (setq rows (list (spachk:row
                          (strcat what ": the " (spachk:etype e)
                                  " on " layer " is NOT CLOSED - the"
                                  " outline must be a bounded entity")
                          1))
             ents (list e)))))
  (if loose
    (setq rows (append rows
                (list (spachk:row
                        (strcat what ": " (itoa (length loose))
                                " loose line/arc"
                                (if (= 1 (length loose)) "" "s")
                                " on " layer
                                " - the outline should be one closed"
                                " polyline, not separate segments")
                        1)))
          ents (append ents loose)))
  (spachk:res rows ents))

;;; --- the two outlines together -----------------------------------------

(defun spachk:audit-nesting (cov wat / rows bc bw)
  (setq rows nil)
  (if (and cov wat)
    (progn
      (setq bc (cal:bbox-ent cov) bw (cal:bbox-ent wat))
      (if (and bc bw)
        (if (spachk:inside-p bw bc 1.0e-6)
          (setq rows (list (spachk:row
                             (strcat "Cover vs water's edge: cover "
                                     (rtos (spachk:bw bc)) " x "
                                     (rtos (spachk:bh bc))
                                     " contains water's edge "
                                     (rtos (spachk:bw bw)) " x "
                                     (rtos (spachk:bh bw)) ", OK")
                             nil)))
          (setq rows (list (spachk:row
                             (strcat "Cover vs water's edge: the water's"
                                     " edge is NOT INSIDE the cover"
                                     " - the cover is always the larger"
                                     " of the two")
                             1)))))))
  (spachk:res rows nil))

;;; --- 4. the dimensions --------------------------------------------------

;; Every dimension: right layer, right style, and does its measurement
;; agree with the distance between its own definition points?
(defun spachk:audit-dims (dims covdim watdim / rows ents e m d p1 p2 sty want)
  (setq rows nil ents nil)
  (foreach e dims
    ;; layer
    (if (not (spachk:on-layer-p e spachk:*lay-dim*))
      (setq rows (append rows
                  (list (spachk:row
                          (strcat "Dim " (spachk:dxf 5 e) ": on layer "
                                  (spachk:layer e) ", should be "
                                  spachk:*lay-dim*)
                          1)))
            ents (cons e ents)))
    ;; style: a Water's Edge dim takes the 0.5 style, everything else
    ;; the cover style
    (setq want (if (spachk:has (spachk:dim-text e) spachk:*sfx-water*)
                   spachk:*ds-water* spachk:*ds-cover*)
          sty  (spachk:dim-style e))
    (if (and (/= sty "") (/= (strcase sty) (strcase want)))
      (setq rows (append rows
                  (list (spachk:row
                          (strcat "Dim " (spachk:dxf 5 e) ": style '"
                                  sty "', should be '" want "'")
                          1)))
            ents (cons e ents)))
    ;; does it measure what it spans?
    (if (spachk:linear-p e)
      (progn
        (setq p1 (car (spachk:dim-pts e))
              p2 (cadr (spachk:dim-pts e))
              m  (spachk:dim-meas e))
        (if (and p1 p2 m)
          (progn
            (setq d (distance p1 p2))
            (if (> (abs (- d m)) spachk:*meas-tol*)
              (setq rows (append rows
                          (list (spachk:row
                                  (strcat "Dim " (spachk:dxf 5 e)
                                          ": reads " (rtos m)
                                          " but spans " (rtos d)
                                          " - the dimension DISAGREES"
                                          " with its own points")
                                  1)))
                    ents (cons e ents))))))))
  (spachk:res rows (reverse ents)))

;; Every dimension belongs on spachk:*lay-dim*.  The per-dimension
;; audit says so one dimension at a time, in the report's DIMENSION
;; AUDIT column; this is the roster-wide verdict, and it carries the
;; suggestion to run CDIM over the strays.  It is the one dimension
;; check LITESPACHECKSCAN keeps -- it costs a layer read apiece, and a
;; sheet whose dimensions sit on the wrong layer plots wrong however
;; sound the dimensions themselves are.  The offending layers are
;; named, since that is what you need to go fix them.
(defun spachk:audit-dimlayer (dims / n off lays lay e s)
  (setq n 0 off 0 lays nil)
  (foreach e dims
    (if (entget e)
      (progn
        (setq n   (1+ n)
              lay (spachk:layer e))
        (if (/= (strcase lay) (strcase spachk:*lay-dim*))
          (progn
            (setq off (1+ off))
            (if (not (member (strcase lay) lays))
              (setq lays (cons (strcase lay) lays))))))))
  (cond
    ((= n 0)
     (spachk:res (list (spachk:row (strcat "Dimension layer: no dimensions"
                                           " in the selection")
                                   1))
                 nil))
    ((= off 0)
     (spachk:res (list (spachk:row (strcat "Dimension layer: all " (itoa n)
                                           " on " spachk:*lay-dim*)
                                   nil))
                 nil))
    (t
     (spachk:res (list (spachk:row
                         (strcat "Dimension layer: " (itoa off) " of "
                                 (itoa n) " NOT on layer "
                                 spachk:*lay-dim* " ("
                                 (spachk:join (reverse lays) ", ")
                                 ") - run " spachk:*dimfix-cmd*
                                 " to move them")
                         1))
                 nil))))

;; The roster: are the dimensions a finished spa sheet needs present,
;; and do the overalls read the outline's true size?
(defun spachk:audit-roster (dims cov wat / rows ents covn watn lapn bb
                                           m want e)
  (setq rows nil ents nil
        covn (spachk:dims-noted dims spachk:*sfx-cover*)
        watn (spachk:dims-noted dims spachk:*sfx-water*)
        lapn (spachk:dims-noted dims spachk:*sfx-lap*))
  ;; --- the cover's overalls
  (setq bb (if cov (cal:bbox-ent cov) nil))
  (cond
    ((null covn)
     (setq rows (append rows
                 (list (spachk:row
                         (strcat "Overalls: NO dimension carries the '"
                                 spachk:*sfx-cover* "' note")
                         1)))))
    (t
     (setq rows (append rows
                 (list (spachk:row
                         (strcat "Overalls: " (itoa (length covn))
                                 " dimension"
                                 (if (= 1 (length covn)) "" "s")
                                 " noted '" spachk:*sfx-cover* "'")
                         nil))))
     ;; each must read one of the cover's two extents
     (if bb
       (foreach e covn
         (setq m (spachk:dim-meas e))
         (if m
           (if (and (> (abs (- m (spachk:bw bb))) spachk:*meas-tol*)
                    (> (abs (- m (spachk:bh bb))) spachk:*meas-tol*))
             (setq rows (append rows
                         (list (spachk:row
                                 (strcat "Overall " (spachk:dxf 5 e)
                                         ": reads " (rtos m)
                                         " but the cover measures "
                                         (rtos (spachk:bw bb)) " x "
                                         (rtos (spachk:bh bb)))
                                 1)))
                   ents (cons e ents))))))))
  ;; --- the water's edge overalls, when there is a water's edge
  (if wat
    (if (null watn)
      (setq rows (append rows
                  (list (spachk:row
                          (strcat "Water's edge: drawn, but NO dimension"
                                  " carries the '" spachk:*sfx-water*
                                  "' note")
                          1))))
      (setq rows (append rows
                  (list (spachk:row
                          (strcat "Water's edge: " (itoa (length watn))
                                  " dimension"
                                  (if (= 1 (length watn)) "" "s")
                                  " noted '" spachk:*sfx-water* "'")
                          nil))))))
  ;; --- the overlap dimension, required only when both are drawn
  (if (and cov wat)
    (if (null lapn)
      (setq rows (append rows
                  (list (spachk:row
                          (strcat "Overlap: both outlines are drawn but"
                                  " there is NO '" spachk:*sfx-lap*
                                  "' dimension")
                          1))))
      (progn
        (setq m (spachk:dim-meas (car lapn))
              want (if (and (cal:bbox-ent cov) (cal:bbox-ent wat))
                       (* 0.5 (- (spachk:bw (cal:bbox-ent cov))
                                 (spachk:bw (cal:bbox-ent wat))))
                       nil))
        (if (and m want (> (abs (- m want)) spachk:*meas-tol*))
          (setq rows (append rows
                      (list (spachk:row
                              (strcat "Overlap: reads " (rtos m)
                                      " but the cover laps the water's"
                                      " edge by " (rtos want))
                              1)))
                ents (cons (car lapn) ents))
          (setq rows (append rows
                      (list (spachk:row
                              (strcat "Overlap: " (rtos m) ", OK")
                              nil))))))))
  (spachk:res rows (reverse ents)))

;; The overalls' standoffs -- SPA puts the across dim 2 ft above the
;; cover and the up dim 3 ft to its left.
(defun spachk:audit-standoff (covn cov / rows bb e loc dx dy)
  (setq rows nil)
  (if (and cov covn (setq bb (cal:bbox-ent cov)))
    (foreach e covn
      (setq loc (spachk:dim-loc e))
      (if loc
        (progn
          (setq dy (- (cadr loc) (cadadr bb))     ; above the top
                dx (- (caar bb) (car loc)))       ; left of the left edge
          (cond
            ;; above the cover: the across dim
            ((> dy 0.0)
             (if (> (abs (- dy spachk:*topoff*)) spachk:*off-tol*)
               (setq rows (append rows
                           (list (spachk:row
                                   (strcat "Overall " (spachk:dxf 5 e)
                                           ": stands " (rtos dy)
                                           " above the cover, SPA puts it "
                                           (rtos spachk:*topoff*))
                                   1))))))
            ;; left of the cover: the up dim
            ((> dx 0.0)
             (if (> (abs (- dx spachk:*dimoff*)) spachk:*off-tol*)
               (setq rows (append rows
                           (list (spachk:row
                                   (strcat "Overall " (spachk:dxf 5 e)
                                           ": stands " (rtos dx)
                                           " left of the cover, SPA puts it "
                                           (rtos spachk:*dimoff*))
                                   1)))))))))))
  (spachk:res rows nil))

;;; --- 5. the hinges ------------------------------------------------------

;; A hinge's label: the MTEXT on the TEXT layer nearest its line.
(defun spachk:hinge-label (hng labels / best bestd p q d e bb)
  (setq bb (cal:bbox-ent hng))
  (if bb
    (progn
      (setq p (list (* 0.5 (+ (caar bb) (caadr bb)))
                    (* 0.5 (+ (cadar bb) (cadadr bb)))))
      (foreach e labels
        (setq q (spachk:dxf 10 e)
              d (distance (list (car p) (cadr p)) (list (car q) (cadr q))))
        (if (or (null bestd) (< d bestd)) (setq bestd d best e)))))
  (if best (spachk:dxf 1 best)))

(defun spachk:audit-hinges (ss cov grade taper / rows ents hngs labels n xs
                                                 row opts allowed fw fl
                                                 sorted e bb want got
                                                 maxrun maxpiece prev
                                                 allvel hw h r k nm vd lvl)
  (setq rows nil ents nil
        hngs (vl-remove-if-not
               '(lambda (e) (= (spachk:etype e) "LINE"))
               (spachk:loose-ents ss spachk:*lay-cover*))
        labels (vl-remove-if-not
                 '(lambda (e) (spachk:on-layer-p e spachk:*lay-text*))
                 (spachk:ents-of-type ss "MTEXT")))
  (if (null hngs)
    (spachk:res
      (list (spachk:row "Hinges: none drawn on layer COVER" 1)) nil)
    (progn
      ;; west to east
      (setq sorted (vl-sort hngs
                     '(lambda (a b)
                        (< (car (spachk:dxf 10 a)) (car (spachk:dxf 10 b))))))
      (setq n (1+ (length sorted))
            allvel (= grade "THERMOLIGHT"))
      ;; --- the piece count against the taper
      (setq row nil)
      (foreach r spachk:*foamtab*
        (if (and (not row) (= (car r) grade) (= (cadr r) taper))
          (setq row r)))
      (if (not row)
        (foreach r spachk:*foamtab*
          (if (and (not row) (= (car r) "STANDARD") (= (cadr r) taper))
            (setq row r))))
      (if row
        (setq opts (caddr row) allowed (cadddr row))
        (setq opts (list (cons 48.0 96.0)) allowed (list 2 3 4 5)))
      (setq fw (car (car opts)) fl (cdr (car opts)))
      (setq rows (append rows
                  (list (spachk:row
                          (strcat "Hinges: " (itoa (length sorted))
                                  " drawn, so " (itoa n) " pieces ("
                                  (spachk:gradeshort grade) " " taper ")")
                          nil))))
      (if (not (spachk:hallow n allowed))
        (setq rows (append rows
                    (list (spachk:row
                            (strcat "Pieces: " (itoa n)
                                    " is NOT an acceptable count for "
                                    (spachk:gradeshort grade) " " taper)
                            1)))))
      ;; --- hinge runs against the foam length.  A hinge's run is its
      ;;     own length, so this stands whether or not the cover outline
      ;;     is there to be measured -- and it must, because the
      ;;     hardware advice below reads maxrun and a nil would take the
      ;;     whole audit down over the one drawing most in need of it.
      (setq maxrun 0.0)
      (foreach e sorted
        (setq maxrun (max maxrun
                          (abs (- (cadr (spachk:dxf 11 e))
                                  (cadr (spachk:dxf 10 e)))))))
      (if (and fl (> maxrun (+ fl 0.01)))
        (setq rows (append rows
                    (list (spachk:row
                            (strcat "Foam length: longest hinge "
                                    (rtos maxrun) " exceeds the "
                                    (rtos fl) " sheet")
                            1))))
        (setq rows (append rows
                    (list (spachk:row
                            (strcat "Foam length: longest hinge "
                                    (rtos maxrun)
                                    (if fl
                                        (strcat " within " (rtos fl) ", OK")
                                        (strcat " - Thermo-Light length"
                                                " N/A, verify")))
                            (if fl nil 2))))))
      ;; --- piece widths against the foam width.  This one DOES need
      ;;     the cover: a piece is bounded by the outline's edges.
      (if (and cov (setq bb (cal:bbox-ent cov)))
        (progn
          (setq maxpiece 0.0 prev (caar bb))
          (foreach e sorted
            (setq maxpiece (max maxpiece (- (car (spachk:dxf 10 e)) prev))
                  prev (car (spachk:dxf 10 e))))
          (setq maxpiece (max maxpiece (- (caadr bb) prev)))
          (if (> maxpiece (+ fw 0.01))
            (setq rows (append rows
                        (list (spachk:row
                                (strcat "Foam width: widest piece "
                                        (rtos maxpiece) " exceeds the "
                                        (rtos fw) " sheet")
                                1))))
            (setq rows (append rows
                        (list (spachk:row
                                (strcat "Foam width: widest piece "
                                        (rtos maxpiece) " within "
                                        (rtos fw) ", OK")
                                nil))))))
        (setq rows (append rows
                    (list (spachk:row
                            (strcat "Foam width: not checked - no cover"
                                    " outline to measure the pieces against")
                            2)))))
      ;; --- the arrangement against the chart
      (setq want (spachk:hingetypes n allvel)
            got (mapcar '(lambda (e)
                           (if (spachk:has (spachk:hinge-label e labels)
                                           "Velcro")
                               "V" "H"))
                        sorted))
      (if (equal want got)
        (setq rows (append rows
                    (list (spachk:row
                            (strcat "Arrangement: "
                                    (spachk:join got " ") ", matches the"
                                    " Hinge Arrangement Chart")
                            nil))))
        (setq rows (append rows
                    (list (spachk:row
                            (strcat "Arrangement: reads "
                                    (spachk:join got " ")
                                    " but the chart says "
                                    (spachk:join want " ")
                                    " for " (itoa n) " pieces")
                            1)))
              ents (append ents sorted)))
      ;; --- every hinge must be labelled
      (setq k 0)
      (foreach e sorted
        (setq k (1+ k))
        (if (null (spachk:hinge-label e labels))
          (setq rows (append rows
                      (list (spachk:row
                              (strcat "Hinge " (itoa k)
                                      ": NO label on layer "
                                      spachk:*lay-text*)
                              1)))
                ents (cons e ents))))
      ;; --- hardware called for by the longest hinge (advice)
      (setq hw nil)
      (foreach h spachk:*hardtab*
        (if (and (not hw) (= (car h) grade)) (setq hw h)))
      (if hw
        (progn
          (setq k 0)
          (foreach nm (list "Velcro hinges" "Double C channel"
                            "Hold down kit")
            (setq vd (spachk:hardverdict (nth (1+ k) hw) maxrun))
            ;; only a YES is advice worth colouring -- a "no" is the
            ;; ordinary answer, and three cyan lines saying nothing is
            ;; needed would bury the one that says something is
            (setq rows (append rows
                        (list (spachk:row
                                (strcat nm ": "
                                        (if (car vd) "YES" "no")
                                        " - " (cdr vd))
                                (if (car vd) 2 nil)))))
            (setq k (1+ k)))))
      (spachk:res rows ents))))

;;; --- 6. the title block -------------------------------------------------

(defun spachk:audit-title (ss / bb s)
  (setq bb (spachk:border-box ss)
        s  (spachk:title-verdict bb))
  (spachk:res
    (list (spachk:row (strcat "Title block: " s)
                      (if (spachk:has s "OK") nil 1)))
    nil))

;;; --- feet-and-inch text -------------------------------------------------
;;;  A distance written in feet must state its inches too: 5' is wrong,
;;;  5'-0" (or 5'-0'') is right, and a plain 40" is right as it stands.

;; A FEET MARK is an apostrophe standing straight after a DIGIT, and
;; that is what keeps prose out of this: "Water's Edge", "Owner's" and
;; "don't" are possessives, not measurements, and are never flagged.
;; Two apostrophes together are the inch mark AutoCAD text often uses
;; in place of ", so 5'-0'' closes exactly as 5'-0" does.
;;
;; T when some feet mark in s is never closed by an inch mark before
;; the next feet mark or the end of the string -- so "5' and 7'-0"" is
;; caught on its first value while "3'-2"" passes.
(defun spachk:feet-open-p (s / lst n i c prev open found)
  (setq lst   (vl-string->list s)
        n     (length lst)
        i     0
        prev  0
        open  nil
        found nil)
  (while (< i n)
    (setq c (nth i lst))
    (cond
      ((= c 34)                                    ; " closes it
       (setq open nil i (1+ i)))
      ((and (= c 39) (< (1+ i) n) (= (nth (1+ i) lst) 39))
       (setq open nil i (+ i 2)))                  ; '' closes it too
      ((and (= c 39) (>= prev 48) (<= prev 57))    ; digit then ' = feet
       (if open (setq found T))                    ; the one before never closed
       (setq open T i (1+ i)))
      (t (setq i (1+ i))))
    (setq prev (nth (1- i) lst)))
  (or found open))

(defun spachk:clip (s n)
  (if (> (strlen s) n) (strcat (substr s 1 n) "...") s))

;; MTEXT reads \, { and } as formatting, so a snippet quoted out of the
;; drawing has them blanked before it goes anywhere near the report.
(defun spachk:mtsafe (s)
  (vl-list->string
    (mapcar '(lambda (c) (if (member c '(92 123 125)) 32 c))
            (vl-string->list s))))

;; The text an entity carries: TEXT and ATTRIB keep it in group 1,
;; MTEXT spills the overflow into group 3 chunks ahead of that.
(defun spachk:ent-text (ent / ed g head tail)
  (setq ed (entget ent) head "" tail "")
  (foreach g ed
    (cond ((= 3 (car g)) (setq head (strcat head (cdr g))))
          ((= 1 (car g)) (setq tail (cdr g)))))
  (strcat head tail))

;; Every text box in the selection: TEXT and MTEXT, plus the ATTRIB
;; values on blocks -- the parts of a block someone types into.  Text
;; baked into a block DEFINITION is left alone: it reads the same on
;; every insert and is not fixable from this drawing.
(defun spachk:text-items (ss / i e ed et out a ad)
  (setq i 0)
  (if ss
    (repeat (sslength ss)
      (setq e  (ssname ss i)
            i  (1+ i)
            ed (entget e)
            et (if ed (cdr (assoc 0 ed))))
      (cond
        ((member et '("TEXT" "MTEXT"))
         (setq out (cons (cons (cdr (assoc 5 ed)) (spachk:ent-text e)) out)))
        ((and (= et "INSERT") (assoc 66 ed) (= 1 (cdr (assoc 66 ed))))
         (setq a (entnext e))
         (while (and a (setq ad (entget a)) (= "ATTRIB" (cdr (assoc 0 ad))))
           (setq out (cons (cons (cdr (assoc 5 ad)) (spachk:ent-text a)) out)
                 a   (entnext a)))))))
  (reverse out))

;; The verdict over every text box, then one row per offender.  The
;; report itself is skipped: SPACHECK writes it onto its own layer, but
;; a rerun reads the drawing before clearing the old one.
(defun spachk:audit-units (ss / items it s n bad rows)
  (setq items (spachk:text-items ss) n 0 bad 0 rows nil)
  (foreach it items
    (setq s (cdr it))
    (if (and s (/= s ""))
      (progn
        (setq n (1+ n))
        (if (spachk:feet-open-p s)
          (setq bad  (1+ bad)
                rows (append rows
                       (list (spachk:row
                               (strcat "Text " (car it) ": \""
                                       (spachk:mtsafe (spachk:clip s 40))
                                       "\" gives feet with NO INCHES"
                                       " - write it 5'-0\" not 5'")
                               1))))))))
  (spachk:res
    (cons (spachk:row
            (cond
              ((= n 0) "Feet & inches: no text in the selection")
              ((= bad 0) (strcat "Feet & inches: all " (itoa n) " text item"
                                 (if (= 1 n) "" "s") " OK"))
              (t (strcat "Feet & inches: " (itoa bad) " of " (itoa n)
                         " text item" (if (= 1 n) "" "s")
                         " give feet with NO INCHES"
                         " - write 5'-0\" not 5'")))
            (if (> bad 0) 1 nil))
          rows)
    nil))

;;; --- the Tech Title date ------------------------------------------------
;;;  The sheet's Tech Title block carries a Date attribute, and it must
;;;  read TODAY in MM/DD/YYYY form.  A sheet going out under an old date
;;;  is the mistake this catches: the drawing was reworked and the title
;;;  block never caught up.

(defun spachk:pad2 (n)
  (if (< n 10) (strcat "0" (itoa n)) (itoa n)))

;; uppercase with every non-alphanumeric dropped, so "Tech Title"
;; matches a block actually named "TECHTITLE" or "Tech-Title"
(defun spachk:squash (s)
  (vl-list->string
    (vl-remove nil
      (mapcar '(lambda (c)
                 (cond ((and (>= c 48) (<= c 57)) c)
                       ((and (>= c 65) (<= c 90)) c)
                       ((and (>= c 97) (<= c 122)) (- c 32))))
              (vl-string->list (if s s ""))))))

;; the block's effective name, so a dynamic block answers by the name
;; it was drawn from rather than its anonymous one
(defun spachk:block-name (ent / res)
  (setq res (vl-catch-all-apply
              'vla-get-EffectiveName
              (list (vlax-ename->vla-object ent))))
  (if (vl-catch-all-error-p res) (spachk:dxf 2 ent) res))

(defun spachk:ins-attrib (ent tag)
  (cdr (assoc (strcase tag) (spachk:attribs ent))))

;; a value may arrive labelled ("Date: 05/01/2024" or "Date = ..."),
;; so the date is whatever follows the last "=" and then the last ":"
(defun spachk:after-eq (s / p)
  (while (setq p (vl-string-search "=" s))
    (setq s (substr s (+ p 2))))
  s)

(defun spachk:datenorm (s)
  (spachk:aftercolon (spachk:after-eq (if s s ""))))

(defun spachk:all-digits-p (s / i n c ok)
  (setq n (strlen s) ok (> n 0) i 1)
  (while (and ok (<= i n))
    (setq c (ascii (substr s i 1)))
    (if (or (< c 48) (> c 57)) (setq ok nil))
    (setq i (1+ i)))
  ok)

(defun spachk:days-in-month (mo yr)
  (cond
    ((member mo '(1 3 5 7 8 10 12)) 31)
    ((member mo '(4 6 9 11)) 30)
    ((and (= 0 (rem yr 4)) (or (/= 0 (rem yr 100)) (= 0 (rem yr 400)))) 29)
    (t 28)))

(defun spachk:today-mdy ( / d)
  ;; (month day year) off the computer clock.  CDATE is
  ;; YYYYMMDD.HHMMSSmsec, decoded arithmetically so DIMZIN (which trims
  ;; rtos output) cannot mangle it.
  (setq d (fix (getvar "CDATE")))
  (list (rem (fix (/ d 100)) 100) (rem d 100) (fix (/ d 10000))))

(defun spachk:mdy-str (mdy)
  (strcat (spachk:pad2 (car mdy)) "/" (spachk:pad2 (cadr mdy)) "/"
          (itoa (caddr mdy))))

;; nil when raw is today's date written MM/DD/YYYY; otherwise a short
;; string saying what is wrong with it.
(defun spachk:date-verdict (raw / s mo dd yr now)
  (setq s (cal:trim (spachk:datenorm raw)))
  (cond
    ((= s "") "is blank - expected MM/DD/YYYY")
    ((or (/= (strlen s) 10)
         (/= (substr s 3 1) "/")
         (/= (substr s 6 1) "/")
         (not (spachk:all-digits-p (substr s 1 2)))
         (not (spachk:all-digits-p (substr s 4 2)))
         (not (spachk:all-digits-p (substr s 7 4))))
     (strcat "'" s "' is not in MM/DD/YYYY format - expected MM/DD/YYYY"))
    (t
     (setq mo (atoi (substr s 1 2))
           dd (atoi (substr s 4 2))
           yr (atoi (substr s 7 4)))
     (cond
       ((or (< mo 1) (> mo 12))
        (strcat "'" s "' - " (substr s 1 2)
                " is not a month (01-12) - expected MM/DD/YYYY"))
       ((or (< dd 1) (> dd (spachk:days-in-month mo yr)))
        (strcat "'" s "' - " (substr s 4 2)
                " is not a valid day for that month - expected MM/DD/YYYY"))
       ((progn (setq now (spachk:today-mdy))
               (not (and (= mo (car now)) (= dd (cadr now))
                         (= yr (caddr now)))))
        (strcat "'" s "' is NOT TODAY'S DATE (" (spachk:mdy-str now)
                ") - update it"))
       (t nil)))))

;; The Tech Title block: the first INSERT whose name carries it, looked
;; for in the selection and then across the drawing, since the title
;; block sits outside the area someone highlights as often as not.
(defun spachk:find-title (ss / pat i e out ss2)
  (setq pat (strcat "*" (spachk:squash spachk:*techtitle-block*) "*") i 0)
  (if ss
    (repeat (sslength ss)
      (setq e (ssname ss i) i (1+ i))
      (if (and (null out) (entget e) (= "INSERT" (spachk:etype e))
               (wcmatch (spachk:squash (spachk:block-name e)) pat))
        (setq out e))))
  (if (null out)
    (progn
      (setq ss2 (ssget "_X" '((0 . "INSERT"))) i 0)
      (if ss2
        (repeat (sslength ss2)
          (setq e (ssname ss2 i) i (1+ i))
          (if (and (null out)
                   (wcmatch (spachk:squash (spachk:block-name e)) pat))
            (setq out e))))))
  out)

;; With no Tech Title in reach there is nothing to read, and that is
;; said plainly rather than flagged -- a spa sheet may well be checked
;; on its own, away from the sheet it will sit on.
(defun spachk:audit-date (ss / blk raw bad)
  (setq blk (spachk:find-title ss))
  (if (null blk)
    (spachk:res
      (list (spachk:row (strcat "Tech Title: no '" spachk:*techtitle-block*
                                "' block in reach - date NOT CHECKED")
                        nil))
      nil)
    (progn
      (setq raw (spachk:ins-attrib blk spachk:*date-tag*)
            bad (if raw
                  (spachk:date-verdict raw)
                  "is missing from the block - expected MM/DD/YYYY"))
      (spachk:res
        (list (spachk:row
                (if bad
                  (strcat "Tech Title: " spachk:*date-tag* " " bad)
                  (strcat "Tech Title: " spachk:*date-tag* " = '"
                          (cal:trim (spachk:datenorm raw)) "' - OK"))
                (if bad 1 nil)))
        nil))))

;;; ======================================================================
;;;  RUNNING THE AUDIT
;;; ======================================================================

;; Everything, in report order, each section under its heading row.
;; The mechanical per-dimension audit (layer, style, span agreement)
;; is DIMCHECK's ground, so its rows come back separately for the
;; report's second column - and a lite run skips it altogether.
;; Returns (main-rows dim-rows flagged-entities).
(defun spachk:audit (ss lite / rows drows ents blk att g tp cov wat covo
                             wato dims covn r)
  (setq rows nil drows nil ents nil)

  ;; 1 -- the block
  (setq rows (append rows (list (spachk:row "THE DETAILS BLOCK" 3))))
  (setq r (spachk:audit-block ss)
        rows (append rows (spachk:res-rows r))
        ents (append ents (spachk:res-ents r)))
  (setq blk (spachk:find-details ss)
        att (if blk (spachk:attribs blk) nil)
        g   (spachk:gradenorm (if (cdr (assoc "GRADE" att))
                                  (spachk:aftercolon (cdr (assoc "GRADE" att)))
                                  nil))
        tp  (if (cdr (assoc "TAPER" att))
                (spachk:tapernorm (spachk:aftercolon (cdr (assoc "TAPER" att))))
                nil))
  (if (and (= g "THERMOLIGHT") (null tp)) (setq tp "1-3/8"))

  ;; 2 -- the cover outline
  (setq rows (append rows (list (spachk:row "THE OUTLINES" 3))))
  (setq r (spachk:audit-outline ss spachk:*lay-cover* "Cover outline" t)
        rows (append rows (spachk:res-rows r))
        ents (append ents (spachk:res-ents r))
        covo (spachk:outline-ents ss spachk:*lay-cover*)
        cov  (if (= 1 (length covo)) (car covo) nil))

  ;; 3 -- the water's edge outline
  (setq r (spachk:audit-outline ss spachk:*lay-water* "Water's edge" nil)
        rows (append rows (spachk:res-rows r))
        ents (append ents (spachk:res-ents r))
        wato (spachk:outline-ents ss spachk:*lay-water*)
        wat  (if (= 1 (length wato)) (car wato) nil))

  (setq r (spachk:audit-nesting cov wat)
        rows (append rows (spachk:res-rows r)))

  ;; 4 -- the dimensions.  The per-dimension audit fills the second
  ;; column; the roster and standoffs are SPA's own rules and stay on
  ;; the main sheet.
  (setq rows (append rows (list (spachk:row "THE OVERALLS" 3))))
  (setq dims (spachk:dims ss))
  ;; the dimension-layer verdict runs in every mode, lite included
  (setq r (spachk:audit-dimlayer dims)
        rows (append rows (spachk:res-rows r)))
  (if (not lite)
    (setq r     (spachk:audit-dims dims cov wat)
          drows (spachk:res-rows r)
          ents  (append ents (spachk:res-ents r))))
  (setq r (spachk:audit-roster dims cov wat)
        rows (append rows (spachk:res-rows r))
        ents (append ents (spachk:res-ents r)))
  (setq covn (spachk:dims-noted dims spachk:*sfx-cover*)
        r    (spachk:audit-standoff covn cov)
        rows (append rows (spachk:res-rows r)))

  ;; 5 -- the hinges (only meaningful with a taper)
  (setq rows (append rows (list (spachk:row "THE HINGES" 3))))
  (if tp
    (progn
      (setq r (spachk:audit-hinges ss cov g tp)
            rows (append rows (spachk:res-rows r))
            ents (append ents (spachk:res-ents r))))
    (setq rows (append rows
                (list (spachk:row
                        "Hinges: not checked - no taper to check against"
                        1)))))

  ;; 6 -- the text boxes: feet must carry inches (every mode, lite too)
  (setq rows (append rows (list (spachk:row "TEXT & UNITS" 3))))
  (setq r (spachk:audit-units ss)
        rows (append rows (spachk:res-rows r)))

  ;; 7 -- the Tech Title date (every mode, lite too)
  (setq rows (append rows (list (spachk:row "THE TECH TITLE" 3))))
  (setq r (spachk:audit-date ss)
        rows (append rows (spachk:res-rows r)))

  ;; 8 -- the title block
  (setq rows (append rows (list (spachk:row "THE TITLE BLOCK" 3))))
  (setq r (spachk:audit-title ss)
        rows (append rows (spachk:res-rows r)))

  (list rows drows ents))

;;; -------------------- the report --------------------------------------

;; The whole report: the SPA-specific findings on the MAIN sheet and,
;; unless lite, the per-dimension audit in a DIMENSION AUDIT column to
;; its right - the DIMCHECK-style pass, set apart so the spa verdicts
;; lead.  Returns (problem-count advisory-count), over both columns.
(defun spachk:write-report (rows drows bb readonly lite
                            / nlin ndim ref h ins ins2 txt r nbad nadv)
  (cal:ensure-layer spachk:*report-layer* spachk:*report-color*)
  (setq nbad 0 nadv 0)
  (foreach r (append rows drows)
    (cond ((spachk:lvl-p r 1) (setq nbad (1+ nbad)))
          ((spachk:lvl-p r 2) (setq nadv (1+ nadv)))))
  ;; height: scale the sheet to the drawing, as the siblings do.  The
  ;; head is title (1.5) + date + verdict (1.2) + legend; a heading
  ;; row is one line plus the 0.4 gap above it.  The dimension column
  ;; is counted the same way, and the taller column drives the height.
  (setq nlin 4.5)
  (foreach r rows
    (setq nlin (+ nlin (cond ((spachk:lvl-p r 3) 1.4)
                             ((spachk:row-lvl r) 1.0)
                             (t spachk:*green-scale*)))))
  (setq ndim (+ 2.5 (if drows (length drows) 1)))
  (if (and (not lite) (> ndim nlin)) (setq nlin ndim))
  (if (and bb (> (max (spachk:bw bb) (spachk:bh bb)) 1.0e-8))
    (progn
      (setq ref (max (spachk:bh bb) (* 0.25 (spachk:bw bb)))
            h   (/ ref (* 1.66 nlin)))
      (if (> h (/ ref 30.0))  (setq h (/ ref 30.0)))
      (if (< h (/ ref 200.0)) (setq h (/ ref 200.0))))
    (setq h 2.5))
  (setq ins (if bb
                (list (+ (caadr bb) (* 0.05 (max (spachk:bw bb) 1.0)))
                      (cadadr bb) 0.0)
                (list 0.0 0.0 0.0)))
  ;; the head: a large title, the date and version small under it, a
  ;; verdict line -- red with the problem count, cyan when only advice,
  ;; plain ALL CLEAR otherwise -- then the colour legend.  The verdict
  ;; is wrapped in its height code first so it never renders as (or
  ;; counts among) the finding rows, which start with a colour code.
  (setq txt (strcat (spachk:big (cond ((and readonly lite)
                                       "LITESPACHECKSCAN REPORT")
                                      (readonly "SPACHECKSCAN REPORT")
                                      (t "SPACHECK REPORT")))
                    "\\P"
                    (spachk:small (strcat (cal:datestr)
                                          "  -  SPACHECK "
                                          *spacheck-version*))
                    "\\P"
                    "{\\H1.2x;"
                    (cond
                      ((> nbad 0)
                       (spachk:red
                         (strcat (itoa nbad) " PROBLEM"
                                 (if (= 1 nbad) "" "S")
                                 (if (> nadv 0)
                                     (strcat ", " (itoa nadv) " ADVISOR"
                                             (if (= 1 nadv) "Y" "IES"))
                                     ""))))
                      ((> nadv 0)
                       (spachk:cyan
                         (strcat "ALL CLEAR - " (itoa nadv) " advisor"
                                 (if (= 1 nadv) "y" "ies"))))
                      (t "ALL CLEAR - every check passed"))
                    "}"
                    "\\P"
                    (spachk:small
                      (strcat (if readonly
                                  "Read-only scan - nothing in the drawing was changed.  "
                                  "")
                              (if lite
                                  "Lite: the dimension audit was skipped - run SPACHECKSCAN or DIMCHECK for it.  "
                                  "")
                              "Problems in " (spachk:red "red")
                              ", advice in " (spachk:cyan "cyan")
                              "; lines that checked out are smaller."))))
  (foreach r rows
    (setq txt (strcat txt "\\P" (spachk:render r))))
  (cal:mtext ins h (* spachk:*report-chars* h) txt spachk:*report-layer*)
  ;; the DIMENSION AUDIT column, to the right of the main sheet
  (if (not lite)
    (progn
      (setq ins2 (list (+ (car ins) (* (+ spachk:*report-chars* 2.0) h))
                       (cadr ins) 0.0)
            txt  (strcat "{\\H1.2x;DIMENSION AUDIT}"
                         "\\P"
                         (spachk:small
                           (strcat "Each dimension against its layer, its"
                                   " style and its own span - DIMCHECK's"
                                   " ground, kept off the main sheet."))))
      (if drows
        (foreach r drows
          (setq txt (strcat txt "\\P" (spachk:render r))))
        (setq txt (strcat txt "\\P"
                          (spachk:small "  Every dimension checks out."))))
      (cal:mtext ins2 h (* spachk:*report-chars* h) txt
                    spachk:*report-layer*)))
  (list nbad nadv))

;;; -------------------- marking (SPACHECK only) -------------------------

(defun spachk:regapp ()
  (if (not (tblsearch "APPID" "SPACHECK")) (regapp "SPACHECK")))

;; Remember the entity's own colour in xdata so SPACHECKRESCUE can put
;; it back even after a crash; an existing stash (from an interrupted
;; run - the TRUE original) is never overwritten.
(defun spachk:stash-color (ent col / ed cur)
  (spachk:regapp)
  (setq ed  (entget ent '("SPACHECK"))
        cur (cdr (assoc 62 (entget ent))))
  (if (and ed (not (assoc -3 ed)))
    (entmod (append ed (list (list -3 (list "SPACHECK"
                                            '(1000 . "COLOR")
                                            (cons 1071 (if cur cur 256))))))))
  ;; now recolour it
  (setq ed (entget ent))
  (entmod (if (assoc 62 ed)
              (subst (cons 62 col) (assoc 62 ed) ed)
              (append ed (list (cons 62 col)))))
  (entupd ent))

;; Put a stashed colour back and drop the xdata.  T when it did.
(defun spachk:unstash (ent / ed xd old)
  (setq ed (entget ent '("SPACHECK"))
        xd (if (assoc -3 ed) (cdadr (assoc -3 ed)) nil))
  (if xd
    (progn
      (setq old (cdr (assoc 1071 xd)))
      (if old
        (progn
          (setq ed (entget ent))
          (entmod (if (= old 256)
                      (if (assoc 62 ed)
                          (vl-remove (assoc 62 ed) ed)
                          ed)
                      (if (assoc 62 ed)
                          (subst (cons 62 old) (assoc 62 ed) ed)
                          (append ed (list (cons 62 old))))))))
      (setq ed (entget ent '("SPACHECK")))
      (entmod (subst (list -3 (list "SPACHECK")) (assoc -3 ed) ed))
      (entupd ent)
      T)))

(defun spachk:zoom-ent (ent / bb p1 p2 m)
  (if (setq bb (cal:bbox-ent ent))
    (progn
      (setq m  (* spachk:*zoom-margin*
                  (max (spachk:bw bb) (spachk:bh bb) 1.0))
            p1 (list (- (caar bb) m) (- (cadar bb) m))
            p2 (list (+ (caadr bb) m) (+ (cadadr bb) m)))
      (command "_.ZOOM" "_Window" p1 p2))))

;;; -------------------- asking ------------------------------------------
;;;  The section-4 helpers, embedded under this file's own prefix.

;;; -------------------- sysvars -----------------------------------------

;;; ======================================================================
;;;  COMMANDS
;;; ======================================================================

(defun c:SPACHECKVER ()
  (princ (strcat "\nSPACHECK " *spacheck-version*))
  (princ (strcat "\n  spa title block: " (rtos spachk:*title-frac* 2 2)
                 "x the liner block = "
                 (rtos (* spachk:*title-frac* spachk:*liner-w*)) " x "
                 (rtos (* spachk:*title-frac* spachk:*liner-h*))))
  (princ))

;;; --- SPACHECKSCAN / LITESPACHECKSCAN: the audits, read-only ------------
;;;  The lite scan is the same audits minus the per-dimension pass,
;;;  for a drawing DIMCHECK already went over.

(defun c:SPACHECKSCAN () (spachk:scan nil))

(defun c:LITESPACHECKSCAN () (spachk:scan T))

(defun spachk:scan (lite / *error* oldecho name ss res rows drows bb ents n)
  (setq name (if lite "LITESPACHECKSCAN" "SPACHECKSCAN"))
  (defun *error* (msg)
    (if oldecho (setvar "CMDECHO" oldecho))
    (if (and msg (not (wcmatch (strcase msg)
                               "*BREAK*,*CANCEL*,*QUIT*,*EXIT*")))
      (princ (strcat "\n" name " error: " msg)))
    (princ))
  (prompt (strcat "\nHighlight the spa drawing and its "
                  spachk:*details-block*
                  " block to " name " (Enter = whole drawing): "))
  (setq ss (ssget))
  (if (null ss) (setq ss (ssget "_X")))
  (if (null ss)
    (prompt "\nNothing to scan.")
    (progn
      (setq oldecho (getvar "CMDECHO"))
      (setvar "CMDECHO" 0)
      (setq res   (spachk:audit ss lite)
            rows  (car res)
            drows (cadr res)
            ents  (caddr res)
            bb    (spachk:bbox-of (spachk:outline-ents ss spachk:*lay-cover*))
            n     (spachk:write-report rows drows bb t lite))
      (setvar "CMDECHO" oldecho)
      (princ (strcat "\n--- " name " complete (read-only) ---"
                     "\n" (itoa (car n)) " problem"
                     (if (= 1 (car n)) "" "s") ", "
                     (itoa (cadr n)) " advisor"
                     (if (= 1 (cadr n)) "y" "ies")
                     (if lite
                         "\nLite: the dimension audit was skipped."
                         "")
                     "\nReport written on layer " spachk:*report-layer*
                     "; nothing else was changed."))))
  (princ))

;;; --- SPACHECK: the audits, then a walk of what they flagged ------------

(defun c:SPACHECK ( / *error* oldecho undo-open ss res rows drows ents bb n
                      e k tot ans marked)
  (defun *error* (msg)
    (cal:sysrestore)
    (if undo-open (command "_.UNDO" "_End"))
    (if (and msg (not (wcmatch (strcase msg)
                               "*BREAK*,*CANCEL*,*QUIT*,*EXIT*")))
      (princ (strcat "\nSPACHECK error: " msg)))
    (princ))
  (prompt (strcat "\nHighlight the spa drawing and its "
                  spachk:*details-block*
                  " block to SPACHECK (Enter = whole drawing): "))
  (setq ss (ssget))
  (if (null ss) (setq ss (ssget "_X")))
  (if (null ss)
    (prompt "\nNothing to check.")
    (progn
      (cal:syssave '("OSMODE" "CMDECHO" "CLAYER"))
      (setq oldecho (getvar "CMDECHO"))
      (setvar "CMDECHO" 0)
      (command "_.UNDO" "_Begin")
      (setq undo-open T)
      (setq res   (spachk:audit ss nil)
            rows  (car res)
            drows (cadr res)
            ents  (caddr res)
            bb    (spachk:bbox-of (spachk:outline-ents ss spachk:*lay-cover*)))
      ;; walk what was flagged, one at a time
      (setq tot (length ents) k 0 marked 0)
      (if (> tot 0)
        (progn
          (princ (strcat "\n" (itoa tot) " item"
                         (if (= 1 tot) "" "s")
                         " to look at, one at a time."))
          (foreach e ents
            (setq k (1+ k))
            (if (entget e)
              (progn
                (spachk:zoom-ent e)
                (setq ans (cal:askkw
                            (strcat "  Item " (itoa k) " of " (itoa tot)
                                    " - mark it as wrong?")
                            "Yes No Skip" "Yes/No/Skip" "No" nil))
                (cond
                  ((= ans "Yes")
                   (spachk:stash-color e spachk:*flag-color*)
                   (setq marked (1+ marked)))
                  ((= ans "Skip") (setq k tot))))))))
      (setq n (spachk:write-report rows drows bb nil nil))
      (command "_.ZOOM" "_Extents")
      (command "_.UNDO" "_End")
      (setq undo-open nil)
      (setvar "CMDECHO" oldecho)
      (cal:sysrestore)
      (princ (strcat "\n--- SPACHECK complete ---"
                     "\n" (itoa (car n)) " problem"
                     (if (= 1 (car n)) "" "s") ", "
                     (itoa (cadr n)) " advisor"
                     (if (= 1 (cadr n)) "y" "ies")
                     "\n" (itoa marked) " item"
                     (if (= 1 marked) "" "s") " marked red"
                     "\nReport written on layer " spachk:*report-layer*
                     ".  SPACHECKRESCUE puts the colours back."))))
  (princ))

;;; --- SPACHECKRESCUE: put every colour back -----------------------------

(defun c:SPACHECKRESCUE ( / *error* oldecho ss i e n)
  (defun *error* (msg)
    (if oldecho (setvar "CMDECHO" oldecho))
    (if (and msg (not (wcmatch (strcase msg)
                               "*BREAK*,*CANCEL*,*QUIT*,*EXIT*")))
      (princ (strcat "\nSPACHECKRESCUE error: " msg)))
    (princ))
  (setq oldecho (getvar "CMDECHO"))
  (setvar "CMDECHO" 0)
  (setq ss (ssget "_X") i 0 n 0)
  (if ss
    (repeat (sslength ss)
      (setq e (ssname ss i) i (1+ i))
      (if (spachk:unstash e) (setq n (1+ n)))))
  ;; and the report itself
  (setq ss (ssget "_X" (list (cons 8 spachk:*report-layer*))) i 0)
  (if ss
    (repeat (sslength ss)
      (entdel (ssname ss i))
      (setq i (1+ i))))
  (setvar "CMDECHO" oldecho)
  (princ (strcat "\nSPACHECKRESCUE: " (itoa n) " colour"
                 (if (= 1 n) "" "s") " put back, report removed."))
  (princ))

;;; --- TUTORIALSPACHECK: every check spelled out -------------------------

(defun spachk:tut-checklist ()
  (list
    "WHAT SPACHECK CHECKS"
    ""
    "Highlight the spa drawing TOGETHER WITH its Spa Cover Details"
    "block.  Every audit below comes from what SPA.LSP actually draws,"
    "so a drawing SPA produced passes and a hand-edited one shows"
    "exactly where it drifted."
    ""
    "1. SPA COVER DETAILS BLOCK"
    "   One in the selection, with a readable TAPER tag.  A missing"
    "     GRADE is taken as Standard, the way SPA takes it."
    "   Thermo-Light must be the 1-3/8 flat taper."
    ""
    "2. THE COVER OUTLINE"
    (strcat "   Exactly one closed entity on layer " spachk:*lay-cover*
            " - one polyline,")
    "     or a circle/ellipse for a round spa.  Loose arcs there are"
    "     the old pre-bounded output and are reported."
    ""
    "3. THE WATER'S EDGE OUTLINE"
    (strcat "   Optional.  When drawn: one closed entity on layer "
            spachk:*lay-water* ",")
    "     and INSIDE the cover - the cover is always the larger."
    ""
    "4. THE DIMENSIONS"
    (strcat "   Every one on layer " spachk:*lay-dim* ", in the right style")
    (strcat "     (" spachk:*ds-cover* " for the cover's, "
            spachk:*ds-water* " for")
    "     the water's edge's), and agreeing with what it spans - a"
    "     dimension whose measurement does not match its own points is"
    "     reported with both numbers."
    (strcat "   Both overalls present and noted '" spachk:*sfx-cover* "',")
    "     reading the cover's true size, standing 2 ft above and 3 ft"
    "     to the left as SPA places them."
    (strcat "   With both outlines drawn, an '" spachk:*sfx-lap*
            "' dimension reading")
    "     the true lap."
    ""
    "5. THE HINGES"
    (strcat "   The LINEs on layer " spachk:*lay-cover*
            " (the outline is a polyline, so")
    "     the two never confuse).  Against the block's grade and taper:"
    "     the piece count must be one the taper allows, no piece wider"
    "     than the foam width, no hinge longer than the foam length,"
    "     the fold/velcro order must match the Hinge Arrangement Chart,"
    (strcat "     and every hinge must carry its label on layer "
            spachk:*lay-text* ".")
    "   Hardware by the longest hinge is reported as advice."
    ""
    "6. THE TITLE BLOCK"
    (strcat "   Everything on layer '" spachk:*border-layer*
            "' measured together.")
    (strcat "   A spa title block is exactly "
            (rtos spachk:*title-frac* 2 2) "x the liner block "
            (rtos spachk:*liner-w*) " x " (rtos spachk:*liner-h*))
    (strcat "     = " (rtos (* spachk:*title-frac* spachk:*liner-w*)) " x "
            (rtos (* spachk:*title-frac* spachk:*liner-h*)) ".")
    "   Out of proportion is reported separately as STRETCHED."
    ""
    "7. THE REPORT"
    "   An MTEXT sheet to the right of the drawing, sized to scale with"
    (strcat "     it.  Problems in RED, advice in CYAN, all-clear at "
            (rtos (* 100.0 spachk:*green-scale*) 2 0) "%.")
    ""
    "COMMANDS"
    "   SPACHECK         audit, then walk what it flagged"
    "   SPACHECKSCAN     the same audits, read-only"
    "   SPACHECKVER      which revision is loaded"
    "   SPACHECKRESCUE   put every colour back, remove the report"
    ""
    "   TUTORIALSPACHECK Demo draws a practice spa with three faults"
    "                    planted in it and walks you through each one."))

;;; --- the demo ----------------------------------------------------------
;;;  A small practice spa drawn in an empty spot, with three faults
;;;  planted in it, walked through one at a time.  Everything it makes
;;;  goes in one list so the offer to erase it afterwards can be kept.

;; Remember one entity the demo made, and hand it straight back so the
;; caller can go on using it.
(defun spachk:demo-ent (e)
  (if e (setq spachk:*demo-ents* (cons e spachk:*demo-ents*)))
  e)

;; A closed rectangle, corners counter-clockwise from p.
(defun spachk:demo-rect (p w h layer / x y)
  (setq x (car p) y (cadr p))
  (spachk:demo-ent
    (entmakex (list '(0 . "LWPOLYLINE") '(100 . "AcDbEntity")
                    (cons 8 layer) '(100 . "AcDbPolyline")
                    '(90 . 4) '(70 . 1)
                    (list 10 x y) '(42 . 0.0)
                    (list 10 (+ x w) y) '(42 . 0.0)
                    (list 10 (+ x w) (+ y h)) '(42 . 0.0)
                    (list 10 x (+ y h)) '(42 . 0.0)))))

(defun spachk:demo-line (p q layer)
  (spachk:demo-ent
    (entmakex (list '(0 . "LINE") '(100 . "AcDbEntity") (cons 8 layer)
                    '(100 . "AcDbLine") (cons 10 p) (cons 11 q)))))

;; An aligned dim carrying a note, drawn the way SPA draws one.
(defun spachk:demo-dim (p1 p2 at note style / e)
  (spachk:dimstyle-set style)
  (setvar "CLAYER" spachk:*lay-dim*)
  (command "_.DIMALIGNED" p1 p2 "_T" (strcat "<>" note) at)
  (if (setq e (entlast)) (spachk:demo-ent e))
  e)

;; Make a dimension style current.  A drawing that has never held a spa
;; sheet has neither spa style in it, and a demo that then dimensioned
;; in STANDARD would report two style faults nobody planted -- so a
;; missing one is saved from the current settings, as SPA does.
(defun spachk:dimstyle-set (name)
  (if (tblsearch "DIMSTYLE" name)
    (command "_.-DIMSTYLE" "_Restore" name)
    (command "_.-DIMSTYLE" "_Save" name)))

;; A Spa Cover Details block, defined and inserted, carrying the GRADE
;; and TAPER the hinge checks read.  Without it the demo's unlabelled
;; hinge -- one of the three planted faults -- could never be reported,
;; because the hinge section stops for want of a taper.
(defun spachk:demo-block (p grade taper / e tag)
  (if (not (tblsearch "BLOCK" spachk:*details-block*))
    (progn
      (entmake (list '(0 . "BLOCK") '(100 . "AcDbEntity")
                     (cons 8 spachk:*lay-text*)
                     '(100 . "AcDbBlockBegin")
                     (cons 2 spachk:*details-block*)
                     '(70 . 2)                 ; has attribute definitions
                     '(10 0.0 0.0 0.0)))
      (foreach e (list (list "GRADE" 12.0) (list "TAPER" 0.0))
        (entmake (list '(0 . "ATTDEF") '(100 . "AcDbEntity")
                       (cons 8 spachk:*lay-text*) '(100 . "AcDbText")
                       (list 10 0.0 (cadr e) 0.0) '(40 . 5.0)
                       (cons 1 (car e)) '(100 . "AcDbAttributeDefinition")
                       (cons 3 (car e)) (cons 2 (car e)) '(70 . 0))))
      (entmake (list '(0 . "ENDBLK") '(100 . "AcDbEntity")
                     (cons 8 spachk:*lay-text*)
                     '(100 . "AcDbBlockEnd")))))
  (setq e (spachk:demo-ent
            (entmakex (list '(0 . "INSERT") '(100 . "AcDbEntity")
                            (cons 8 spachk:*lay-text*)
                            '(100 . "AcDbBlockReference")
                            '(66 . 1)          ; attributes follow
                            (cons 2 spachk:*details-block*)
                            (cons 10 p)))))
  (foreach tag (list (list "GRADE" (strcat "GRADE: " grade) 12.0)
                     (list "TAPER" (strcat "TAPER: " taper) 0.0))
    (spachk:demo-ent
      (entmakex (list '(0 . "ATTRIB") '(100 . "AcDbEntity")
                      (cons 8 spachk:*lay-text*) '(100 . "AcDbText")
                      (list 10 (car p) (+ (cadr p) (caddr tag)) 0.0)
                      '(40 . 5.0) (cons 1 (cadr tag))
                      '(100 . "AcDbAttribute") (cons 2 (car tag))
                      '(70 . 0)))))
  (spachk:demo-ent
    (entmakex (list '(0 . "SEQEND") '(100 . "AcDbEntity")
                    (cons 8 spachk:*lay-text*))))
  e)

;; Pause with an explanation, zoomed on what is being explained.
(defun spachk:demo-say (n of ent title lines / l)
  (if ent (spachk:zoom-ent ent))
  (princ (strcat "\n\n--- " (itoa n) " of " (itoa of) ": " title " ---"))
  (foreach l lines (princ (strcat "\n  " l)))
  (getstring "\n  (Enter to go on) "))

(defun spachk:demo (/ base x y e cov wat lay)
  (setq spachk:*demo-ents* nil)
  (foreach lay (list (list spachk:*lay-cover* 3)
                     (list spachk:*lay-water* 5)
                     (list spachk:*lay-dim* 7)
                     (list spachk:*lay-text* 7)
                     (list spachk:*border-layer* 8))
    (cal:ensure-layer (car lay) (cadr lay)))
  (setq base (getpoint "\nPick an empty spot for the practice drawing: "))
  (if (null base)
    (princ "\nNo spot picked - demo skipped.")
    (progn
      (setq x (car base) y (cadr base))
      (command "_.UNDO" "_Begin")
      ;; the cover, and a water's edge 3 in from it
      (setq cov (spachk:demo-rect (list x y) 84.0 60.0 spachk:*lay-cover*)
            wat (spachk:demo-rect (list (+ x 3.0) (+ y 3.0))
                                  78.0 54.0 spachk:*lay-water*))
      ;; overall dims, cover noted -- the top one deliberately WRONG:
      ;; it reads 80 across a cover that is really 84
      (spachk:demo-dim (list x (+ y 60.0)) (list (+ x 80.0) (+ y 60.0))
                       (list (+ x 40.0) (+ y 84.0))
                       (strcat "\\X" spachk:*sfx-cover*) spachk:*ds-cover*)
      (spachk:demo-dim (list x y) (list x (+ y 60.0))
                       (list (- x 36.0) (+ y 30.0))
                       (strcat "\\X" spachk:*sfx-cover*) spachk:*ds-cover*)
      ;; the water's edge overalls and the overlap between the two, so
      ;; the only things the scan reports are the three planted faults
      (spachk:demo-dim (list (+ x 3.0) (+ y 3.0)) (list (+ x 81.0) (+ y 3.0))
                       (list (+ x 42.0) (+ y 21.0))
                       (strcat "\\X" spachk:*sfx-water*) spachk:*ds-water*)
      (spachk:demo-dim (list (+ x 3.0) (+ y 3.0)) (list (+ x 3.0) (+ y 57.0))
                       (list (+ x 21.0) (+ y 30.0))
                       (strcat "\\X" spachk:*sfx-water*) spachk:*ds-water*)
      (spachk:demo-dim (list x y) (list (+ x 3.0) y)
                       (list (+ x 1.5) (- y 12.0))
                       (strcat "\\X" spachk:*sfx-lap*) spachk:*ds-cover*)
      ;; a hinge with NO label -- the second planted fault
      (spachk:demo-line (list (+ x 42.0) y) (list (+ x 42.0) (+ y 60.0))
                        spachk:*lay-cover*)
      ;; the details block, so the hinge section has a taper to work
      ;; from and can get as far as noticing the missing label
      (spachk:demo-block (list (+ x 120.0) (+ y 40.0)) "STANDARD" "4-3")
      ;; a border at the LINER size instead of 0.6x it -- the third
      (spachk:demo-rect (list (- x 200.0) (- y 200.0))
                        spachk:*liner-w* spachk:*liner-h*
                        spachk:*border-layer*)
      (command "_.ZOOM" "_Extents")
      (princ (strcat "\n\nA practice spa, with three faults planted in it."
                     "\nSPACHECK finds each one without being told where."))
      (spachk:demo-say
        1 3 cov "the overall that disagrees with the outline"
        (list "The cover polyline measures 84 x 60."
              "The dimension across the top says 80."
              ""
              "SPACHECK measures the outline itself and compares every"
              (strcat "dimension noted '" spachk:*sfx-cover*
                      "' against it, so a dim typed over,")
              "stretched, or left behind after a resize is named with"
              "both numbers - what it reads and what the cover is."))
      (spachk:demo-say
        2 3 nil "the hinge with no label"
        (list "One hinge line runs down the middle of the cover."
              (strcat "There is no MTEXT on the " spachk:*lay-text*
                      " layer against it.")
              ""
              "Every hinge must say whether it is a fold hinge or a"
              "velcro one, because the Hinge Arrangement Chart is read"
              "off those labels.  An unlabelled hinge is reported by"
              "number, and the arrangement check cannot run without it."))
      (spachk:demo-say
        3 3 nil "the title block left at the liner size"
        (list (strcat "The border is " (rtos spachk:*liner-w*) " x "
                      (rtos spachk:*liner-h*) " - the LINER block size.")
              (strcat "A spa title block must be exactly "
                      (rtos spachk:*title-frac* 2 2) "x that: "
                      (rtos (* spachk:*title-frac* spachk:*liner-w*)) " x "
                      (rtos (* spachk:*title-frac* spachk:*liner-h*)) ".")
              ""
              "This is the easiest one to get wrong, because a border"
              "copied from a liner sheet looks right until it plots."
              "SPACHECK names the factor it actually came out at."))
      (command "_.UNDO" "_End")
      (if (= "Yes" (cal:askkw "Run SPACHECKSCAN on it now"
                                 "Yes No" "Yes/No" "Yes" nil))
        (progn
          ;; the real command, not a rehearsal of it -- so it asks for a
          ;; selection exactly as it always does
          (princ (strcat "\n(SPACHECKSCAN asks what to scan - press Enter"
                         " to take the whole drawing.)"))
          (c:SPACHECKSCAN)))
      (if (= "Yes" (cal:askkw "Erase the practice drawing"
                                 "Yes No" "Yes/No" "Yes" nil))
        (progn
          (foreach e spachk:*demo-ents* (if (entget e) (entdel e)))
          (setq e (ssget "_X" (list (cons 8 spachk:*report-layer*))))
          (if e
            (progn
              (setq x 0)
              (repeat (sslength e)
                (entdel (ssname e x))
                (setq x (1+ x)))))
          (princ "\nPractice drawing erased.")))
      (setq spachk:*demo-ents* nil)))
  (princ))

(defun c:TUTORIALSPACHECK ( / *error* oldecho oldlay ans l)
  (defun *error* (msg)
    (if oldecho (setvar "CMDECHO" oldecho))
    (if oldlay (setvar "CLAYER" oldlay))
    (if (and msg (not (wcmatch (strcase msg)
                               "*BREAK*,*CANCEL*,*QUIT*,*EXIT*")))
      (princ (strcat "\nTUTORIALSPACHECK error: " msg)))
    (princ))
  (setq oldecho (getvar "CMDECHO") oldlay (getvar "CLAYER"))
  (setvar "CMDECHO" 0)
  (setq ans (cal:askkw "Show me" "Checks Demo Both" "Checks/Demo/Both" "Both" nil))
  (if (member ans '("Checks" "Both"))
    (foreach l (spachk:tut-checklist) (princ (strcat "\n" l))))
  (if (member ans '("Demo" "Both"))
    (spachk:demo))
  (setvar "CLAYER" oldlay)
  (setvar "CMDECHO" oldecho)
  (princ))

(princ (strcat "\nSPACHECK " *spacheck-version*
               " loaded.  Type SPACHECK to run."))
(princ)


;;; ======================================================================
;;; >>> STOCKCOVER.lsp
;;; ======================================================================

;;; ===================================================================
;;; STOCKCOVER.lsp  -  paste a stock cover drawing onto a highlighted
;;;                    perimeter in the current drawing
;;;
;;; AutoCAD 2018+ (uses ActiveX for bounding boxes and the DWG insert
;;; fallback -- (vl-load-com) is called on load).
;;;
;;; Commands:
;;;   STOCKCOVER      replace a highlighted perimeter with a stock DWG
;;;   STOCKLIST       list every stock drawing in the stock folder
;;;   STOCKCOVER-CFG  point the routine at the stock folder
;;;
;;; SHARED BUILD: requires CALOFIN-LIB.lsp (load via CALOFIN-LOADER.lsp).
;;; Generic helpers live there under cal: - see STANDARDS.md.
;;;
;;; What STOCKCOVER does:
;;;   1. You highlight the perimeter that is to be replaced.
;;;   2. You type the short name of the stock drawing -- "5M" finds
;;;      "5M_Tech.dwg", "20M" finds "20M_Tech.dwg" (see the suffix
;;;      list below).  Enter on its own reuses the last name.
;;;   3. The stock DWG is read straight off disk into a scratch block,
;;;      exploded, and lined up on the highlighted perimeter so the two
;;;      perimeters sit on top of each other.
;;;   4. The highlighted entities are erased and the scratch block
;;;      definition is purged.
;;;
;;; Alignment is by the anchor POINTs both sides carry: the highlighted
;;; area and every stock drawing have a point at the bottom left and a
;;; point at the top right.  The stock is placed in ONE move, its
;;; bottom-left anchor onto the highlighted bottom-left anchor, and
;;; then left exactly there -- no fit prompt, no scaling, no shuffling
;;; afterwards.  When either side has no anchor points, the corners of
;;; its bounding box stand in and STOCKCOVER says so.  If the two
;;; anchor spans disagree by more than *stock-anchor-tol*, the wrong
;;; file was probably named: STOCKCOVER prints how far off it is, loud,
;;; but still places anchored -- one U rolls the whole run back.
;;; Nothing is erased until the new geometry is placed.
;;;
;;; The whole run is one UNDO step.
;;;
;;; Versioning: see tools/release_lisp.py at the repo root.  It reads
;;; *stockcover-version* below and stamps a dated, REV-numbered twin of
;;; this file into releases/.
;;; ===================================================================

(vl-load-com)

;;; -------------------------------------------------------------------
;;;  SETTINGS - set *stock-folder* before handing this file out; a user
;;;  can still override it per machine with STOCKCOVER-CFG, which is
;;;  remembered in the AutoCAD profile and wins over the value here.
;;; -------------------------------------------------------------------

(setq *stockcover-version* "v1.3") ; printed on load and at command
                                   ; start, so a loaded routine and its
                                   ; releases/ twin can never disagree

(setq *stock-folder* "F:\\TechTeam\\2022 StockCoverTech")
                                   ; where the stock DWGs live

(setq *stock-suffixes* '("_Tech"))  ; tried after an exact stem match:
                                    ; "5M" -> "5M.dwg", then
                                    ; "5M_Tech.dwg", then "5M*.dwg"

(setq *stock-explode* t)   ; T  = explode the insert so the stock
                           ;      geometry merges into the drawing
                           ; nil = leave it as a single block reference

(setq *stock-anchor-tol* 0.25) ; inches - the two anchor spans may
                            ; differ this much before STOCKCOVER
                            ; shouts that the wrong file was named

(setq *stock-env-folder* "StockCover_Folder") ; profile keys used to
(setq *stock-env-last*   "StockCover_Last")   ; remember folder + name

;;; -------------------------------------------------------------------
;;;  small helpers
;;; -------------------------------------------------------------------

(defun stock:say (s) (princ (strcat "\n" s)) (princ))

(defun stock:getenv (key / v)             ; "" and unset both read nil
  (setq v (getenv key))
  (if (and v (/= v "")) v))

(defun stock:fwd (s / i c out)            ; backslashes -> forward
  (setq out "" i 1)                       ; slashes, which AutoCAD's
  (while (<= i (strlen s))                ; file prompts prefer
    (setq c (substr s i 1))
    (setq out (strcat out (if (= c "\\") "/" c)))
    (setq i (1+ i)))
  out)

(defun stock:trim (s)                     ; drop a trailing separator
  (if (and (> (strlen s) 0)
           (member (substr s (strlen s) 1) '("\\" "/")))
    (substr s 1 (1- (strlen s)))
    s))

(defun stock:folder ()                    ; profile override, else the
  (stock:trim                             ; setting at the top of file
    (if (stock:getenv *stock-env-folder*)
      (stock:getenv *stock-env-folder*)
      *stock-folder*)))

(defun stock:path (folder file) (strcat folder "\\" file))

(defun stock:files (folder)               ; bare DWG names in folder
  (if (vl-file-directory-p folder)
    (vl-directory-files folder "*.dwg" 1)))

(defun stock:stems (files)
  (mapcar '(lambda (f) (vl-filename-base f)) files))

;;; Candidates for a typed name, best first: an exact stem match, then
;;; each configured suffix, then a leading-substring sweep.  Each rung
;;; is only tried when the one above it came up empty, so "5M" cannot
;;; be dragged off its exact file by "5MB_Tech.dwg" also existing.
(defun stock:match (name files / up hit f s)
  (setq up (strcase name))
  (foreach f files
    (if (= (strcase (vl-filename-base f)) up) (setq hit (cons f hit))))
  (if (null hit)
    (foreach s *stock-suffixes*
      (if (null hit)
        (foreach f files
          (if (= (strcase (vl-filename-base f)) (strcase (strcat name s)))
            (setq hit (cons f hit)))))))
  (if (null hit)
    (foreach f files
      (if (wcmatch (strcase (vl-filename-base f)) (strcat up "*"))
        (setq hit (cons f hit)))))
  (reverse hit))

(defun stock:uniq-block (/ i nm)          ; a block name the drawing is
  (setq i 0 nm "STOCK$0")                 ; not already using, so the
  (while (tblsearch "BLOCK" nm)           ; insert can never redefine
    (setq i (1+ i) nm (strcat "STOCK$" (itoa i))))
  nm)

;;; Everything added to the database after MARK (nil = whole drawing).
(defun stock:new-ents (mark / e ss)
  (setq ss (ssadd))
  (setq e (if mark (entnext mark) (entnext)))
  (while e
    (ssadd e ss)
    (setq e (entnext e)))
  (if (> (sslength ss) 0) ss))

;;; Combined bounding box of a selection set -> ((minx miny minz)
;;; (maxx maxy maxz)), or nil if nothing in it could be measured.
(defun stock:size (bb)                    ; (width height)
  (list (- (car (cadr bb)) (car (car bb)))
        (- (cadr (cadr bb)) (cadr (car bb)))))

(defun stock:fmt (wh)
  (strcat (rtos (car wh) 2 3) " x " (rtos (cadr wh) 2 3)))

;;; The bottom-left / top-right anchor POINTs of a selection: of all
;;; POINT entities in it, the ones lowest and highest along x+y.
;;; -> (bl tr) as 3D points, or nil when the selection holds fewer
;;; than two POINTs.
(defun stock:anchors (ss / i en ed p pts bl tr)
  (setq i 0)
  (while (< i (sslength ss))
    (setq en (ssname ss i)
          ed (entget en))
    (if (= (cdr (assoc 0 ed)) "POINT")
      (setq pts (cons (cdr (assoc 10 ed)) pts)))
    (setq i (1+ i)))
  (if (>= (length pts) 2)
    (progn
      (setq bl (car pts) tr (car pts))
      (foreach p (cdr pts)
        (if (< (+ (car p) (cadr p)) (+ (car bl) (cadr bl))) (setq bl p))
        (if (> (+ (car p) (cadr p)) (+ (car tr) (cadr tr))) (setq tr p)))
      (list (list (car bl) (cadr bl) 0.0)
            (list (car tr) (cadr tr) 0.0)))))

;;; Span of an anchor pair: (width height) bottom-left -> top-right.
(defun stock:span (an)
  (list (- (car (cadr an)) (car (car an)))
        (- (cadr (cadr an)) (cadr (car an)))))

;;; -------------------------------------------------------------------
;;;  reading the stock DWG in
;;; -------------------------------------------------------------------

;;; -INSERT with an explicit block name reads the file off disk rather
;;; than reusing anything already in the drawing.  2015+ engines refuse
;;; to route (command) through vl-catch-all-apply, so the insert goes
;;; through command-s, which runs the command to completion in one call
;;; and turns a failed insert into a catchable error instead of leaving
;;; the command hanging.  Each string travels as one input token, so the
;;; space in the stock folder's name needs no quoting.  If the insert
;;; still comes back empty, fall back to ActiveX, which takes the raw
;;; path.
(defun stock:insert (path bname / spec used stem)
  (setq spec (strcat bname "=" (stock:fwd path)))
  (vl-catch-all-apply
    'command-s (list "_.-INSERT" spec '(0.0 0.0 0.0) 1.0 1.0 0.0))
  (if (tblsearch "BLOCK" bname) (setq used bname))
  (if (null used)
    (progn
      ;; ActiveX takes the raw path, so it needs no quoting - but it
      ;; names the definition after the file, which can collide
      (setq stem (vl-filename-base path))
      (if (tblsearch "BLOCK" stem)
        (stock:say
          (strcat "a block named \"" stem "\" is already in this drawing -"
                  " rename it and try again."))
        (if (not (vl-catch-all-error-p
                   (vl-catch-all-apply 'vla-InsertBlock
                     (list (vla-get-ModelSpace
                             (vla-get-ActiveDocument (vlax-get-acad-object)))
                           (vlax-3d-point 0.0 0.0 0.0)
                           path 1.0 1.0 1.0 0.0))))
          (setq used stem)))))
  used)

;;; -------------------------------------------------------------------
;;;  STOCKLIST
;;; -------------------------------------------------------------------

(defun c:STOCKLIST (/ folder files s)
  (setq folder (stock:folder)
        files  (stock:files folder))
  (cond
    ((null (vl-file-directory-p folder))
     (stock:say (strcat "stock folder not reachable: " folder))
     (stock:say "point STOCKCOVER at it with STOCKCOVER-CFG."))
    ((null files)
     (stock:say (strcat "no DWGs in " folder)))
    (t
     (stock:say (strcat (itoa (length files)) " stock drawing(s) in " folder ":"))
     (foreach s (stock:stems files) (princ (strcat "\n  " s)))))
  (princ))

;;; -------------------------------------------------------------------
;;;  STOCKCOVER-CFG
;;; -------------------------------------------------------------------

(defun c:STOCKCOVER-CFG (/ cur f new)
  (setq cur (stock:folder))
  (stock:say (strcat "stock folder is now: " cur))
  ;; getfiled on any DWG inside the folder is the portable folder picker
  (setq f (getfiled "Pick any DWG inside the stock folder"
                    (strcat cur "\\") "dwg" 0))
  (if f
    (progn
      (setq new (stock:trim (vl-filename-directory f)))
      (setenv *stock-env-folder* new)
      (stock:say (strcat "stock folder set to " new))
      (stock:say (strcat (itoa (length (stock:files new))) " DWG(s) there.")))
    (stock:say "unchanged."))
  (princ))

;;; -------------------------------------------------------------------
;;;  STOCKCOVER
;;; -------------------------------------------------------------------

(defun c:STOCKCOVER (/ *error* stock:restore
                       oscm osos osclay osiu osareq osadia undone
                       folder files ss-old tbb tsz tanch name last hits
                       pick i file path bname mark ss-new sbb ssz sanch
                       dx dy f)

  (defun stock:restore ()
    (if oscm   (setvar "CMDECHO"  oscm))
    (if osos   (setvar "OSMODE"   osos))
    (if osclay (setvar "CLAYER"   osclay))
    (if osiu   (setvar "INSUNITS" osiu))
    (if osareq (setvar "ATTREQ"   osareq))
    (if osadia (setvar "ATTDIA"   osadia)))

  ;; 2015+ engines forbid (command) inside *error* unless the error
  ;; mode was pushed beforehand; command-s is the sanctioned
  ;; replacement and needs no setup, so the handler uses only that.
  (defun *error* (msg)
    (if (and msg (not (wcmatch (strcase msg) "*BREAK*,*CANCEL*,*QUIT*,*EXIT*")))
      (princ (strcat "\nSTOCKCOVER error: " msg)))
    (stock:restore)
    (if undone
      (progn
        (vl-catch-all-apply 'command-s (list "_.UNDO" "_End"))
        (princ "\nNothing was left half done - use U to roll the run back.")))
    (princ))

  (setq oscm   (getvar "CMDECHO")
        osos   (getvar "OSMODE")
        osclay (getvar "CLAYER")
        osiu   (getvar "INSUNITS")
        osareq (getvar "ATTREQ")
        osadia (getvar "ATTDIA"))

  (stock:say (strcat "STOCKCOVER " *stockcover-version*
                     " - drop a stock cover onto a highlighted perimeter."))

  (setq folder (stock:folder))
  (setq files  (stock:files folder))
  (cond
    ((null (vl-file-directory-p folder))
     (stock:say (strcat "stock folder not reachable: " folder))
     (stock:say "set it with STOCKCOVER-CFG.")
     (setq files nil))
    ((null files)
     (stock:say (strcat "no DWGs in " folder))))

  (if files
    (progn
      ;; ---------------------------------------------- what to replace
      (princ "\nHighlight the perimeter to be replaced: ")
      (setq ss-old (ssget))
      (if (null ss-old)
        (stock:say "nothing highlighted - nothing to replace.")
        (progn
          (setq tbb (cal:bbox-ss ss-old))
          (if (null tbb)
            (stock:say "could not measure the highlighted entities.")
            (progn
              (setq tsz (stock:size tbb))
              (stock:say (strcat "highlighted area: " (stock:fmt tsz)))
              (setq tanch (stock:anchors ss-old))
              (if tanch
                (stock:say "anchor points found on the highlighted area.")
                (progn
                  (setq tanch (list (car tbb) (cadr tbb)))
                  (stock:say "no anchor points highlighted - using the box corners.")))

              ;; ------------------------------------- which stock file
              (setq last (stock:getenv *stock-env-last*))
              (setq name
                (getstring t
                  (strcat "\nStock drawing name"
                          (if last (strcat " <" last ">") "") ": ")))
              (if (= name "") (setq name last))
              (if (null name)
                (stock:say "no name given.")
                (progn
                  (setq hits (stock:match name files))
                  (cond
                    ((null hits)
                     (stock:say (strcat "no stock drawing matches \"" name
                                        "\" - try STOCKLIST.")))
                    (t
                     (if (= (length hits) 1)
                       (setq file (car hits))
                       (progn
                         (stock:say (strcat (itoa (length hits))
                                            " drawings match \"" name "\":"))
                         (setq i 1)
                         (foreach f hits
                           (princ (strcat "\n  " (itoa i) ". "
                                          (vl-filename-base f)))
                           (setq i (1+ i)))
                         (initget 7)
                         (setq pick (getint "\nWhich one? "))
                         (setq file (if (and (>= pick 1) (<= pick (length hits)))
                                      (nth (1- pick) hits)))))
                     (if (null file)
                       (stock:say "no drawing picked.")
                       (progn
                         (setq path (stock:path folder file))
                         (setenv *stock-env-last* name)
                         (stock:say (strcat "using " path))

                         ;; ------------------------------- bring it in
                         (setvar "CMDECHO" 0)
                         (setvar "OSMODE" 0)
                         (setvar "INSUNITS" 0) ; no silent unit rescale
                         (setvar "ATTREQ" 0)
                         (setvar "ATTDIA" 0)
                         (command "_.UNDO" "_BEgin")
                         (setq undone t)

                         (setq bname (stock:uniq-block))
                         (setq mark (entlast))
                         (setq bname (stock:insert path bname))
                         (if (null bname)
                           (stock:say (strcat "could not read " path))
                           (progn
                             (if *stock-explode*
                               (command "_.EXPLODE" (entlast) ""))
                             (setq ss-new (stock:new-ents mark))
                             (if (null ss-new)
                               (stock:say (strcat path " brought nothing in."))
                               (progn
                                 (setq sbb (cal:bbox-ss ss-new))
                                 (if (null sbb)
                                   (stock:say "could not measure the stock geometry.")
                                   (progn
                                     (setq ssz (stock:size sbb))
                                     (stock:say (strcat "stock geometry: "
                                                        (stock:fmt ssz)))

                                     ;; ------------------ anchor check
                                     (setq sanch (stock:anchors ss-new))
                                     (if (null sanch)
                                       (progn
                                         (setq sanch (list (car sbb) (cadr sbb)))
                                         (stock:say "no anchor points in the stock file - using its box corners.")))
                                     ;; the bottom-left -> top-right
                                     ;; spans should agree; when they do
                                     ;; not, the wrong file was probably
                                     ;; named - say so, loudly, but the
                                     ;; placement stays anchored as-is
                                     (setq dx (- (car (stock:span sanch))
                                                 (car (stock:span tanch)))
                                           dy (- (cadr (stock:span sanch))
                                                 (cadr (stock:span tanch))))
                                     (if (or (> (abs dx) *stock-anchor-tol*)
                                             (> (abs dy) *stock-anchor-tol*))
                                       (progn
                                         (stock:say (strcat "ANCHORS DO NOT AGREE: the stock's span is off by "
                                                            (rtos dx 2 3) " across and "
                                                            (rtos dy 2 3) " up."))
                                         (stock:say "check you named the right stock drawing - one U rolls this back.")))

                                     ;; ------------------------- place:
                                     ;; ONE move, bottom-left anchor to
                                     ;; bottom-left anchor, and it stays
                                     ;; exactly there
                                     (command "_.MOVE" ss-new ""
                                              (car sanch) (car tanch))
                                     (command "_.ERASE" ss-old "")
                                     (if *stock-explode*
                                       (command "_.-PURGE" "_B" bname "_N"))
                                     (stock:say
                                       (strcat (vl-filename-base file) " placed on the anchor - "
                                               (itoa (sslength ss-new))
                                               " object(s) in, "
                                               (itoa (sslength ss-old))
                                               " out."))))))))
                         (command "_.UNDO" "_End")
                         (setq undone nil)))))))))))))

  (stock:restore)
  (princ))

(princ (strcat "\nSTOCKCOVER " *stockcover-version*
               " loaded.  STOCKCOVER to place a stock cover,"
               " STOCKLIST to see what is available,"
               " STOCKCOVER-CFG to set the folder."))
(princ)


;;; ======================================================================
;;; >>> drone.lsp
;;; ======================================================================

;;; ===================================================================
;;; DRONE.LSP                                          AutoCAD 2018
;;; -------------------------------------------------------------------
;;; Command: DRONE
;;;
;;; SHARED BUILD: requires CALOFIN-LIB.lsp (load via CALOFIN-LOADER.lsp).
;;; Generic helpers live there under cal: - see STANDARDS.md.
;;;
;;; Drawing cleanup routine that applies five fixes in one pass:
;;;
;;;   1. TEXT  - every highlighted (pre-selected) text entity is
;;;              switched to style ROMANC at height 4.5, with color,
;;;              linetype and lineweight forced to BYLAYER.
;;;              If nothing is highlighted when the command starts you
;;;              are prompted to select text; pressing Enter at that
;;;              prompt processes ALL text in the drawing.
;;;
;;;   2. POOL / SPA POINTS - every POINT entity on layer POOL or on
;;;              layer SPA is moved to layer POINTS with color /
;;;              linetype / lineweight all set to BYLAYER (POINTS is
;;;              magenta, so they show pink).  The pool's points and
;;;              the spa's share the one POINTS layer.
;;;
;;;   3. SPA PERIMETER - the spa outline - lines, arcs, circles,
;;;              ellipses, polylines and splines on layer SPA - is
;;;              moved to layer POOL, so the pool perimeter and the
;;;              spa perimeter share it, and forced to BYLAYER so the
;;;              moved geometry picks up POOL's own appearance.
;;;              Points are swept off SPA by step 2 first, so only
;;;              the outline is left to move.
;;;
;;;   4. ANCHOR POINTS - every POINT entity on layer ANCHORS is given
;;;              an explicit magenta (ACI 6) color - the same pink as
;;;              the points - but stays on the ANCHORS layer.
;;;
;;;   5. ORIENT - after the conversion the processed text is rotated
;;;              flat so it reads west -> east, right side up
;;;              (absolute angle 0).  Each text pivots about its own
;;;              insertion point - the labels share that point in
;;;              space with the POINT they belong to - so every label
;;;              stays anchored to its point.  Set
;;;              *drone-orient-angle* to nil to only flip upside-down
;;;              text instead ("Most readable").
;;;
;;; The ROMANC text style and the POINTS and POOL layers are created
;;; if they do not already exist.  Locked layers are unlocked for the
;;; duration of the command and re-locked afterwards.  The whole run
;;; is wrapped in a single undo group.
;;; ===================================================================

(setq *drone-version* "v1.0")   ; announced on load; release_lisp.py
                                   ; stamps the dated twin in releases/

(vl-load-com)

;; ---------------------------------------------------------------
;; Configuration
;; ---------------------------------------------------------------
(setq *drone-text-style*  "ROMANC"
      *drone-text-font*   "romanc.shx"
      *drone-text-height* 4.5
      *drone-pt-layers*   '("POOL" "SPA")   ; POINTs found on these...
      *drone-dest-layer*  "POINTS"          ; ...move to this one
      *drone-perim-src*   '("SPA")          ; outlines found on these...
      *drone-perim-layer* "POOL"            ; ...move to this one
      *drone-perim-types* "LINE,ARC,CIRCLE,ELLIPSE,LWPOLYLINE,POLYLINE,SPLINE"
      *drone-perim-color* 4          ; ACI 4 = cyan, POOL's own color
      *drone-anch-layer*  "ANCHORS"
      *drone-pink*        6           ; ACI 6 = magenta / pink
      *drone-orient-angle* 0.0)       ; absolute text angle in degrees
                                      ; (0 = read west->east, right
                                      ; side up); nil = only flip
                                      ; upside-down text ("Most
                                      ; readable")

;; ---------------------------------------------------------------
;; Helpers
;; ---------------------------------------------------------------

;; Make sure the target text style exists.
(defun drone:ensure-style (name font)
  (if (null (tblsearch "STYLE" name))
    (entmake
      (list '(0 . "STYLE")
            '(100 . "AcDbSymbolTableRecord")
            '(100 . "AcDbTextStyleTableRecord")
            (cons 2 name)
            '(70 . 0)
            '(40 . 0.0)                ; height 0 = not fixed
            '(41 . 1.0)                ; width factor
            '(50 . 0.0)                ; oblique angle
            '(71 . 0)
            (cons 3 font)
            '(4 . ""))))
  (tblsearch "STYLE" name))

;; Unlock every layer in NAMES that is currently locked and return the
;; list of layer objects that were unlocked (so they can be re-locked).
(defun drone:unlock-layers (names doc / layers obj unlocked name)
  (setq layers (vla-get-Layers doc))
  (foreach name names
    (if (and name (tblsearch "LAYER" name))
      (progn
        (setq obj (vla-Item layers name))
        (if (= :vlax-true (vla-get-Lock obj))
          (progn
            (vla-put-Lock obj :vlax-false)
            (setq unlocked (cons obj unlocked)))))))
  unlocked)

(defun drone:relock-layers (objs / obj)
  (foreach obj objs (vla-put-Lock obj :vlax-true)))

;; Reset color / linetype / lineweight of a vla-object to BYLAYER.
(defun drone:force-bylayer (obj)
  (vla-put-Color obj acByLayer)
  (vla-put-Linetype obj "ByLayer")
  (vla-put-Lineweight obj acLnWtByLayer))

;; Rotate a text to the target orientation.  Setting the Rotation
;; property pivots the text about its insertion/alignment point; the
;; point labels share that point in space with the POINT entity they
;; belong to, so each label swings around its own point and stays
;; anchored to it.  With *drone-orient-angle* set, the text is turned
;; to that absolute angle; with it nil, only upside-down text (angle
;; in (90, 270] degrees) is flipped 180.
(defun drone:orient (obj / cur target)
  (setq cur (rem (vla-get-Rotation obj) (* 2.0 pi)))   ; radians
  (if (< cur 0.0) (setq cur (+ cur (* 2.0 pi))))
  (setq target
        (if *drone-orient-angle*
          (* pi (/ *drone-orient-angle* 180.0))
          (if (and (> cur (* 0.5 pi)) (<= cur (* 1.5 pi)))
            (rem (+ cur pi) (* 2.0 pi))
            cur)))
  (if (not (equal cur target 1e-8))
    (vla-put-Rotation obj target)))

;; Join layer names into the comma-separated form an ssget filter
;; wants: ("POOL" "SPA") -> "POOL,SPA".
(defun drone:csv (names / out name)
  (foreach name names
    (setq out (if out (strcat out "," name) name)))
  out)

;; Collect the distinct layer names used by the entities of a
;; selection set.
(defun drone:sel-layers (ss / i lay result)
  (if ss
    (progn
      (setq i 0)
      (while (< i (sslength ss))
        (setq lay (cdr (assoc 8 (entget (ssname ss i)))))
        (if (not (member (strcase lay) result))
          (setq result (cons (strcase lay) result)))
        (setq i (1+ i)))))
  result)

;; ---------------------------------------------------------------
;; Error handler - restore locked layers and close the undo group
;; even if the user hits Esc or something fails mid-run.
;; ---------------------------------------------------------------
(defun drone:error (msg)
  (if *drone-unlocked* (drone:relock-layers *drone-unlocked*))
  (setq *drone-unlocked* nil)
  (if *drone-doc* (vla-EndUndoMark *drone-doc*))
  (if (and msg (not (wcmatch (strcase msg) "*BREAK*,*CANCEL*,*QUIT*,*EXIT*")))
    (princ (strcat "\nDRONE error: " msg)))
  (if *drone-old-error* (setq *error* *drone-old-error*))
  (princ))

;; ---------------------------------------------------------------
;; Main command
;; ---------------------------------------------------------------
(defun c:DRONE (/ ss-text ss-pt ss-perim ss-anch i ent obj
                  n-text n-pt n-perim n-anch)

  (setq *drone-old-error* *error*
        *error*           drone:error
        *drone-doc*       (vla-get-ActiveDocument (vlax-get-acad-object))
        *drone-unlocked*  nil
        n-text 0  n-pt 0  n-perim 0  n-anch 0)

  (vla-StartUndoMark *drone-doc*)

  ;; Make sure the style and both destination layers are available.
  (drone:ensure-style *drone-text-style* *drone-text-font*)
  (cal:ensure-layer *drone-dest-layer* *drone-pink*)
  (cal:ensure-layer *drone-perim-layer* *drone-perim-color*)

  ;; ------------------------------------------------------------
  ;; 1. Text: highlighted selection, else prompt, Enter = all text
  ;; ------------------------------------------------------------
  (setq ss-text (ssget "_I" '((0 . "TEXT"))))
  (if (null ss-text)
    (progn
      (prompt "\nSelect text to update <Enter = all text in drawing>: ")
      (setq ss-text (ssget '((0 . "TEXT"))))
      (if (null ss-text)
        (setq ss-text (ssget "_X" '((0 . "TEXT")))))))

  ;; ------------------------------------------------------------
  ;; 2/3/4. Points on POOL / SPA, the spa outline, and the ANCHORS
  ;;        points - anywhere in the drawing
  ;; ------------------------------------------------------------
  (setq ss-pt    (ssget "_X" (list '(0 . "POINT")
                                   (cons 8 (drone:csv *drone-pt-layers*))))
        ss-perim (ssget "_X" (list (cons 0 *drone-perim-types*)
                                   (cons 8 (drone:csv *drone-perim-src*))))
        ss-anch  (ssget "_X" (list '(0 . "POINT")
                                   (cons 8 *drone-anch-layer*))))

  ;; Unlock every layer we are about to touch.
  (setq *drone-unlocked*
        (drone:unlock-layers
          (append *drone-pt-layers*
                  *drone-perim-src*
                  (list *drone-perim-layer*
                        *drone-anch-layer*
                        *drone-dest-layer*)
                  (drone:sel-layers ss-text))
          *drone-doc*))

  ;; Text -> ROMANC / 4.5 / BYLAYER
  (if ss-text
    (progn
      (setq i 0)
      (while (< i (sslength ss-text))
        (setq ent (ssname ss-text i)
              obj (vlax-ename->vla-object ent))
        (vla-put-StyleName obj *drone-text-style*)
        (vla-put-Height obj *drone-text-height*)
        (drone:force-bylayer obj)
        (setq n-text (1+ n-text)
              i      (1+ i)))))

  ;; POOL / SPA points -> POINTS layer, everything BYLAYER
  (if ss-pt
    (progn
      (setq i 0)
      (while (< i (sslength ss-pt))
        (setq obj (vlax-ename->vla-object (ssname ss-pt i)))
        (vla-put-Layer obj *drone-dest-layer*)
        (drone:force-bylayer obj)
        (setq n-pt (1+ n-pt)
              i    (1+ i)))))

  ;; Spa outline -> POOL layer, everything BYLAYER so it takes POOL's
  ;; color and linetype rather than carrying the spa layer's over.
  (if ss-perim
    (progn
      (setq i 0)
      (while (< i (sslength ss-perim))
        (setq obj (vlax-ename->vla-object (ssname ss-perim i)))
        (vla-put-Layer obj *drone-perim-layer*)
        (drone:force-bylayer obj)
        (setq n-perim (1+ n-perim)
              i       (1+ i)))))

  ;; ANCHORS points -> pink (ACI 6), same layer
  (if ss-anch
    (progn
      (setq i 0)
      (while (< i (sslength ss-anch))
        (setq obj (vlax-ename->vla-object (ssname ss-anch i)))
        (vla-put-Color obj *drone-pink*)
        (setq n-anch (1+ n-anch)
              i      (1+ i)))))

  ;; ------------------------------------------------------------
  ;; 5. Orient the converted text to read west -> east, right side
  ;;    up, each label pivoting about its insertion point (= the
  ;;    point it labels).
  ;; ------------------------------------------------------------
  (if ss-text
    (progn
      (setq i 0)
      (while (< i (sslength ss-text))
        (vl-catch-all-apply
          'drone:orient
          (list (vlax-ename->vla-object (ssname ss-text i))))
        (setq i (1+ i)))))

  ;; Re-lock whatever we unlocked and close the undo group.
  (drone:relock-layers *drone-unlocked*)
  (setq *drone-unlocked* nil)
  (vla-EndUndoMark *drone-doc*)
  (setq *error* *drone-old-error*)

  (princ (strcat "\nDRONE done: "
                 (itoa n-text) " text -> " *drone-text-style*
                 " h" (rtos *drone-text-height* 2 2)
                 " oriented W->E, "
                 (itoa n-pt) " point(s) -> " *drone-dest-layer*
                 ", "
                 (itoa n-perim) " perimeter -> " *drone-perim-layer*
                 ", "
                 (itoa n-anch) " ANCHORS point(s) -> pink."))
  (princ))

(princ "\nDRONE.LSP loaded.  Type DRONE to run.")
(princ)


;;; ======================================================================
;;; >>> tydrn.lsp
;;; ======================================================================

;;; ===================================================================
;;; TYDRN.LSP                                          AutoCAD 2018
;;; -------------------------------------------------------------------
;;; Commands: TYDRN             the cleanup below
;;;           TYLERDRONESUITE  TYDRN, then PADDLE, then AUTODIM
;;;
;;; SHARED BUILD: requires CALOFIN-LIB.lsp (load via CALOFIN-LOADER.lsp).
;;; Generic helpers live there under cal: - see STANDARDS.md.
;;;
;;; Drawing cleanup routine that applies three fixes in one pass:
;;;
;;;   1. TEXT  - every highlighted (pre-selected) text entity is
;;;              switched to style ROMANC at height 4.5, with color,
;;;              linetype and lineweight forced to BYLAYER.
;;;              If nothing is highlighted when the command starts you
;;;              are prompted to select text; pressing Enter at that
;;;              prompt processes ALL text in the drawing.
;;;
;;;   2. POOL POINTS - every POINT entity on layer POOL is moved to
;;;              layer POINTS with color / linetype / lineweight all
;;;              set to BYLAYER (POINTS is magenta, so they show pink).
;;;
;;;   3. ANCHOR POINTS - every POINT entity on layer ANCHORS is given
;;;              an explicit magenta (ACI 6) color - the same pink as
;;;              the points - but stays on the ANCHORS layer.
;;;
;;;   4. ORIENT - after the conversion the processed text is rotated
;;;              flat so it reads west -> east, right side up
;;;              (absolute angle 0).  Each text pivots about its own
;;;              insertion point - the labels share that point in
;;;              space with the POINT they belong to - so every label
;;;              stays anchored to its point.  Set
;;;              *tydrn-orient-angle* to nil to only flip upside-down
;;;              text instead ("Most readable").
;;;
;;; The ROMANC text style and the POINTS layer are created if they do
;;; not already exist.  Locked layers are unlocked for the duration of
;;; the command and re-locked afterwards.  The whole run is wrapped in
;;; a single undo group.
;;; ===================================================================

(setq *tydrn-version* "v1.1")   ; announced on load; release_lisp.py
                                   ; stamps the dated twin in releases/

(vl-load-com)

;; ---------------------------------------------------------------
;; Configuration
;; ---------------------------------------------------------------
(setq *tydrn-text-style*  "ROMANC"
      *tydrn-text-font*   "romanc.shx"
      *tydrn-text-height* 4.5
      *tydrn-pool-layer*  "POOL"
      *tydrn-dest-layer*  "POINTS"
      *tydrn-anch-layer*  "ANCHORS"
      *tydrn-pink*        6           ; ACI 6 = magenta / pink
      *tydrn-orient-angle* 0.0)       ; absolute text angle in degrees
                                      ; (0 = read west->east, right
                                      ; side up); nil = only flip
                                      ; upside-down text ("Most
                                      ; readable")

;; ---------------------------------------------------------------
;; Helpers
;; ---------------------------------------------------------------

;; Make sure the target text style exists.
(defun tydrn:ensure-style (name font)
  (if (null (tblsearch "STYLE" name))
    (entmake
      (list '(0 . "STYLE")
            '(100 . "AcDbSymbolTableRecord")
            '(100 . "AcDbTextStyleTableRecord")
            (cons 2 name)
            '(70 . 0)
            '(40 . 0.0)                ; height 0 = not fixed
            '(41 . 1.0)                ; width factor
            '(50 . 0.0)                ; oblique angle
            '(71 . 0)
            (cons 3 font)
            '(4 . ""))))
  (tblsearch "STYLE" name))

;; Unlock every layer in NAMES that is currently locked and return the
;; list of layer objects that were unlocked (so they can be re-locked).
(defun tydrn:unlock-layers (names doc / layers obj unlocked)
  (setq layers (vla-get-Layers doc))
  (foreach name names
    (if (and name (tblsearch "LAYER" name))
      (progn
        (setq obj (vla-Item layers name))
        (if (= :vlax-true (vla-get-Lock obj))
          (progn
            (vla-put-Lock obj :vlax-false)
            (setq unlocked (cons obj unlocked)))))))
  unlocked)

(defun tydrn:relock-layers (objs)
  (foreach obj objs (vla-put-Lock obj :vlax-true)))

;; Reset color / linetype / lineweight of a vla-object to BYLAYER.
(defun tydrn:force-bylayer (obj)
  (vla-put-Color obj acByLayer)
  (vla-put-Linetype obj "ByLayer")
  (vla-put-Lineweight obj acLnWtByLayer))

;; Rotate a text to the target orientation.  Setting the Rotation
;; property pivots the text about its insertion/alignment point; the
;; point labels share that point in space with the POINT entity they
;; belong to, so each label swings around its own point and stays
;; anchored to it.  With *tydrn-orient-angle* set, the text is turned
;; to that absolute angle; with it nil, only upside-down text (angle
;; in (90, 270] degrees) is flipped 180.
(defun tydrn:orient (obj / cur target)
  (setq cur (rem (vla-get-Rotation obj) (* 2.0 pi)))   ; radians
  (if (< cur 0.0) (setq cur (+ cur (* 2.0 pi))))
  (setq target
        (if *tydrn-orient-angle*
          (* pi (/ *tydrn-orient-angle* 180.0))
          (if (and (> cur (* 0.5 pi)) (<= cur (* 1.5 pi)))
            (rem (+ cur pi) (* 2.0 pi))
            cur)))
  (if (not (equal cur target 1e-8))
    (vla-put-Rotation obj target)))

;; Collect the distinct layer names used by the entities of a
;; selection set.
(defun tydrn:sel-layers (ss / i lay result)
  (if ss
    (progn
      (setq i 0)
      (while (< i (sslength ss))
        (setq lay (cdr (assoc 8 (entget (ssname ss i)))))
        (if (not (member (strcase lay) result))
          (setq result (cons (strcase lay) result)))
        (setq i (1+ i)))))
  result)

;; ---------------------------------------------------------------
;; Error handler - restore locked layers and close the undo group
;; even if the user hits Esc or something fails mid-run.
;; ---------------------------------------------------------------
(defun tydrn:error (msg)
  (if *tydrn-unlocked* (tydrn:relock-layers *tydrn-unlocked*))
  (setq *tydrn-unlocked* nil)
  (if *tydrn-doc* (vla-EndUndoMark *tydrn-doc*))
  (if (and msg (not (wcmatch (strcase msg) "*BREAK*,*CANCEL*,*QUIT*,*EXIT*")))
    (princ (strcat "\nTYDRN error: " msg)))
  (if *tydrn-old-error* (setq *error* *tydrn-old-error*))
  (princ))

;; ---------------------------------------------------------------
;; Main command
;; ---------------------------------------------------------------
(defun C:TYDRN (/ ss-text ss-pool ss-anch i ent obj
                  n-text n-pool n-anch)

  (setq *tydrn-old-error* *error*
        *error*           tydrn:error
        *tydrn-doc*       (vla-get-ActiveDocument (vlax-get-acad-object))
        *tydrn-unlocked*  nil
        n-text 0  n-pool 0  n-anch 0)

  (vla-StartUndoMark *tydrn-doc*)

  ;; Make sure the style and destination layer are available.
  (tydrn:ensure-style *tydrn-text-style* *tydrn-text-font*)
  (cal:ensure-layer *tydrn-dest-layer* *tydrn-pink*)

  ;; ------------------------------------------------------------
  ;; 1. Text: highlighted selection, else prompt, Enter = all text
  ;; ------------------------------------------------------------
  (setq ss-text (ssget "_I" '((0 . "TEXT"))))
  (if (null ss-text)
    (progn
      (prompt "\nSelect text to update <Enter = all text in drawing>: ")
      (setq ss-text (ssget '((0 . "TEXT"))))
      (if (null ss-text)
        (setq ss-text (ssget "_X" '((0 . "TEXT")))))))

  ;; ------------------------------------------------------------
  ;; 2/3. Points on POOL and ANCHORS, anywhere in the drawing
  ;; ------------------------------------------------------------
  (setq ss-pool (ssget "_X" (list '(0 . "POINT") (cons 8 *tydrn-pool-layer*)))
        ss-anch (ssget "_X" (list '(0 . "POINT") (cons 8 *tydrn-anch-layer*))))

  ;; Unlock every layer we are about to touch.
  (setq *tydrn-unlocked*
        (tydrn:unlock-layers
          (append (list *tydrn-pool-layer*
                        *tydrn-anch-layer*
                        *tydrn-dest-layer*)
                  (tydrn:sel-layers ss-text))
          *tydrn-doc*))

  ;; Text -> ROMANC / 4.5 / BYLAYER
  (if ss-text
    (progn
      (setq i 0)
      (while (< i (sslength ss-text))
        (setq ent (ssname ss-text i)
              obj (vlax-ename->vla-object ent))
        (vla-put-StyleName obj *tydrn-text-style*)
        (vla-put-Height obj *tydrn-text-height*)
        (tydrn:force-bylayer obj)
        (setq n-text (1+ n-text)
              i      (1+ i)))))

  ;; POOL points -> POINTS layer, everything BYLAYER
  (if ss-pool
    (progn
      (setq i 0)
      (while (< i (sslength ss-pool))
        (setq obj (vlax-ename->vla-object (ssname ss-pool i)))
        (vla-put-Layer obj *tydrn-dest-layer*)
        (tydrn:force-bylayer obj)
        (setq n-pool (1+ n-pool)
              i      (1+ i)))))

  ;; ANCHORS points -> pink (ACI 6), same layer
  (if ss-anch
    (progn
      (setq i 0)
      (while (< i (sslength ss-anch))
        (setq obj (vlax-ename->vla-object (ssname ss-anch i)))
        (vla-put-Color obj *tydrn-pink*)
        (setq n-anch (1+ n-anch)
              i      (1+ i)))))

  ;; ------------------------------------------------------------
  ;; 4. Orient the converted text to read west -> east, right side
  ;;    up, each label pivoting about its insertion point (= the
  ;;    point it labels).
  ;; ------------------------------------------------------------
  (if ss-text
    (progn
      (setq i 0)
      (while (< i (sslength ss-text))
        (vl-catch-all-apply
          'tydrn:orient
          (list (vlax-ename->vla-object (ssname ss-text i))))
        (setq i (1+ i)))))

  ;; Re-lock whatever we unlocked and close the undo group.
  (tydrn:relock-layers *tydrn-unlocked*)
  (setq *tydrn-unlocked* nil)
  (vla-EndUndoMark *tydrn-doc*)
  (setq *error* *tydrn-old-error*)

  (princ (strcat "\nTYDRN done: "
                 (itoa n-text) " text -> " *tydrn-text-style*
                 " h" (rtos *tydrn-text-height* 2 2)
                 " oriented W->E, "
                 (itoa n-pool) " point(s) POOL -> " *tydrn-dest-layer*
                 ", "
                 (itoa n-anch) " ANCHORS point(s) -> pink."))
  (princ))

;;; ===================================================================
;;; TYLERDRONESUITE - the drone trace, start to finish
;;; -------------------------------------------------------------------
;;; TYDRN, then PADDLE, then AUTODIM, in that order because that is the
;;; order the work has to happen in: the points have to be on the right
;;; layer before PADDLE can find the perimeter features to pad, and the
;;; pads have to be in before AUTODIM dimensions what is there.
;;;
;;; Nothing is skipped or reworded - each stage is the command itself,
;;; asking its own questions, so anything learned about TYDRN, PADDLE
;;; or AUTODIM stays true here.  The suite only supplies the order.
;;;
;;; EACH STAGE KEEPS ITS OWN UNDO GROUP, so three U's back the suite
;;; out, one per stage.  That is deliberate, and it is XYPLOT's
;;; reasoning about its ABHD handoff: a stage that went well should not
;;; have to be undone to get at one that did not.
;;;
;;; Esc in any stage stops the suite there - an AutoLISP error unwinds
;;; to the command line, so the stages after it never start.  What ran
;;; before it stays run, which is why the check below happens first.
;;; ===================================================================

(setq *tydrn-suite* '("TYDRN" "PADDLE" "AUTODIM"))

;; Is C:<name> defined in this session?  (XYPLOT's boundp test, with
;; the name computed rather than quoted.)
(defun tydrn:has (name)
  (boundp (read (strcat "c:" name))))

;; "PADDLE and AUTODIM" -- the way the refusal names what is missing.
(defun tydrn:namelist (names / out n i nm)
  (setq out "" n (length names) i 0)
  (foreach nm names
    (setq out (strcat out
                      (cond ((= i 0) "")
                            ((= i (1- n)) (if (= n 2) " and " ", and "))
                            (t ", "))
                      nm)
          i   (1+ i)))
  out)

(defun c:TYLERDRONESUITE ( / missing nm step)
  ;; Every stage is checked BEFORE any of them runs.  Half a suite is
  ;; worse than none: TYDRN would have moved the points and PADDLE
  ;; dropped the pads, and the operator would find out only at the end
  ;; that the dimensioning they ran this for was never going to happen.
  (setq missing nil)
  (foreach nm *tydrn-suite*
    (if (not (tydrn:has nm)) (setq missing (cons nm missing))))
  (setq missing (reverse missing))
  (if missing
    (progn
      (princ (strcat "\nTYLERDRONESUITE needs " (tydrn:namelist missing)
                     ", which " (if (= 1 (length missing)) "is" "are")
                     " not loaded here."))
      (princ "\n  APPLOAD the missing file - or LAZPASS.lsp, which is the")
      (princ "\n  whole build in one - and run it again.  Nothing has been")
      (princ "\n  changed."))
    (progn
      (princ "\nTYLERDRONESUITE: TYDRN, then PADDLE, then AUTODIM.")
      (princ "\n  Each stage is its own undo group, so a stage that went")
      (princ "\n  well is not undone to get at one that did not.  Esc in")
      (princ "\n  any stage stops the suite there.")
      (setq step 0)
      (foreach nm *tydrn-suite*
        (setq step (1+ step))
        (princ (strcat "\n\n--- " (itoa step) " of "
                       (itoa (length *tydrn-suite*)) ": " nm " ---"))
        ;; through the command line, not as a direct call, so each stage
        ;; prompts and errors exactly as it does when it is typed
        (vl-cmdf (strcat "_." nm)))
      (princ "\n\nTYLERDRONESUITE done - all three stages ran.")))
  (princ))

(princ (strcat "\nTYDRN.LSP " *tydrn-version*
               " loaded.  Type TYDRN to run, or TYLERDRONESUITE"
               " for TYDRN + PADDLE + AUTODIM."))
(princ)


;;; ======================================================================
;;; >>> wcalst.lsp
;;; ======================================================================

;;; ===================================================================
;;; WCALST.lsp — straighten a curved constant-width "ladder" band
;;; -------------------------------------------------------------------
;;; Command: WCALST
;;;
;;; SHARED BUILD: requires CALOFIN-LIB.lsp (load via CALOFIN-LOADER.lsp).
;;; Generic helpers live there under cal: - see STANDARDS.md.
;;;
;;; Select a band drawn as two long curved sides connected by rungs,
;;; click the side that must come out straight, and the command draws
;;; the developed (unrolled) band below the selection:
;;;
;;;   * the chosen side as one straight line (layer AIR-B, red)
;;;   * the opposite side as its rigidly unrolled, slightly wavy chain
;;;     (kept on its original layer)
;;;   * DARTS  — V cutouts where unrolling creates excess material
;;;   * INSERTS — straight slits plus a loose sliver piece drawn below
;;;     the band where unrolling opens a gap
;;;   * band-height dimensions at both ends (layer DIMENSION)
;;;
;;; Darts + inserts are capped (default 20): the required correction is
;;; accumulated along the band and only released when it reaches a
;;; minimum useful width, so the cut count stays conservative.
;;;
;;; Tested with AutoCAD 2018; plain AutoLISP, no VLX / ObjectARX.
;;; Load with APPLOAD, then run WCALST.
;;; ===================================================================

;;; ------------------------ small math helpers ----------------------

(setq *wcalst-version* "v1.0")   ; announced on load; release_lisp.py
                                    ; stamps the dated twin in releases/

(defun wc:key (p)
  ;; fuzzy node key so touching endpoints share one node
  (strcat (rtos (car p) 2 3) "," (rtos (cadr p) 2 3))
)

(defun wc:turn (d0 d1 / d)
  ;; signed turn angle normalized to (-pi, pi]
  (setq d (- d1 d0))
  (while (> d pi) (setq d (- d pi pi)))
  (while (<= d (- pi)) (setq d (+ d pi pi)))
  d
)

(defun wc:dir (a b)
  ;; direction angle of a->b
  (atan (- (cadr b) (cadr a)) (- (car b) (car a)))
)

;;; ------------------------- segment soup ---------------------------

(defun wc:ent-points (en / ed et pts sub sd closed)
  ;; ordered vertex list of a LINE / LWPOLYLINE / POLYLINE
  (setq ed (entget en)
        et (cdr (assoc 0 ed))
        pts nil
  )
  (cond
    ((= et "LINE")
     (setq pts (list (cdr (assoc 10 ed)) (cdr (assoc 11 ed))))
    )
    ((= et "LWPOLYLINE")
     (foreach g ed
       (if (= (car g) 10) (setq pts (cons (cdr g) pts)))
     )
     (setq pts (reverse pts))
     (if (= 1 (logand 1 (if (assoc 70 ed) (cdr (assoc 70 ed)) 0)))
       (setq pts (append pts (list (car pts))))
     )
    )
    ((= et "POLYLINE")
     (setq closed (= 1 (logand 1 (if (assoc 70 ed) (cdr (assoc 70 ed)) 0)))
           sub (entnext en)
     )
     (while (and sub (= "VERTEX" (cdr (assoc 0 (setq sd (entget sub))))))
       ;; keep on-curve vertices, skip spline frame control points
       (if (= 0 (logand 16 (cdr (assoc 70 sd))))
         (setq pts (cons (cdr (assoc 10 sd)) pts))
       )
       (setq sub (entnext sub))
     )
     (setq pts (reverse pts))
     (if (and closed pts) (setq pts (append pts (list (car pts)))))
    )
  )
  ;; force 2D
  (mapcar '(lambda (p) (list (car p) (cadr p))) pts)
)

(defun wc:build-segs (ss / i en pts a segs lay)
  ;; -> list of (ptA ptB layer ename), one entry per 2-point segment
  (setq i 0 segs nil)
  (while (< i (sslength ss))
    (setq en  (ssname ss i)
          lay (cdr (assoc 8 (entget en)))
          pts (wc:ent-points en)
    )
    (while (cdr pts)
      (setq a (car pts) pts (cdr pts))
      (if (> (distance a (car pts)) 1.0e-6)
        (setq segs (cons (list a (car pts) lay en) segs))
      )
    )
    (setq i (1+ i))
  )
  (reverse segs)
)

(defun wc:build-nodes (segs / nodes i k e)
  ;; -> assoc list (key . (segidx ...))
  (setq nodes nil i 0)
  (foreach sg segs
    (foreach p (list (car sg) (cadr sg))
      (setq k (wc:key p)
            e (assoc k nodes)
      )
      (if e
        (setq nodes (subst (cons k (cons i (cdr e))) e nodes))
        (setq nodes (cons (list k i) nodes))
      )
    )
    (setq i (1+ i))
  )
  nodes
)

(defun wc:other-end (sg p)
  ;; endpoint of segment sg that is not (fuzzy-)equal to p
  (if (equal (wc:key (car sg)) (wc:key p))
    (cadr sg)
    (car sg)
  )
)

;;; -------------------------- chain tracing -------------------------

(defun wc:trace (segs nodes seed toward / cur p q ids pts cands best
                 bestang j sg r ang d0 stop)
  ;; walk from segment SEED through endpoint TOWARD, always taking the
  ;; straightest continuation; stop when the best turn exceeds 60 deg.
  ;; -> (ids . pts)  ids = seg indices walked (seed first),
  ;;                 pts = nodes visited (start node first)
  (setq cur seed
        p   (wc:other-end (nth seed segs) toward)
        q   toward
        ids (list seed)
        pts (list q p)                  ; reversed order, start last
        stop nil
  )
  (while (not stop)
    (setq d0 (wc:dir p q)
          cands (cdr (assoc (wc:key q) nodes))
          best nil
          bestang nil
    )
    (foreach j cands
      (if (/= j cur)
        (progn
          (setq sg (nth j segs)
                r (wc:other-end sg q)
                ang (abs (wc:turn d0 (wc:dir q r)))
          )
          (if (or (not bestang) (< ang bestang))
            (setq bestang ang best j)
          )
        )
      )
    )
    (if (or (not best) (> bestang 1.0472) (> (length ids) 5000)) ; 60 deg
      (setq stop T)
      (setq ids (cons best ids)
            p q
            cur best
            q (wc:other-end (nth best segs) q)
            pts (cons q pts)
      )
    )
  )
  (cons (reverse ids) (reverse pts))
)

(defun wc:full-chain (segs nodes seed / sg r1 r2)
  ;; trace both directions from SEED -> (ids . pts) covering the whole side
  (setq sg (nth seed segs)
        r1 (wc:trace segs nodes seed (car sg))   ; towards first endpoint
        r2 (wc:trace segs nodes seed (cadr sg))  ; towards second endpoint
  )
  ;; r1 pts = (B A ...towards a-side); r2 pts = (A B ...towards b-side)
  (cons
    (append (reverse (cdr (car r1))) (car r2))       ; ids, seed once
    (append (reverse (cdr r1)) (cddr (cdr r2)))      ; pts, join at A B
  )
)

;;; --------------------------- development --------------------------

(defun wc:member-key (p keys)
  (member (wc:key p) keys)
)

(defun wc:dev-point (fp pts s / k n A B ax ay L2 tt cx cy d2 bk bt bd
                     d c sn dx dy)
  ;; project FP on the chain, develop it with the transform of the
  ;; nearest chain segment -> (devx devy proj-s proj-dist original-pt)
  (setq k 0 n (1- (length pts)) bd 1.0e18 bk 0 bt 0.0)
  (while (< k n)
    (setq A (nth k pts) B (nth (1+ k) pts)
          ax (- (car B) (car A)) ay (- (cadr B) (cadr A))
          L2 (+ (* ax ax) (* ay ay))
          tt (if (< L2 1.0e-12)
               0.0
               (/ (+ (* (- (car fp) (car A)) ax)
                     (* (- (cadr fp) (cadr A)) ay))
                  L2)
             )
          tt (max 0.0 (min 1.0 tt))
          cx (+ (car A) (* tt ax)) cy (+ (cadr A) (* tt ay))
          d2 (+ (expt (- (car fp) cx) 2) (expt (- (cadr fp) cy) 2))
    )
    (if (< d2 bd) (setq bd d2 bk k bt tt))
    (setq k (1+ k))
  )
  (setq A (nth bk pts) B (nth (1+ bk) pts)
        d (wc:dir A B)
        c (cos (- d)) sn (sin (- d))
        dx (- (car fp) (car A)) dy (- (cadr fp) (cadr A))
  )
  (list
    (+ (nth bk s) (- (* dx c) (* dy sn)))
    (+ (* dx sn) (* dy c))
    (+ (nth bk s) (* bt (- (nth (1+ bk) s) (nth bk s))))
    (sqrt bd)
    fp
  )
)

;;; ---------------------------- drawing -----------------------------

(defun wc:line (a b lay)
  (entmake
    (list '(0 . "LINE") (cons 8 lay)
          (list 10 (car a) (cadr a) 0.0)
          (list 11 (car b) (cadr b) 0.0)
    )
  )
)

(defun wc:pline (pts lay closed)
  (entmake
    (append
      (list '(0 . "LWPOLYLINE") '(100 . "AcDbEntity") (cons 8 lay)
            '(100 . "AcDbPolyline") (cons 90 (length pts))
            (cons 70 (if closed 1 0))
      )
      (mapcar '(lambda (p) (cons 10 (list (car p) (cadr p)))) pts)
    )
  )
)

(defun wc:emit (idebt rungs pts s wmin maxfeat carry / feats acc k fsum
                cw f fdev)
  ;; walk the per-interval correction debt, releasing a dart (mouth
  ;; capped at 4") or an insert whenever the accumulator reaches WMIN.
  ;; CARRY non-nil: the un-released remainder carries to the next rung
  ;; (large corrections split into several capped darts - best fit);
  ;; CARRY nil: the accumulator resets after each release (fewest cuts)
  ;; -> (feats fsum): feats = ((x width type local-depth) ...) in band
  ;;    order, fsum = inserts added - dart widths removed
  (setq feats nil acc 0.0 k 0 fsum 0.0)
  (while (< k (length idebt))
    (setq acc (+ acc (nth k idebt)))
    (if (and (>= (abs acc) wmin) (< (length feats) maxfeat))
      (progn
        (setq cw (abs acc))
        (if (< acc 0) (setq cw (min cw 4.0)))      ; dart mouth cap
        (setq f (nth (1+ k) rungs)
              fdev (wc:dev-point (caddr f) pts s)
        )
        ;; turn towards the far side = dart
        (setq feats (cons (list (nth (car f) s) cw
                                (if (< acc 0) 1 -1)
                                (- (cadr fdev)))
                          feats)
              fsum (+ fsum (if (< acc 0) (- cw) cw))
              acc (if carry
                    (if (< acc 0) (+ acc cw) (- acc cw))
                    0.0
                  )
        )
      )
    )
    (setq k (1+ k))
  )
  (list (reverse feats) fsum)
)

(defun wc:mult (sgm paircnt / f)
  ;; how many times this segment is drawn (2 = mesh interior, 1 = outline)
  (setq f (assoc (strcat (wc:key (car sgm)) "|" (wc:key (cadr sgm)))
                 paircnt))
  (if (not f)
    (setq f (assoc (strcat (wc:key (cadr sgm)) "|" (wc:key (car sgm)))
                   paircnt))
  )
  (if f (cdr f) 0)
)

(defun wc:chain-at (sv pts s / k n t0 sa sb A B)
  ;; point on the chosen chain at arc position SV
  (setq k 0 n (1- (length pts)))
  (while (and (< k (1- n)) (> sv (nth (1+ k) s)))
    (setq k (1+ k))
  )
  (setq sa (nth k s) sb (nth (1+ k) s)
        A (nth k pts) B (nth (1+ k) pts)
        t0 (if (> (- sb sa) 1.0e-9) (/ (- sv sa) (- sb sa)) 0.0)
        t0 (max 0.0 (min 1.0 t0))
  )
  (list (+ (car A) (* t0 (- (car B) (car A))))
        (+ (cadr A) (* t0 (- (cadr B) (cadr A))))
  )
)

(defun wc:depth-at (xv dps / a b res found)
  ;; linear interpolation of developed depth (cadr) at developed-x XV
  ;; over DPS (a list of dev-points sorted ascending by car); used to
  ;; land dart feet exactly on the bottom line
  (setq res (cadr (car dps)) found nil)
  (while (and (cdr dps) (not found))
    (setq a (car dps) b (cadr dps))
    (if (and (<= (car a) xv) (<= xv (car b)))
      (setq res (if (> (- (car b) (car a)) 1.0e-9)
                  (+ (cadr a) (* (- (cadr b) (cadr a))
                                 (/ (- xv (car a)) (- (car b) (car a)))))
                  (cadr a))
            found T
      )
    )
    (setq dps (cdr dps))
  )
  res
)

(defun wc:instair (xv rngs / hit)
  ;; T if arc position XV falls inside any (lo hi) stair range
  (setq hit nil)
  (foreach r rngs
    (if (and (>= xv (car r)) (<= xv (cadr r))) (setq hit T))
  )
  hit
)

(defun wc:notch (dps dfeats / runs run dp dd lx rx curr)
  ;; split the bottom line into runs at each dart mouth so no segment
  ;; spans the mouth (the base under the dart is erased); the run ends
  ;; land on the bottom line at the dart feet.
  ;; DFEATS: darts (cx cw) sorted ascending by cx.
  ;; -> list of runs, each a list of local (x y) points
  (setq runs nil run nil curr -1.0e18)
  (foreach dp dps
    (while (and dfeats
                (<= (- (car (car dfeats)) (/ (cadr (car dfeats)) 2.0))
                    (car dp)))
      (setq dd (car dfeats) dfeats (cdr dfeats)
            lx (- (car dd) (/ (cadr dd) 2.0))
            rx (+ (car dd) (/ (cadr dd) 2.0))
            run (cons (list lx (wc:depth-at lx dps)) run)   ; close at L foot
      )
      (if (cdr run) (setq runs (cons (reverse run) runs)))
      (setq run (list (list rx (wc:depth-at rx dps)))       ; reopen at R foot
            curr (max curr rx)
      )
    )
    (if (> (car dp) curr)
      (setq run (cons (list (car dp) (cadr dp)) run))
    )
  )
  (if (cdr run) (setq runs (cons (reverse run) runs)))
  (reverse runs)
)

(defun wc:vdim (p1 p2 xline lay)
  ;; vertical rotated dimension between P1 and P2, dim line at X=XLINE
  (entmake
    (list '(0 . "DIMENSION") '(100 . "AcDbEntity") (cons 8 lay)
          '(100 . "AcDbDimension")
          (list 10 xline (/ (+ (cadr p1) (cadr p2)) 2.0) 0.0)
          '(70 . 32) '(1 . "")
          '(100 . "AcDbAlignedDimension")
          (list 13 (car p1) (cadr p1) 0.0)
          (list 14 (car p2) (cadr p2) 0.0)
          '(100 . "AcDbRotatedDimension")
          (cons 50 (/ pi 2))
    )
  )
)

;;; ------------------------------ main ------------------------------

(defun c:WCALST (/ *error* oldlay ss segs nodes pick en pk seed sg d2min
                 d2c i r ids pts chainkeys s n p0 p1 dch j far ang rungs
                 widths w mid side cross ni f k turns d0 d1 idebt i0 i1
                 tsum total wmin maxfeat acc feats fdev farlay fseed
                 fsegs cands rfar rr farpts farids fk seen ordered devpts
                 minx miny maxx maxy sgp x0 y0 wpt a b ld hz cw x
                 dl dr yb enda endb lay2 inundo conns nmk sgm dp1 dp2
                 bandlays tileh toplen botb bota tx th pass stop
                 resid featsb residb paircnt bndpts vy vfeats vresid
                 vlab ssstairs stsegs stkeys synth comp compkeys grow
                 strest nodes2 endpts dpa stentry stpath usedj stpt stgo
                 stcand se pA pB stang stca stsn sttot stlen stprev stdx
                 stdy dfeats run stairrng stage)

  (defun *error* (msg)
    (if inundo (command "_.UNDO" "_End"))
    (if oldlay (setvar "CLAYER" oldlay))
    (if (and msg (not (wcmatch (strcase msg) "*BREAK*,*CANCEL*,*QUIT*,*EXIT*")))
      (princ (strcat "\nWCALST error: " msg))
    )
    (princ)
  )
  (setq oldlay (getvar "CLAYER"))

  ;; ---- 1.-7. the questions, staged so every prompt after the first
  ;; offers Back (Undo works too): the side pick returns to the band
  ;; selection, the numeric prompts to the side pick - the trace is
  ;; recomputed from whatever is re-answered.  A trace that fails now
  ;; re-opens the pick it came from instead of ending the command.
  (setq stage 1)
  (while (< stage 6)
    (cond

      ;; ---- 1. selection ----------------------------------------------
      ((= stage 1)
       (princ "\nSelect the band of lines (two long sides + rungs): ")
       (setq ss (ssget '((0 . "LINE,LWPOLYLINE,POLYLINE"))))
       (if (not ss) (progn (princ "\nNothing selected.") (exit)))
       (setq segs (wc:build-segs ss))
       (if (< (length segs) 6)
         (princ "\nToo few segments to form a band - select again.")
         (progn
           (setq nodes (wc:build-nodes segs))
           (setq stage 2)
         )
       ))

      ;; ---- 2. pick the side to straighten ----------------------------
      ((= stage 2)
       (initget "Back Undo")
       (setq pick (entsel "\nClick the long side to STRAIGHTEN [Back]: "))
       (cond
         ((= (type pick) 'STR) (setq stage 1))
         ((not pick)
          (princ "  (nothing picked - click a line of the selection)"))
         ((not (ssmemb (car pick) ss))
          (princ "  (that entity is not in the selection)"))
         (T
          (setq en (car pick) pk (cadr pick))
          ;; seed = the segment of the picked entity nearest the pick
          (setq seed nil d2min 1.0e18 i 0)
          (foreach sg segs
            (if (eq (cadddr sg) en)
              (progn
                (setq d2c (cal:d2 pk (mapcar '(lambda (u v) (/ (+ u v) 2.0))
                                            (car sg) (cadr sg))))
                (if (< d2c d2min) (setq d2min d2c seed i))
              )
            )
            (setq i (1+ i))
          )
          (if (not seed)
            (princ "\nCould not locate a segment at that pick.")
            (setq stage 3)
          )
         )
       ))

      ;; ---- 3.-6. trace, rungs, orientation, turn debt (no input) -----
      ((= stage 3)
       (setq r (wc:full-chain segs nodes seed)
             ids (car r)
             pts (cdr r)
       )
       (if (< (length ids) 3)
         (progn
           (princ "\nCould not trace a long side from that pick - pick again.")
           (setq stage 2)
         )
         (progn
           (setq chainkeys (mapcar 'wc:key pts))

           ;; arc length of each chain node
           (setq s (list 0.0))
           (setq p0 (car pts))
           (foreach p1 (cdr pts)
             (setq s (cons (+ (car s) (distance p0 p1)) s) p0 p1)
           )
           (setq s (reverse s)
                 n (length pts)
           )

           ;; ---- 4. rungs --------------------------------------------
           ;; conns records every segment hanging off the chosen chain
           ;; (rungs, diagonal braces, chords) so none of them is later
           ;; mistaken for a free-standing reference mark
           (setq rungs nil conns nil ni 0)
           (foreach p pts
             (setq p0 (nth (max 0 (1- ni)) pts)
                   p1 (nth (min (1- n) (1+ ni)) pts)
                   dch (wc:dir p0 p1)
             )
             (foreach j (cdr (assoc (wc:key p) nodes))
               (if (not (member j ids))
                 (progn
                   (setq conns (cons j conns)
                         far (wc:other-end (nth j segs) p)
                   )
                   (if (not (wc:member-key far chainkeys))
                     (progn
                       (setq ang (abs (wc:turn dch (wc:dir p far)))
                             ang (min ang (- pi ang))
                       )
                       (if (> ang 0.7854)          ; > 45 deg off the chain
                         (setq rungs (cons (list ni p far) rungs))
                       )
                     )
                   )
                 )
               )
             )
             (setq ni (1+ ni))
           )
           (setq rungs (reverse rungs))
           (if (< (length rungs) 2)
             (progn
               (princ "\nCould not find the rungs between the two sides - pick again.")
               (setq stage 2)
             )
             (progn
               ;; band width = median rung length
               (setq widths (vl-sort (mapcar '(lambda (r)
                                                (distance (cadr r) (caddr r)))
                                             rungs)
                                     '<)
                     w (nth (/ (length widths) 2) widths)
               )

               ;; ---- 5. normalize orientation: far side below the
               ;; ---- travel direction
               (setq side 0)
               (foreach f rungs
                 (setq ni (car f) p (cadr f) far (caddr f)
                       p0 (nth (max 0 (1- ni)) pts)
                       p1 (nth (min (1- n) (1+ ni)) pts)
                       cross (- (* (- (car p1) (car p0))
                                   (- (cadr far) (cadr p)))
                                (* (- (cadr p1) (cadr p0))
                                   (- (car far) (car p))))
                 )
                 (setq side (+ side (if (> cross 0) 1 -1)))
               )
               (if (> side 0)          ; far side is left -> walk the other way
                 (progn
                   (setq pts (reverse pts)
                         mid (car (reverse s))
                         s (reverse (mapcar '(lambda (v) (- mid v)) s))
                         chainkeys (reverse chainkeys)
                         rungs (mapcar '(lambda (f)
                                          (list (- n 1 (car f)) (cadr f) (caddr f)))
                                       rungs)
                         rungs (reverse rungs)
                   )
                 )
               )

               ;; ---- 6. turn angles and per-interval correction debt --
               (setq turns (list 0.0) k 1)
               (while (< k (1- n))
                 (setq d0 (wc:dir (nth (1- k) pts) (nth k pts))
                       d1 (wc:dir (nth k pts) (nth (1+ k) pts))
                       turns (cons (wc:turn d0 d1) turns)
                       k (1+ k)
                 )
               )
               (setq turns (reverse (cons 0.0 turns)))

               (setq idebt nil k 0)
               (while (< k (1- (length rungs)))
                 (setq i0 (car (nth k rungs))
                       i1 (car (nth (1+ k) rungs))
                       tsum 0.0
                       j (1+ i0)
                 )
                 (while (<= j i1)
                   (setq tsum (+ tsum (nth j turns)) j (1+ j))
                 )
                 (setq idebt (cons (* tsum w) idebt) k (1+ k))
               )
               (setq idebt (reverse idebt)
                     total (apply '+ (mapcar 'abs idebt))
               )
               (setq stage 4)
             )
           )
         )
       ))

      ;; ---- 7. feature threshold (conservative, capped) ---------------
      ((= stage 4)
       (initget "Back Undo")
       (setq maxfeat (getint "\nMaximum darts + inserts <20> [Back]: "))
       (if (= (type maxfeat) 'STR)
         (setq stage 2)
         (progn
           (if (or (not maxfeat) (< maxfeat 1)) (setq maxfeat 20))
           (setq stage 5)
         )
       ))
      ;; a tile of this height sits along the straightened edge: cuts
      ;; may only come up to (width - tile height - 1") from the far edge
      (T
       (initget "Back Undo")
       (setq tileh (getreal
                     "\nTile height along the straightened edge <none> [Back]: "))
       (if (= (type tileh) 'STR)
         (setq stage 4)
         (progn
           (if (and tileh (< tileh 0.0)) (setq tileh nil))
           (setq stage 6)
         )
       ))
    )
  )
  ;; stair sections: the bottom line wraps around steps there; each
  ;; windowed section is developed rigidly as one piece so every tread
  ;; length and riser rise is kept exactly (treads come out level,
  ;; equal steps up and down stay equal)
  (princ "\nWindow the STAIR section(s) if any (Enter = none): ")
  (setq ssstairs (ssget))

  ;; ---- 8. develop the far edge ----------------------------------------
  ;; far side points = every rung far foot + the far chain traced from a
  ;; middle rung (feet alone already outline the edge if the chain breaks)
  (setq fseed (caddr (nth (/ (length rungs) 2) rungs))
        cands (cdr (assoc (wc:key fseed) nodes))
        fsegs nil
  )
  (foreach j cands
    (setq far (wc:other-end (nth j segs) fseed))
    (if (and (not (member j ids))
             (not (wc:member-key far chainkeys)))
      (setq fsegs (cons j fsegs))
    )
  )
  (setq farpts nil farlay nil farids nil)
  (if fsegs
    (progn
      (setq rr (wc:full-chain segs nodes (car fsegs))
            farids (car rr)
            farpts (cdr rr)
            farlay (caddr (nth (car fsegs) segs))
      )
    )
  )
  (if (not farlay) (setq farlay (caddr (nth seed segs))))
  ;; layers the band structure itself lives on: bands may be full
  ;; triangulated meshes (interior vertices, doubled edges), so segment
  ;; bookkeeping cannot tell structure from reference marks — layers can
  (setq bandlays (list (caddr (nth seed segs))))
  (if (and farlay (not (member farlay bandlays)))
    (setq bandlays (cons farlay bandlays))
  )
  (foreach k conns
    (if (not (member (caddr (nth k segs)) bandlays))
      (setq bandlays (cons (caddr (nth k segs)) bandlays))
    )
  )

  ;; outline vertices: segments drawn ONCE are outline (mesh interiors
  ;; are always shared by two triangles and appear twice). Keeping every
  ;; far-side outline vertex preserves sharp steps (~90 deg temporary
  ;; rises) that the straightest-path tracing cuts across
  (setq paircnt nil)
  (foreach sgm segs
    (setq fk (strcat (wc:key (car sgm)) "|" (wc:key (cadr sgm)))
          f  (assoc fk paircnt)
    )
    (if (not f)
      (setq fk (strcat (wc:key (cadr sgm)) "|" (wc:key (car sgm)))
            f  (assoc fk paircnt)
      )
    )
    (if f
      (setq paircnt (subst (cons (car f) (1+ (cdr f))) f paircnt))
      (setq paircnt (cons (cons fk 1) paircnt))
    )
  )
  (setq bndpts nil)
  (foreach sgm segs
    (if (equal (caddr sgm) farlay)
      (progn
        (setq f (assoc (strcat (wc:key (car sgm)) "|" (wc:key (cadr sgm)))
                       paircnt))
        (if (not f)
          (setq f (assoc (strcat (wc:key (cadr sgm)) "|" (wc:key (car sgm)))
                         paircnt))
        )
        (if (and f (= 1 (cdr f)))
          (foreach p (list (car sgm) (cadr sgm))
            (if (not (wc:member-key p chainkeys))
              (setq bndpts (cons p bndpts))
            )
          )
        )
      )
    )
  )

  ;; merge + dedupe far points, order by projected arc length
  (setq seen nil ordered nil)
  (foreach f (append farpts (mapcar 'caddr rungs) bndpts)
    (setq fk (wc:key f))
    (if (not (member fk seen))
      (setq seen (cons fk seen)
            ordered (cons f ordered)
      )
    )
  )
  (setq devpts (mapcar '(lambda (f) (wc:dev-point f pts s)) ordered)
        ;; drop points projecting far off the chain (past the band ends,
        ;; end blocks, unrelated marks caught in the selection) and points
        ;; developing at/above the straight edge (end-clamp artifacts —
        ;; the far side always lies below the straightened edge)
        devpts (vl-remove-if
                 '(lambda (dp)
                    (or (> (cadddr dp) (* 1.75 w))
                        (> (cadr dp) (* -0.05 w))
                        (< (car dp) (* -0.25 w))
                        (> (car dp) (+ (car (reverse s)) (* 0.25 w)))))
                 devpts)
        devpts (vl-sort devpts '(lambda (a b) (< (caddr a) (caddr b))))
  )
  (if (< (length devpts) 2)
    (progn (princ "\nCould not develop the opposite side.") (exit))
  )

  ;; ---- 8s. stair sections ----------------------------------------------
  ;; each windowed stair section is developed as one rigid piece: the
  ;; whole outline path is rotated by the chord direction of the chosen
  ;; chain across the section and anchored at the section entry, so
  ;; treads come out level with their exact lengths and every riser
  ;; keeps its exact rise (validated against a hand-drawn example:
  ;; every segment length is preserved to the hundredth)
  (setq synth nil stkeys nil stairrng nil)
  (if ssstairs
    (progn
      ;; candidate segments: in the window, on the far side's layer,
      ;; outline (drawn once), touching neither end of the chain
      (setq stsegs nil)
      (foreach sgm segs
        (if (and (ssmemb (cadddr sgm) ssstairs)
                 (equal (caddr sgm) farlay)
                 (= 1 (wc:mult sgm paircnt))
                 (not (wc:member-key (car sgm) chainkeys))
                 (not (wc:member-key (cadr sgm) chainkeys)))
          (setq stsegs (cons (list (car sgm) (cadr sgm)) stsegs))
        )
      )
      ;; process each connected stair path
      (while stsegs
        ;; flood-fill one connected component
        (setq comp (list (car stsegs))
              compkeys (list (wc:key (car (car stsegs)))
                             (wc:key (cadr (car stsegs))))
              stsegs (cdr stsegs)
              grow T
        )
        (while grow
          (setq grow nil strest nil)
          (foreach sgm stsegs
            (if (or (member (wc:key (car sgm)) compkeys)
                    (member (wc:key (cadr sgm)) compkeys))
              (setq comp (cons sgm comp)
                    compkeys (cons (wc:key (car sgm))
                                   (cons (wc:key (cadr sgm)) compkeys))
                    grow T
              )
              (setq strest (cons sgm strest))
            )
          )
          (setq stsegs (reverse strest))
        )
        ;; open ends of the path = nodes with a single incident segment
        (setq nodes2 (wc:build-nodes comp) endpts nil)
        (foreach e nodes2
          (if (= 2 (length e))               ; (key idx) -> one segment
            (progn
              (setq sgm (nth (cadr e) comp))
              (setq endpts (cons (if (equal (wc:key (car sgm)) (car e))
                                   (car sgm)
                                   (cadr sgm))
                                 endpts))
            )
          )
        )
        (if (>= (length endpts) 2)
          (progn
            ;; entry = the end nearest the chain start (smaller proj-s)
            (setq endpts (vl-sort endpts
                           '(lambda (a b) (< (caddr (wc:dev-point a pts s))
                                             (caddr (wc:dev-point b pts s))))))
            (setq stentry (car endpts)
                  dpa (wc:dev-point stentry pts s)
            )
            ;; walk the path from the entry
            (setq stpath (list stentry) usedj nil stpt stentry stgo T)
            (while stgo
              (setq stcand nil)
              (foreach j (cdr (assoc (wc:key stpt) nodes2))
                (if (not (member j usedj)) (setq stcand j))
              )
              (if stcand
                (setq usedj (cons stcand usedj)
                      stpt (wc:other-end (nth stcand comp) stpt)
                      stpath (cons stpt stpath)
                )
                (setq stgo nil)
              )
            )
            (setq stpath (reverse stpath)
                  se (caddr (wc:dev-point (car (reverse stpath)) pts s))
                  pA (wc:chain-at (caddr dpa) pts s)
                  pB (wc:chain-at se pts s)
                  ;; arc-length span this stair section covers, so darts
                  ;; are not placed on it (handled by hand afterward)
                  stairrng (cons (list (min (caddr dpa) se)
                                       (max (caddr dpa) se))
                                 stairrng)
            )
            (if (> (distance pA pB) 1.0e-6)
              (progn
                ;; rotate the section by the chain chord, anchor at entry
                (setq stang (- (wc:dir pA pB))
                      stca (cos stang)
                      stsn (sin stang)
                      sttot 0.0
                      stprev (car stpath)
                )
                (foreach stq (cdr stpath)
                  (setq sttot (+ sttot (distance stprev stq)) stprev stq)
                )
                (setq stlen 0.0 stprev (car stpath))
                (foreach stq stpath
                  (setq stlen (+ stlen (distance stprev stq))
                        stprev stq
                        stdx (- (car stq) (car stentry))
                        stdy (- (cadr stq) (cadr stentry))
                  )
                  (setq synth
                    (cons (list (+ (car dpa) (- (* stdx stca) (* stdy stsn)))
                                (+ (cadr dpa) (+ (* stdx stsn) (* stdy stca)))
                                (+ (caddr dpa)
                                   (if (> sttot 1.0e-9)
                                     (* (- se (caddr dpa)) (/ stlen sttot))
                                     0.0))
                                0.0
                                stq)
                          synth)
                        stkeys (cons (wc:key stq) stkeys)
                  )
                )
              )
            )
          )
        )
      )
      ;; splice: synthesized stair points replace their projected twins
      (if synth
        (setq devpts (vl-remove-if
                       '(lambda (dp) (member (wc:key (nth 4 dp)) stkeys))
                       devpts)
              devpts (vl-sort (append devpts synth)
                              '(lambda (a b) (< (caddr a) (caddr b))))
        )
      )
    )
  )

  ;; bottom line lengths: along the original curve vs as developed
  (setq botb 0.0 bota 0.0 dp1 (car devpts))
  (foreach dp2 (cdr devpts)
    (setq botb (+ botb (distance (nth 4 dp1) (nth 4 dp2)))
          bota (+ bota (distance (list (car dp1) (cadr dp1))
                                 (list (car dp2) (cadr dp2))))
          dp1 dp2
    )
  )

  ;; ---- 8b. feature emission -------------------------------------------
  ;; two variants are produced:
  ;;   A) minimum darts+inserts: one conservative pass at the base
  ;;      threshold (fewest, widest features)
  ;;   B) target <1%: the threshold is refined until the after-cuts
  ;;      residual (bottom-after - darts + inserts vs bottom-before)
  ;;      aims under 1% of the original bottom length
  ;; dart mouths are capped at 4" on the bottom line in both (larger
  ;; corrections split across consecutive rungs)
  (setq wmin (max (* 0.04 w) (/ total maxfeat)))

  (setq rr (wc:emit idebt rungs pts s wmin maxfeat nil)
        featsb (car rr)                            ; minimum variant
        residb (+ (- bota botb) (cadr rr))
  )

  (setq pass 0 stop nil)
  (while (not stop)
    (setq rr (wc:emit idebt rungs pts s wmin maxfeat T)
          feats (car rr)
          resid (+ (- bota botb) (cadr rr))
          pass (1+ pass)
    )
    (if (or (<= (abs resid) (* 0.01 botb))         ; under the 1% target
            (>= (length feats) maxfeat)            ; no room for more
            (<= wmin (* 0.0401 w))                 ; threshold bottomed out
            (>= pass 10)
        )
      (setq stop T)
      (setq wmin (max (* 0.04 w) (* wmin 0.6)))    ; more, smaller features
    )
  )

  ;; darts landing inside a windowed stair section are dropped (the
  ;; stairs are developed rigidly and get their darts added by hand);
  ;; inserts are left in place
  (if stairrng
    (progn
      (setq feats  (vl-remove-if
                     '(lambda (f) (and (= 1 (caddr f))
                                       (wc:instair (car f) stairrng)))
                     feats)
            featsb (vl-remove-if
                     '(lambda (f) (and (= 1 (caddr f))
                                       (wc:instair (car f) stairrng)))
                     featsb)
            fsum 0.0
      )
      (foreach f feats
        (setq fsum (+ fsum (if (= 1 (caddr f)) (- (cadr f)) (cadr f))))
      )
      (setq resid (+ (- bota botb) fsum) fsum 0.0)
      (foreach f featsb
        (setq fsum (+ fsum (if (= 1 (caddr f)) (- (cadr f)) (cadr f))))
      )
      (setq residb (+ (- bota botb) fsum))
    )
  )

  ;; ---- 9. placement below the selection --------------------------------
  (setq minx 1.0e18 miny 1.0e18 maxx -1.0e18 maxy -1.0e18)
  (foreach sg segs
    (foreach wpt (list (car sg) (cadr sg))
      (setq minx (min minx (car wpt)) miny (min miny (cadr wpt))
            maxx (max maxx (car wpt)) maxy (max maxy (cadr wpt))
      )
    )
  )
  (setq x0 minx
        y0 (- miny (* 1.5 w))          ; straight edge sits here
  )

  ;; ---- 10. draw ----------------------------------------------------------
  (command "_.UNDO" "_Begin")
  (setq inundo T)
  (setq lay2 (cal:ensure-layer "AIR-B" 1))
  (cal:ensure-layer "DIMENSION" 3)

  ;; two stacked drawings: the <1% target version, and below it the
  ;; minimum darts+inserts version
  (setq toplen (car (reverse s))
        nmk 0
        vy y0
  )
  (foreach vr (list (list feats resid "TARGET <1%")
                    (list featsb residb "MINIMUM DARTS+INSERTS"))
    (setq vfeats (car vr)
          vresid (cadr vr)
          vlab (caddr vr)
    )

    ;; variant label above the straight edge
    (cal:text (list x0 (+ vy (* 0.6 w))) (* 0.4 w) vlab "DIMENSION")

    ;; straight (chosen) edge
    (setq sgp (list (+ x0 (car s)) vy)
          wpt (list (+ x0 toplen) vy)
    )
    (wc:line sgp wpt lay2)

    ;; darts of this variant as (center-x mouth-width), sorted by x
    (setq dfeats nil)
    (foreach f vfeats
      (if (= 1 (caddr f))
        (setq dfeats (cons (list (car f) (cadr f)) dfeats))
      )
    )
    (setq dfeats (vl-sort dfeats '(lambda (a b) (< (car a) (car b)))))

    ;; far edge: bottom line split at each dart mouth so no segment spans
    ;; the mouth (the base under the dart is erased); the dart legs drawn
    ;; below close each gap, tied to the bottom line at the feet
    (foreach run (wc:notch devpts dfeats)
      (if (> (length run) 1)
        (wc:pline (mapcar '(lambda (p) (list (+ x0 (car p)) (+ vy (cadr p))))
                          run)
                  farlay nil)
      )
    )

    ;; band ends (vertical closing lines)
    (setq enda (list (+ x0 (car (car devpts))) (+ vy (cadr (car devpts))))
          endb (list (+ x0 (car (car (reverse devpts))))
                     (+ vy (cadr (car (reverse devpts)))))
    )
    (wc:line (list (car enda) vy) enda lay2)
    (wc:line (list (car endb) vy) endb lay2)

    ;; darts and inserts
    (foreach f vfeats
      (setq x (+ x0 (car f))
            cw (cadr f)
            ;; local band depth = the actual bottom line at this feature
            ld (max (- (wc:depth-at (car f) devpts)) (* 0.2 w))
            ;; apex/slit stop line, measured down from the straightened
            ;; edge.  With a tile height, tile+1" is the HIGHEST the apex
            ;; may rise (closest it may come to the straight edge); the
            ;; apex sits on that line, dropping lower only where the band
            ;; is too shallow to reach it (kept 1" above the foot).
            ;; Without a tile height, the default 42% of the local depth.
            hz (if tileh (min (+ tileh 1.0) (- ld 1.0)) (* 0.42 ld))
            yb (- vy ld)                          ; local far edge
      )
      (if (= 1 (caddr f))
        (progn                                    ; DART: V legs, feet on
          ;; the bottom line, apex at the stop line; the mouth base was
          ;; erased by splitting the far-edge polyline there
          (wc:line (list x (- vy hz))
                   (list (- x (/ cw 2.0))
                         (+ vy (wc:depth-at (- (car f) (/ cw 2.0)) devpts)))
                   lay2)
          (wc:line (list x (- vy hz))
                   (list (+ x (/ cw 2.0))
                         (+ vy (wc:depth-at (+ (car f) (/ cw 2.0)) devpts)))
                   lay2)
        )
        (progn                                    ; INSERT: slit + sliver below
          (wc:line (list x yb) (list x (- vy hz)) lay2)
          ;; sliver piece: 1" wide at the top, the gap width at the
          ;; bottom, sides about 1" longer than the slit it goes into
          (setq dl (+ (- ld hz) 1.0)              ; slit length + 1"
                cw (max cw 1.0)
                yb (- vy ld (* 0.2 w))            ; sliver top
                dr (- yb dl)                      ; sliver bottom
          )
          (wc:pline
            (list (list (- x (/ cw 2.0)) dr) (list (+ x (/ cw 2.0)) dr)
                  (list (+ x 0.5) yb) (list (- x 0.5) yb)
            )
            lay2 T
          )
        )
      )
    )

    ;; carry-along marks: selected segments on OTHER layers than the
    ;; band structure (reference crosses, datum lines, existing cut
    ;; marks) are developed point-by-point onto their own layer
    (setq k 0)
    (foreach sgm segs
      (if (and (not (member (caddr sgm) bandlays))
               (not (member k ids))
               (not (member k farids))
               (not (member k conns)))
        (progn
          (setq dp1 (wc:dev-point (car sgm) pts s)
                dp2 (wc:dev-point (cadr sgm) pts s)
          )
          ;; keep only marks that actually sit on/near the band
          (if (and (<= (cadddr dp1) (* 1.75 w))
                   (<= (cadddr dp2) (* 1.75 w)))
            (progn
              (wc:line (list (+ x0 (car dp1)) (+ vy (cadr dp1)))
                       (list (+ x0 (car dp2)) (+ vy (cadr dp2)))
                       (caddr sgm))
              (setq nmk (1+ nmk))
            )
          )
        )
      )
      (setq k (1+ k))
    )

    ;; height dimensions at both ends
    (wc:vdim (list (car enda) vy) enda (- (car enda) (* 1.2 w)) "DIMENSION")
    (wc:vdim (list (car endb) vy) endb (+ (car endb) (* 1.2 w)) "DIMENSION")

    ;; length summary to the right of the drawing: top line, bottom line
    ;; before (along the original curve) and after (as drawn), the delta
    ;; the flattened bottom line is off by, and the residual once the
    ;; darts close / inserts fill (target: under 1%)
    (setq tx (+ (car endb) (* 2.0 w))
          th (* 0.35 w)
    )
    (cal:text (list tx vy) th
             (strcat "TOP LINE:      " (rtos toplen 2 2)
                     "  (" (rtos toplen 4 8) ")")
             "DIMENSION")
    (cal:text (list tx (- vy (* 0.55 w))) th
             (strcat "BOTTOM BEFORE: " (rtos botb 2 2)
                     "  (" (rtos botb 4 8) ")")
             "DIMENSION")
    (cal:text (list tx (- vy (* 1.10 w))) th
             (strcat "BOTTOM AFTER:  " (rtos bota 2 2)
                     "  (" (rtos bota 4 8) ")")
             "DIMENSION")
    (cal:text (list tx (- vy (* 1.65 w))) th
             (strcat "DELTA:         " (rtos (- bota botb) 2 2)
                     "  (" (rtos (* 100.0 (/ (abs (- bota botb)) botb)) 2 2)
                     "%" (if (< bota botb) " short)" " long)"))
             "DIMENSION")
    (cal:text (list tx (- vy (* 2.20 w))) th
             (strcat "AFTER CUTS:    " (rtos vresid 2 2)
                     "  (" (rtos (* 100.0 (/ (abs vresid) botb)) 2 2)
                     "%)  [target <1%]"
                     (if (> (abs vresid) (* 0.01 botb)) "  ** OVER TARGET **" ""))
             "DIMENSION")

    ;; next variant goes below this one
    (setq vy (- vy (* 5.0 w)))
  )

  (command "_.UNDO" "_End")
  (setq inundo nil)
  (setvar "CLAYER" oldlay)

  ;; ---- 11. report ---------------------------------------------------------
  (princ (strcat "\nWCALST: developed length " (rtos toplen 2 2)
                 ", band width " (rtos w 2 2) ", two drawings:"))
  (foreach vr (list (list feats resid "target <1%")
                    (list featsb residb "minimum cuts"))
    (setq dl 0 dr 0)
    (foreach f (car vr) (if (= 1 (caddr f)) (setq dl (1+ dl)) (setq dr (1+ dr))))
    (princ (strcat "\n  " (caddr vr) ": " (itoa dl) " dart(s), "
                   (itoa dr) " insert(s) (max " (itoa maxfeat)
                   "), after cuts " (rtos (cadr vr) 2 2)
                   " (" (rtos (* 100.0 (/ (abs (cadr vr)) botb)) 2 2) "%)"
                   (if (> (abs (cadr vr)) (* 0.01 botb)) " OVER TARGET" "")))
  )
  (princ (strcat "\n  top line " (rtos toplen 2 2)
                 ", bottom before " (rtos botb 2 2)
                 ", bottom after " (rtos bota 2 2)
                 ", delta " (rtos (- bota botb) 2 2)
                 " (" (rtos (* 100.0 (/ (abs (- bota botb)) botb)) 2 2)
                 "%)."))
  (if (> nmk 0)
    (princ (strcat " " (itoa (/ nmk 2)) " reference mark(s) carried along."))
  )
  (princ)
)

(princ "\nWCALST loaded -- select the band, pick the side to straighten.")
(princ)


;;; ======================================================================
;;; >>> xftconv.lsp
;;; ======================================================================

;;; ===================================================================
;;;  XFTCONV.lsp   -  Leica XFT / DXF survey import cleanup
;;;  AutoCAD 2018
;;;
;;;  Command:  XFTCONV   - highlight the import, that is the only answer
;;;                        it needs
;;;
;;; SHARED BUILD: requires CALOFIN-LIB.lsp (load via CALOFIN-LOADER.lsp).
;;; Generic helpers live there under cal: - see STANDARDS.md.
;;;
;;;  What it does, to the objects you highlight:
;;;    1. scales the whole selection by 12 (feet -> inches), about the
;;;       middle of everything highlighted
;;;    2. finds every Leica point marker in the selection
;;;         - the X made of 2 crossing LINEs on layer LEICA_POINT
;;;           (a POINT on that layer works too)
;;;         - its name TEXT / MTEXT on layer LEICA_POINT_NAME  ("P22")
;;;    3. replaces each one with an "ab_pt" block on layer POINTS,
;;;       attribute "number" set to the point number with the letter
;;;       prefix stripped ("P22" -> "22")
;;;    4. erases the old marker lines and the old name text
;;;    5. erases every other TEXT / MTEXT left in the selection - the
;;;       numbers live in the block attributes now, so the rest is noise
;;;
;;;  Non-text geometry is scaled and otherwise left alone.  The whole
;;;  run is one UNDO step.
;;; ===================================================================


;;; -------------------------------------------------------------------
;;;  SETTINGS - edit these if the export or the template ever changes
;;; -------------------------------------------------------------------

(setq *xft-version* "v1.3") ; printed on load and at command start so a
                             ; support screenshot says which copy is loaded

(setq
  *xft-scale*        12.0                 ; scale factor applied to the selection
  *xft-marker-layer* "LEICA_POINT"        ; layer of the X marker (wildcards ok)
  *xft-name-layer*   "LEICA_POINT_NAME"   ; layer of the point name text
  *xft-block*        "ab_pt"              ; block that replaces the marker
  *xft-block-layer*  "POINTS"             ; layer the block is inserted on
  *xft-att-tag*      "number"             ; attribute tag holding the number
  *xft-att-style*    "Attributes"         ; text style for the attribute
  *xft-att-height*   4.0                  ; attribute height (as shown on the sample)
  *xft-att-offset*   '(0.8697246 -3.5316825) ; attribute offset from the point
  *xft-name-reach*   6.0                  ; name search radius = this x text height
  *xft-fuzz*         1e-4                 ; tolerance for "same point"
  *xft-purge-text*   t                    ; erase every TEXT/MTEXT left in the
                                          ; selection once the points are done
)

(vl-load-com)   ; getboundingbox, for the middle of the selection


;;; -------------------------------------------------------------------
;;;  small helpers
;;; -------------------------------------------------------------------

(defun xft:mid (a b)
  (list (/ (+ (car a) (car b)) 2.0)
        (/ (+ (cadr a) (cadr b)) 2.0)
        (/ (+ (caddr a) (caddr b)) 2.0)
  )
)

(defun xft:same (a b)                     ; same location within fuzz
  (< (cal:d2 a b) (* *xft-fuzz* *xft-fuzz*))
)

(defun xft:onlayer (ed pattern)
  (wcmatch (strcase (cdr (assoc 8 ed))) (strcase pattern))
)

;; strip the usual MTEXT formatting codes so "\A1;P22" comes back as "P22"
(defun xft:plain (s / out i c nxt n)
  (setq out "" i 1 n (strlen s))
  (while (<= i n)
    (setq c (substr s i 1))
    (cond
      ((= c "\\")
       (setq nxt (strcase (substr s (1+ i) 1)))
       (cond
         ((member nxt '("P" "X"))                 ; line break / paragraph
          (setq out (strcat out " ") i (+ i 2)))
         ((member nxt '("L" "O" "K"))             ; under/over/strike on-off
          (setq i (+ i 2)))
         ((wcmatch nxt "[ACFHQTW]")               ; codes closed by ";"
          (setq i (+ i 2))
          (while (and (<= i n) (/= (substr s i 1) ";")) (setq i (1+ i)))
          (setq i (1+ i)))
         (t (setq out (strcat out (substr s (1+ i) 1)) i (+ i 2)))
       )
      )
      ((member c '("{" "}")) (setq i (1+ i)))
      (t (setq out (strcat out c) i (1+ i)))
    )
  )
  out
)

;; "P22" -> "22"   "22" -> "22"   "STA" -> "STA"
(defun xft:number (s / i n c)
  (setq s (cal:trim (xft:plain s)) n (strlen s) i 1)
  (while (and (<= i n)
              (setq c (ascii (substr s i 1)))
              (or (< c 48) (> c 57)))
    (setq i (1+ i)))
  (if (<= i n) (substr s i) s)
)

;; where a text entity "sits".  a justified TEXT is really located at its
;; alignment point (11); on MTEXT group 11 is the direction vector, not a
;; point, so MTEXT always uses its insertion point (10).
(defun xft:txtpt (ed)
  (if (and (= "TEXT" (cdr (assoc 0 ed)))
           (assoc 11 ed)
           (or (/= 0 (cdr (assoc 72 (append ed '((72 . 0))))))
               (/= 0 (cdr (assoc 73 (append ed '((73 . 0))))))))
    (cdr (assoc 11 ed))
    (cdr (assoc 10 ed))
  )
)

;; centre of the box around everything that was highlighted.  ActiveX
;; getboundingbox is the only thing that knows the real extents of an arc,
;; a spline or a block, so it does the work; if it will not answer for an
;; object, that object's own definition points are used instead.
(defun xft:centre (ss / i en mn mx lo hi ed pair)
  (setq i 0 lo nil hi nil)
  (while (< i (sslength ss))
    (setq en (ssname ss i))
    (if (not (vl-catch-all-error-p
               (vl-catch-all-apply
                 '(lambda ()
                    (vla-getboundingbox (vlax-ename->vla-object en) 'mn 'mx)))))
      (setq lo (if lo (mapcar 'min lo (vlax-safearray->list mn)) (vlax-safearray->list mn))
            hi (if hi (mapcar 'max hi (vlax-safearray->list mx)) (vlax-safearray->list mx)))
      ;; fallback - whatever points the entity carries itself
      (progn
        (setq ed (entget en))
        (foreach pair ed
          (if (and (member (car pair) '(10 11))
                   (listp (cdr pair))
                   (= 3 (length (cdr pair))))
            (setq lo (if lo (mapcar 'min lo (cdr pair)) (cdr pair))
                  hi (if hi (mapcar 'max hi (cdr pair)) (cdr pair)))
          )
        )
      )
    )
    (setq i (1+ i))
  )
  (if (and lo hi)
    (mapcar '(lambda (a b) (/ (+ a b) 2.0)) lo hi)
    (list 0.0 0.0 0.0)
  )
)

;; add ename to the marker group at ctr, or start a new group
(defun xft:collect (groups ctr en / out hit)
  (setq out '() hit nil)
  (foreach g groups
    (if (and (not hit) (xft:same (car g) ctr))
      (setq out (cons (cons (car g) (cons en (cdr g))) out) hit t)
      (setq out (cons g out))
    )
  )
  (if hit (reverse out) (cons (list ctr en) groups))
)


;;; -------------------------------------------------------------------
;;;  drawing setup - make sure the layer, style and block are there
;;; -------------------------------------------------------------------

(defun xft:locked (lname / tb)
  (and (setq tb (tblsearch "LAYER" lname))
       (= 4 (logand 4 (cdr (assoc 70 tb)))))
)

(defun xft:style ()
  (if (tblsearch "STYLE" *xft-att-style*)
    *xft-att-style*
    (getvar "TEXTSTYLE")
  )
)

;; build ab_pt the same way the template has it, if it is missing
(defun xft:ensure-block ( / sty)
  (if (not (tblsearch "BLOCK" *xft-block*))
    (progn
      (setq sty (xft:style))
      (entmake (list '(0 . "BLOCK")
                     '(100 . "AcDbEntity")
                     '(8 . "0")
                     '(100 . "AcDbBlockBegin")
                     (cons 2 *xft-block*)
                     '(70 . 2)
                     '(10 0.0 0.0 0.0)
                     (cons 3 *xft-block*)
                     '(1 . "")))
      (entmake '((0 . "POINT")
                 (100 . "AcDbEntity")
                 (8 . "0")
                 (100 . "AcDbPoint")
                 (10 0.0 0.0 0.0)))
      (entmake (list '(0 . "ATTDEF")
                     '(100 . "AcDbEntity")
                     '(8 . "0")
                     '(100 . "AcDbText")
                     '(10 1.0 -2.0 0.0)
                     '(40 . 1.0)
                     '(1 . "0")
                     (cons 7 sty)
                     '(100 . "AcDbAttributeDefinition")
                     '(3 . "Type_Point_Number")
                     (cons 2 *xft-att-tag*)
                     '(70 . 4)))
      (entmake '((0 . "ENDBLK") (100 . "AcDbEntity") (8 . "0") (100 . "AcDbBlockEnd")))
      (princ (strcat "\n  block \"" *xft-block* "\" was not in this drawing - created it."))
    )
  )
  (tblsearch "BLOCK" *xft-block*)
)


;;; -------------------------------------------------------------------
;;;  insert one replacement point
;;; -------------------------------------------------------------------

(defun xft:insert (pt num / apt)
  (setq apt (list (+ (car pt) (car  *xft-att-offset*))
                  (+ (cadr pt) (cadr *xft-att-offset*))
                  (caddr pt)))
  (entmake (list '(0 . "INSERT")
                 '(100 . "AcDbEntity")
                 (cons 8 *xft-block-layer*)
                 '(100 . "AcDbBlockReference")
                 '(66 . 1)
                 (cons 2 *xft-block*)
                 (cons 10 pt)
                 '(41 . 1.0) '(42 . 1.0) '(43 . 1.0)
                 '(50 . 0.0)))
  (entmake (list '(0 . "ATTRIB")
                 '(100 . "AcDbEntity")
                 '(8 . "0")
                 '(100 . "AcDbText")
                 (cons 10 apt)
                 (cons 40 *xft-att-height*)
                 (cons 1 num)
                 (cons 7 (xft:style))
                 '(100 . "AcDbAttribute")
                 (cons 2 *xft-att-tag*)
                 '(70 . 0)))
  (entmake (list '(0 . "SEQEND")
                 '(100 . "AcDbEntity")
                 (cons 8 *xft-block-layer*)))
)


;;; -------------------------------------------------------------------
;;;  XFTCONV
;;; -------------------------------------------------------------------

(defun c:XFTCONV ( / *error* xft:restore oscm osos osclay undone
                     ss base i en ed typ
                     markers names g nm e
                     ctr best bestd bestr rank txth d reach num
                     nmade nblank nleft)

  (defun xft:restore ()
    (if oscm   (setvar "CMDECHO" oscm))
    (if osos   (setvar "OSMODE"  osos))
    (if osclay (setvar "CLAYER"  osclay))
  )

  (defun *error* (msg)
    (if (and msg (not (wcmatch (strcase msg) "*BREAK*,*CANCEL*,*QUIT*,*EXIT*")))
      (princ (strcat "\nXFTCONV error: " msg)))
    (while (> (getvar "CMDACTIVE") 0) (command))   ; back out of SCALE etc.
    (xft:restore)
    (if undone (command "_.UNDO" "_End"))
    (princ "\nNothing was left half done - use U to roll the run back.")
    (princ)
  )

  (setq oscm   (getvar "CMDECHO")
        osos   (getvar "OSMODE")
        osclay (getvar "CLAYER"))

  (princ (strcat "\nXFTCONV " *xft-version*
                 " - scale the survey and swap the Leica points for blocks."))

  ;; ---- selection -------------------------------------------------
  ;; the only prompt there is.  the scale factor and the base point used
  ;; to be asked for, and the staged Back that moved between them went
  ;; with them - it is always x12 about the middle of the selection now,
  ;; so there is nothing left to step back to.
  (princ "\nSelect the imported survey objects (Enter = everything in this space): ")
  (setq ss (ssget))
  (if (not ss)
    (setq ss (ssget "_X" (list (cons 410 (getvar "CTAB")))))
  )

  (if (not ss)
    (progn (princ "\nNothing to work on.") (xft:restore) (princ))
    (progn

      ;; ---- locked layers would break the swap --------------------
      (if (or (xft:locked *xft-marker-layer*)
              (xft:locked *xft-name-layer*)
              (xft:locked *xft-block-layer*))
        (progn
          (princ "\nUnlock LEICA_POINT / LEICA_POINT_NAME / POINTS first, then run XFTCONV again.")
          (xft:restore)
          (princ)
        )
        (progn

          (setvar "CMDECHO" 0)
          (setvar "OSMODE" 0)
          (command "_.UNDO" "_BEgin")
          (setq undone t)

          ;; ---- 0. the layer and the block have to be there --------
          (cal:ensure-layer *xft-block-layer* 6)
          (xft:ensure-block)

          ;; ---- 1. scale x12 about the middle of what was picked ---
          ;; getboundingbox works in WCS, SCALE wants the current UCS
          (setq base (trans (xft:centre ss) 0 1))
          (if (/= *xft-scale* 1.0)
            (progn
              (princ (strcat "\nScaling " (itoa (sslength ss)) " objects by "
                             (rtos *xft-scale* 2 4) " about the middle of the selection ..."))
              (command "_.SCALE" ss "" base *xft-scale*)
            )
          )

          ;; ---- 2. sort the selection into markers and names -------
          (setq markers '() names '() i 0)
          (while (< i (sslength ss))
            (setq en  (ssname ss i)
                  ed  (entget en)
                  typ (cdr (assoc 0 ed)))
            (cond
              ;; name text first - LEICA_POINT would also match its layer
              ((and (member typ '("TEXT" "MTEXT"))
                    (xft:onlayer ed *xft-name-layer*))
               (setq names (cons (list (xft:txtpt ed)
                                       (cdr (assoc 1 ed))
                                       (cdr (assoc 40 ed))
                                       en
                                       nil)
                                 names)))
              ;; the X marker - both lines share the same midpoint
              ((and (= typ "LINE") (xft:onlayer ed *xft-marker-layer*))
               (setq markers (xft:collect markers
                                          (xft:mid (cdr (assoc 10 ed)) (cdr (assoc 11 ed)))
                                          en)))
              ;; some exports drop a plain POINT instead
              ((and (= typ "POINT") (xft:onlayer ed *xft-marker-layer*))
               (setq markers (xft:collect markers (cdr (assoc 10 ed)) en)))
            )
            (setq i (1+ i))
          )

          ;; ---- 3. match each marker to its name ------------------
          ;; the export stacks the name right above the marker, so a
          ;; name in the same column wins over a merely closer one -
          ;; that keeps tight clusters from stealing each other's tags
          (setq nmade 0 nblank 0)
          (foreach g markers
            (setq ctr   (car g)
                  best  nil
                  bestd nil
                  bestr nil)
            (foreach nm names
              (if (not (nth 4 nm))
                (progn
                  (setq txth  (if (and (nth 2 nm) (> (nth 2 nm) 0.0)) (nth 2 nm) 1.0)
                        reach (* *xft-name-reach* txth)
                        d     (cal:d2 ctr (car nm))
                        rank  (if (<= (abs (- (car (car nm)) (car ctr))) (* 0.5 txth)) 0 1))
                  (if (and (< d (* reach reach))
                           (or (not best)
                               (< rank bestr)
                               (and (= rank bestr) (< d bestd))))
                    (setq best nm bestd d bestr rank)
                  )
                )
              )
            )
            (if best
              (progn
                (setq num (xft:number (nth 1 best)))
                (setq names (subst (list (car best) (nth 1 best) (nth 2 best) (nth 3 best) t)
                                   best names))
              )
              (setq num "" nblank (1+ nblank))
            )
            ;; ---- 4. new point in, old marker out ------------------
            (xft:insert ctr num)
            (foreach e (cdr g) (entdel e))
            (if best (entdel (nth 3 best)))
            (setq nmade (1+ nmade))
          )

          ;; ---- 5. every other bit of text in the selection goes ---
          ;; the numbers now live in the block attributes, so anything
          ;; still written as text is leftover import noise.  entget
          ;; comes back nil on what step 4 already erased, which keeps
          ;; entdel from toggling those back into the drawing.
          (setq nleft 0)
          (if *xft-purge-text*
            (progn
              (setq i 0)
              (while (< i (sslength ss))
                (setq en (ssname ss i)
                      ed (entget en))
                (if (and ed (member (cdr (assoc 0 ed)) '("TEXT" "MTEXT")))
                  (progn (entdel en) (setq nleft (1+ nleft)))
                )
                (setq i (1+ i))
              )
            )
          )

          (command "_.UNDO" "_End")
          (setq undone nil)
          (xft:restore)

          ;; ---- report --------------------------------------------
          (princ (strcat "\n"
                         (itoa nmade) " point(s) replaced with \"" *xft-block* "\"."))
          (if (> nblank 0)
            (princ (strcat "\n" (itoa nblank)
                           " had no name text nearby - inserted with a blank number.")))
          (if (> nleft 0)
            (princ (strcat "\n" (itoa nleft) " leftover text object(s) erased.")))
          (princ)
        )
      )
    )
  )
  (princ)
)


;;; -------------------------------------------------------------------
;;;  make sure the pieces exist as soon as the file loads
;;; -------------------------------------------------------------------

(defun c:XFTCONV-SETUP ()
  (cal:ensure-layer *xft-block-layer* 6)
  (xft:ensure-block)
  (princ (strcat "\nLayer \"" *xft-block-layer* "\" and block \"" *xft-block* "\" are ready."))
  (princ)
)

(princ (strcat "\nXFTCONV.lsp " *xft-version*
               " loaded.  Type XFTCONV to scale a survey import and swap its points."))
(princ)


;;; ======================================================================
;;; >>> XYPLOT.lsp
;;; ======================================================================

;;; ==========================================================================
;;; XYPLOT.lsp  --  Plot an X/Y sheet, twice: as points, and dimensioned
;;; --------------------------------------------------------------------------
;;; For AutoCAD 2018 and later (plain AutoLISP, no external libraries).
;;;
;;; Commands:  XYPLOT      draw both graphs from a spreadsheet of X/Y offsets
;;;            XYPLOTVER   print the loaded version
;;;
;;; SHARED BUILD: requires CALOFIN-LIB.lsp (load via CALOFIN-LOADER.lsp).
;;; Generic helpers live there under cal: - see STANDARDS.md.
;;;
;;; ABCDEF's sister command, for the survey that arrives already reduced.
;;; Where ABCDEF is handed four tape distances per point and has to work out
;;; where the point is, XYPLOT is handed the answer - an X and a Y off one
;;; origin - and only has to draw it.  The sheet is
;;;
;;;     POINT NAME | X | Y
;;;
;;; and the command asks for one thing the sheet cannot say: where the
;;; origin goes in the drawing.  Pick that point and both graphs are built
;;; around it.
;;;
;;; TWO GRAPHS, side by side:
;;;
;;;   GRAPH 1 - THE POINTS AS GIVEN.  Every point at its X/Y off the origin,
;;;     labelled with its name from the sheet, drawn as an "ab_pt" block on
;;;     layer POINTS.  That is the same survey point every other calofin
;;;     tool reads, so ABHD, CABHD, ABFIND, BPCALLOUT and LHD pick this
;;;     import up untouched - and the run ends by offering ABHD the set.
;;;
;;;   GRAPH 2 - THE SAME POINTS, DIMENSIONED LINEARLY.  A second copy off to
;;;     the right, with the X offsets dimensioned as one continuous chain
;;;     along the bottom and the Y offsets as another down the left side,
;;;     each dimension's extension lines running back to the point it
;;;     belongs to.  Graph 1 shows you the shape; graph 2 shows you the
;;;     numbers the shape was built from, in the order they run.
;;;
;;; Only graph 1 carries ab_pt blocks.  Graph 2's markers are plain POINTs
;;; on a XYPLOT layer, deliberately: two ab_pt copies of one survey in one
;;; drawing would hand ABHD the same pool twice and it would try to fit a
;;; perimeter around both.
;;;
;;; The dimensions measure the drawn geometry rather than reprinting the
;;; sheet's text, so a value that did not survive the trip shows up as a
;;; dimension that disagrees with its own column in the report.  They land
;;; on layer DIMENSION in the drawing's current dimension style, the same
;;; as AUTODIM's and WCALST's.
;;;
;;; X and Y are read as architectural feet-inches or as plain decimal
;;; inches, negatives included - 12'-3 1/2", -4'-0", 37.25, 3 1/2" all read.
;;; The feet-inch parser is ABCDEF's, including its repairs for scanned and
;;; re-typed field sheets (a split fraction "1 /4", a foot mark read as a
;;; digit, "IO" for "10"), because it is the same handwriting either way.
;;;
;;; All geometry is created in inches (1 drawing unit = 1 inch).
;;; ==========================================================================

(vl-load-com)

;; Version banner, shown on load and at the top of every run's report.
(setq *xyplot-version* "v1.2")

;;; --------------------------------------------------------------------------
;;;  Tunables
;;; --------------------------------------------------------------------------

;; Gap between the two graphs, as a share of graph 1's width.  Wide enough
;; that graph 2's Y dimension chain never runs into graph 1.
(setq xyp:*gutter* 0.35)

;; Two points whose X (or Y) differ by less than this share one rung of the
;; dimension chain - a chain rung of a sixteenth of an inch is unreadable
;; and tells nobody anything.
(setq xyp:*same* 0.0625)

(setq xyp:*dirty* nil)   ; set T whenever a value needed cleaning
(setq xyp:*fixes* nil)   ; running list of cleanup / warning messages

;;; --------------------------------------------------------------------------
;;;  Survey points the rest of the toolkit already understands
;;;  (ABCDEF's block, made the same way - see its header for why.)
;;; --------------------------------------------------------------------------

(setq xyp:*point-layer* "POINTS")
(setq xyp:*point-block* "ab_pt")
(setq xyp:*point-tag*   "number")

;; Replace every occurrence of the single char OLD with NEW in S.
(defun xyp:replace (s old new / out i c)
  (setq out "" i 1)
  (repeat (strlen s)
    (setq c (substr s i 1))
    (setq out (strcat out (if (= c old) new c)))
    (setq i (1+ i)))
  out)

;; Remove every occurrence of the single char CH from S.
(defun xyp:strip (s ch)
  (xyp:replace s ch ""))

;; Split S on spaces, returning a list of non-empty tokens.
(defun xyp:tokens (s / out tok i c)
  (setq out '() tok "" i 1)
  (repeat (strlen s)
    (setq c (substr s i 1))
    (if (= c " ")
      (progn (if (/= tok "") (setq out (cons tok out))) (setq tok ""))
      (setq tok (strcat tok c)))
    (setq i (1+ i)))
  (if (/= tok "") (setq out (cons tok out)))
  (reverse out))

;; True if S is one or more chars and every char is a digit 0-9.
(defun xyp:alldigits (s / ok i a)
  (if (= (strlen s) 0)
    nil
    (progn
      (setq ok T i 1)
      (repeat (strlen s)
        (setq a (ascii (substr s i 1)))
        (if (or (< a 48) (> a 57)) (setq ok nil))
        (setq i (1+ i)))
      ok)))

;; Return the 1-character string for Unicode code point N, but ONLY when this
;; AutoCAD's (chr)/(ascii) round-trip cleanly to that exact point.  On builds
;; where (chr) wraps code points > 255 modulo 256 (some pre-2019 releases),
;; e.g. (chr 8242) -> "2", the round-trip fails and we return nil rather than
;; corrupt real digits.  Everything is caught so it can never raise on load/run.
(defun xyp:safechr (n / r a)
  (setq r (vl-catch-all-apply 'chr (list n)))
  (if (or (vl-catch-all-error-p r) (/= (type r) 'STR) (/= (strlen r) 1))
    nil
    (progn
      (setq a (vl-catch-all-apply 'ascii (list r)))
      (if (and (not (vl-catch-all-error-p a)) (= a n)) r nil))))

;; True if S contains only characters a feet-inch value may legitimately hold
;; (digits, space, and  "  '  -  .  / ).  Anything else after scrubbing means a
;; genuinely corrupt cell we should flag rather than silently mis-read.
(defun xyp:parseable-p (s / ok i a)
  (setq ok T i 1)
  (repeat (strlen s)
    (setq a (ascii (substr s i 1)))
    (if (not (or (and (>= a 48) (<= a 57))   ; 0-9
                 (= a 32) (= a 34) (= a 39)   ; space  "  '
                 (= a 45) (= a 46) (= a 47))) ; -  .  /
      (setq ok nil))
    (setq i (1+ i)))
  ok)

;; Character-level scrub of a raw cell: letter / underscore / dash look-alikes
;; and the "smart quote" glyphs Excel/Word insert.  No non-ASCII bytes are
;; embedded in this source (some AutoCAD builds refuse to load such files);
;; single-byte look-alikes use (chr), higher code points go through
;; xyp:safechr so a build that can't represent them simply skips that pair:
;;   U+2019 ' / U+2032 prime -> '     U+201D " / U+2033 dbl prime -> "
;;   U+2013 en / U+2014 em dash and CP1252 bytes 150/151 -> -
;; These are high-confidence fixes and are NOT flagged as "needs verifying";
;; only the riskier repairs (fraction rebuild, apostrophe-as-1, split feet)
;; set xyp:*dirty*.
(defun xyp:scrub (raw / s q)
  (setq s raw)
  (setq s (xyp:replace s "_" "-"))    ; underscore read for a dash
  (setq s (xyp:replace s "O" "0"))    ; letter O -> zero
  (setq s (xyp:replace s "o" "0"))
  (setq s (xyp:replace s "I" "1"))    ; letter I / l / bar -> one
  (setq s (xyp:replace s "l" "1"))
  (setq s (xyp:replace s "|" "1"))
  (setq s (xyp:replace s (chr 150) "-"))   ; CP1252 en dash byte
  (setq s (xyp:replace s (chr 151) "-"))   ; CP1252 em dash byte
  (if (setq q (xyp:safechr 8217)) (setq s (xyp:replace s q "'")))
  (if (setq q (xyp:safechr 8242)) (setq s (xyp:replace s q "'")))
  (if (setq q (xyp:safechr 8221)) (setq s (xyp:replace s q "\"")))
  (if (setq q (xyp:safechr 8243)) (setq s (xyp:replace s q "\"")))
  (if (setq q (xyp:safechr 8211)) (setq s (xyp:replace s q "-")))
  (if (setq q (xyp:safechr 8212)) (setq s (xyp:replace s q "-")))
  s)

;; TOK is an all-digit run with no slash.  A fraction like 3/4 whose slash was
;; scanned as a 1 becomes 314; because that substitution keeps the length, a
;; valid inch fraction (den in 2..32, 0<num<den) has exactly one reconstruction.
;; Return "num/den" if one is found (scanning candidate slash positions left to
;; right), else nil.
(defun xyp:defrac (tok / len k num den ni di best)
  (setq len (strlen tok) k 1 best nil)
  (while (and (<= k len) (null best))
    (if (= (substr tok k 1) "1")
      (progn
        (setq num (substr tok 1 (1- k))
              den (substr tok (1+ k)))
        (if (and (> (strlen num) 0) (> (strlen den) 0)
                 (xyp:alldigits num) (xyp:alldigits den))
          (progn
            (setq ni (atoi num) di (atoi den))
            (if (and (member di '(2 4 8 16 32)) (> ni 0) (< ni di))
              (setq best (strcat num "/" den)))))))
    (setq k (1+ k)))
  best)

;; A fraction OCR-split across tokens: "1 /4", "1/ 4" or "1 / 4" tokenises as
;; ("1" "/4"), ("1/" "4") or ("1" "/" "4"), and the broken "/x" piece would
;; otherwise contribute 0 (losing the fraction).  Re-join a token that starts
;; or ends with "/" with its neighbour so the value parses as a real fraction.
(defun xyp:mergefrac (toks / out tok changed)
  (setq out '() changed nil)
  (while toks
    (setq tok (car toks) toks (cdr toks))
    (cond
      ;; "1/" + "4" -> re-queue "1/4" (also eats the middle of "1 / 4")
      ((and toks (= (substr tok (strlen tok) 1) "/"))
       (setq toks (cons (strcat tok (car toks)) (cdr toks)))
       (setq changed T))
      ;; "1" + "/4" -> "1/4"
      ((and out (> (strlen tok) 1) (= (substr tok 1 1) "/"))
       (setq out (cons (strcat (car out) tok) (cdr out)))
       (setq changed T))
      (T (setq out (cons tok out)))))
  (if changed (setq xyp:*dirty* T))
  (reverse out))

(defun xyp:ftin->in (raw maxd / s neg feet ftstr rest inch p dp tok
                                    num den slash df val)
  (setq s (xyp:scrub (cal:trim raw)))
  (cond
    ((= s "") nil)                              ; blank cell
    ((not (xyp:parseable-p s))               ; corrupt char left over
     (setq xyp:*dirty* T) nil)
    (T
      (setq neg nil)
      (if (= (substr s 1 1) "-") (setq neg T s (cal:trim (substr s 2))))
      ;; --- split feet from inches ----------------------------------------
      (setq p (vl-string-search "'" s))
      (cond
        (p                                      ; explicit foot mark
          (setq ftstr (cal:trim (substr s 1 p)))
          (if (vl-string-search " " ftstr) (setq xyp:*dirty* T))
          (setq feet (atof (xyp:strip ftstr " ")))
          (setq rest (cal:trim (substr s (+ p 2)))))
        ((setq dp (vl-string-search "-" s))     ; no ' but a dash: it is the
          (setq ftstr (xyp:strip (cal:trim (substr s 1 dp)) " "))
          (if (vl-string-search " " (cal:trim (substr s 1 dp)))
            (setq xyp:*dirty* T))            ; feet/inch separator
          (setq feet (atof ftstr))
          (setq rest (cal:trim (substr s (+ dp 2)))))
        (T (setq feet 0.0 ftstr "" rest s)))    ; inches only
      ;; --- clean the inch remainder --------------------------------------
      (if (= (substr rest 1 1) "-") (setq rest (cal:trim (substr rest 2))))
      (setq rest (xyp:strip rest "\""))   ; drop inch marks
      (setq rest (xyp:strip rest "'"))    ; and a trailing ' misused as one
      (setq rest (xyp:replace rest "-" " "))
      (setq rest (cal:trim rest))
      ;; --- inches: sum whole-number and fraction tokens ------------------
      (setq inch 0.0)
      (foreach tok (xyp:mergefrac (xyp:tokens rest))
        ;; a slash-less all-digit run of 3+ digits is very likely a fraction
        ;; whose "/" was scanned as a "1" (114 -> 1/4); reconstruct it.
        (if (and (not (vl-string-search "/" tok))
                 (>= (strlen tok) 3)
                 (xyp:alldigits tok)
                 (setq df (xyp:defrac tok)))
          (setq tok df xyp:*dirty* T))
        (setq slash (vl-string-search "/" tok))
        (if slash
          (progn
            (setq num (atof (substr tok 1 slash)))
            (setq den (atof (substr tok (+ slash 2))))
            (if (/= den 0.0) (setq inch (+ inch (/ num den)))))
          (setq inch (+ inch (atof tok)))))
      (setq val (+ (* feet 12.0) inch))
      ;; --- foot mark scanned as a "1" ------------------------------------
      ;; e.g. 10'-10" -> "101-10": with no real ' and a value past the
      ;; diagonal, a trailing 1 on the feet was the apostrophe; drop it.
      (if (and maxd (null p) (> val (* maxd 1.05))
               (> (strlen ftstr) 1)
               (= (substr ftstr (strlen ftstr) 1) "1"))
        (progn
          (setq feet (atof (substr ftstr 1 (1- (strlen ftstr))))
                val  (+ (* feet 12.0) inch)
                xyp:*dirty* T)))
      (if neg (setq val (- val)))
      ;; --- final sanity: non-positive or still impossible -> unreadable --
      (if (or (<= val 0.0) (and maxd (> val (* maxd 1.1))))
        (progn (setq xyp:*dirty* T) nil)
        val))))

(defun xyp:in->ftin (v / neg feet whole frac n den ft s)
  (setq neg (< v 0.0) v (abs v))
  (setq n (fix (+ (* v 32.0) 0.5)))      ; total 1/32" units, rounded
  (setq feet (fix (/ n 384)))            ; 384 = 32*12
  (setq n (- n (* feet 384)))
  (setq whole (fix (/ n 32)))
  (setq n (- n (* whole 32)))            ; leftover 1/32 units, 0..31
  (setq den 32)
  (while (and (> n 0) (= (rem n 2) 0)) (setq n (/ n 2) den (/ den 2)))
  (setq s (strcat (itoa feet) "'-" (itoa whole)))
  (if (> n 0) (setq s (strcat s " " (itoa n) "/" (itoa den))))
  (setq s (strcat s "\""))
  (if neg (strcat "-" s) s))

;; Coerce a COM cell value to a trimmed string.
(defun xyp:cellstr (v)
  (cond ((null v) "")
        ((= (type v) 'STR) (cal:trim v))
        ((= (type v) 'REAL) (cal:trim (rtos v 2 6)))
        ((= (type v) 'INT) (itoa v))
        (T "")))

(defun xyp:xl-cell (sheet r c / res)
  (setq res (vl-catch-all-apply
              '(lambda ()
                 (vlax-variant-value
                   (vlax-get-property
                     (vlax-get-property
                       (vlax-get-property sheet "Cells") "Item" r c)
                     "Text")))))
  (if (vl-catch-all-error-p res) "" (xyp:cellstr res)))

;; nth (1-based) element of a list, or "" when the index is nil / out of range.
(defun xyp:nth-field (lst idx)
  (if (and idx (> idx 0) (<= idx (length lst))) (nth (1- idx) lst) ""))

;; Print the accumulated cleanup / unreadable report (if any).
(defun xyp:report-fixes (/ m)
  (if xyp:*fixes*
    (progn
      (princ "\n\n--- dirty values cleaned before import ---")
      (foreach m (reverse xyp:*fixes*) (princ (strcat "\n" m)))
      (princ "\n  ( * = auto-corrected, ? = unreadable. Verify these! )"))))

;; Parse RAW to inches, logging into xyp:*fixes* if the value had to be
;; cleaned up (a risky repair) or could not be read at all.  LABEL identifies
;; the cell in the log, e.g. "P3 / FROM C".  MAXD is the rectangle diagonal.
(defun xyp:parse-log (raw label maxd / clean v)
  (setq clean (cal:trim raw))
  (if (= clean "")
    nil                                     ; blank cell: not measured
    (progn
      (setq xyp:*dirty* nil)
      (setq v (xyp:ftin->in raw maxd))
      (cond
        ((null v)                           ; nonblank but unreadable
         (setq xyp:*fixes*
               (cons (strcat "  ? " label ": \"" clean
                             "\"  could not be read - left blank")
                     xyp:*fixes*)))
        (xyp:*dirty*                     ; cleaned something up
         (setq xyp:*fixes*
               (cons (strcat "  * " label ": \"" clean "\"  ->  "
                             (xyp:in->ftin v))
                     xyp:*fixes*))))
      v)))

;; Split one CSV line into a list of field strings, honouring "quoted" fields
;; and "" escaped quotes.
(defun xyp:parse-csv-line (line / fields cur i n c inq)
  (setq fields '() cur "" i 1 n (strlen line))
  ;; state: inq = inside a quoted field
  (setq inq nil)
  (while (<= i n)
    (setq c (substr line i 1))
    (cond
      (inq
        (if (= c "\"")
          (if (= (substr line (1+ i) 1) "\"")   ; "" -> literal quote
            (progn (setq cur (strcat cur "\"")) (setq i (1+ i)))
            (setq inq nil))
          (setq cur (strcat cur c))))
      ((= c "\"") (setq inq T))
      ((= c ",") (setq fields (cons cur fields) cur ""))
      (T (setq cur (strcat cur c))))
    (setq i (1+ i)))
  (setq fields (cons cur fields))
  (reverse fields))

;; format a real to 3 decimals, left-padded into WIDTH
(defun xyp:padnum (v width / s)
  (setq s (rtos v 2 3))
  (while (< (strlen s) width) (setq s (strcat " " s)))
  s)

;;; --------------------------------------------------------------------------
;;;  Reading the sheet
;;;
;;;  Returns a list of rows, each (NAME X Y) with X and Y reals in inches,
;;;  or nil for a cell that was blank or unreadable.  Column order is
;;;  discovered from the header row, so the sheet's columns may sit in any
;;;  order as long as the headers name them.
;;; --------------------------------------------------------------------------

;; Which column a header names.  X and Y are checked as whole words before
;; the looser EASTING / NORTHING spellings, and the name column last, so a
;; header like "X OFFSET" cannot be mistaken for the point name.
(defun xyp:col-of (up)
  (cond ((or (= up "X") (= up "X OFFSET") (= up "OFFSET X")
             (vl-string-search "EASTING" up)
             (and (vl-string-search "X" up)
                  (or (vl-string-search "OFFSET" up)
                      (vl-string-search "COORD" up)
                      (vl-string-search "DIST" up)))) 'x)
        ((or (= up "Y") (= up "Y OFFSET") (= up "OFFSET Y")
             (vl-string-search "NORTHING" up)
             (and (vl-string-search "Y" up)
                  (or (vl-string-search "OFFSET" up)
                      (vl-string-search "COORD" up)
                      (vl-string-search "DIST" up)))) 'y)
        ((or (vl-string-search "NAME" up) (vl-string-search "POINT" up)
             (vl-string-search "LABEL" up) (vl-string-search "NO" up)) 'name)
        (T nil)))

(defun xyp:read-csv (file / fp line fields i h up kind
                            name-c x-c y-c rows nm)
  (setq fp (open file "r"))
  (if (null fp)
    (progn (princ "\n** Could not open the file for reading.") nil)
    (progn
      (setq name-c nil x-c nil y-c nil)
      (setq line (read-line fp))
      (while (and line (= (cal:trim (xyp:strip line (chr 13))) ""))
        (setq line (read-line fp)))
      (if line
        (progn
          (setq fields (xyp:parse-csv-line (xyp:strip line (chr 13))) i 1)
          (foreach h fields
            (setq up (strcase (cal:trim h)) kind (xyp:col-of up))
            (cond ((and (eq kind 'name) (null name-c)) (setq name-c i))
                  ((and (eq kind 'x) (null x-c)) (setq x-c i))
                  ((and (eq kind 'y) (null y-c)) (setq y-c i)))
            (setq i (1+ i)))))
      (if (null name-c) (setq name-c 1))     ; fall back to the first column
      (if (null x-c) (setq x-c 2))
      (if (null y-c) (setq y-c 3))
      (setq rows '() xyp:*fixes* '())
      (while (setq line (read-line fp))
        (setq line (xyp:strip line (chr 13)))
        (if (/= (cal:trim line) "")
          (progn
            (setq fields (xyp:parse-csv-line line))
            (setq nm (cal:trim (xyp:nth-field fields name-c)))
            (if (/= nm "")
              (setq rows
                (cons (list nm
                        (xyp:parse-log (xyp:nth-field fields x-c)
                                       (strcat nm " / X") nil)
                        (xyp:parse-log (xyp:nth-field fields y-c)
                                       (strcat nm " / Y") nil))
                      rows))))))
      (close fp)
      (xyp:report-fixes)
      (reverse rows))))

(defun xyp:read-excel (file / xl created wbs wb sheet used rng nrows ncols
                              r c up kind name-c x-c y-c rows nm err)
  ;; connect to an existing Excel, else start one.  Structure, error
  ;; handling and object release are ABCDEF's, which is the copy that has
  ;; survived contact with real machines.
  (setq xl (vl-catch-all-apply 'vlax-get-object (list "Excel.Application")))
  (if (vl-catch-all-error-p xl)
    (progn (setq xl (vlax-create-object "Excel.Application") created T)))
  (if (or (null xl) (vl-catch-all-error-p xl))
    (progn (princ "\n** Could not start Excel (is it installed?).") nil)
    (progn
      (vl-catch-all-apply '(lambda () (vlax-put-property xl "Visible" :vlax-false)))
      (vl-catch-all-apply '(lambda () (vlax-put-property xl "DisplayAlerts" :vlax-false)))
      (setq err (vl-catch-all-apply
                  '(lambda ()
                     (setq wbs (vlax-get-property xl "Workbooks"))
                     (setq wb (vlax-invoke-method wbs "Open" file))
                     (setq sheet (vlax-get-property wb "ActiveSheet"))
                     (setq used (vlax-get-property sheet "UsedRange"))
                     ;; widen columns so "Text" is never truncated to ####
                     (vl-catch-all-apply
                       '(lambda () (vlax-invoke-method
                                     (vlax-get-property used "Columns") "AutoFit")))
                     (setq nrows (vlax-get-property
                                   (vlax-get-property used "Rows") "Count"))
                     (setq ncols (vlax-get-property
                                   (vlax-get-property used "Columns") "Count")))))
      (if (vl-catch-all-error-p err)
        (progn
          (princ (strcat "\n** Could not open the spreadsheet: "
                         (vl-catch-all-error-message err)))
          (if created (vl-catch-all-apply '(lambda () (vlax-invoke-method xl "Quit"))))
          nil)
        (progn
          ;; --- locate columns from the header row ------------------------
          (setq name-c nil x-c nil y-c nil c 1)
          (while (<= c ncols)
            (setq up (strcase (xyp:xl-cell sheet 1 c)) kind (xyp:col-of up))
            (cond ((and (eq kind 'name) (null name-c)) (setq name-c c))
                  ((and (eq kind 'x) (null x-c)) (setq x-c c))
                  ((and (eq kind 'y) (null y-c)) (setq y-c c)))
            (setq c (1+ c)))
          ;; a sheet with no headers at all is still readable: name, X, Y
          ;; in the first three columns is the shape everyone writes anyway
          (if (null name-c) (setq name-c 1))
          (if (null x-c) (setq x-c 2))
          (if (null y-c) (setq y-c 3))
          ;; --- read the data rows ----------------------------------------
          (setq rows '() xyp:*fixes* '() r 2)
          (while (<= r nrows)
            (setq nm (xyp:xl-cell sheet r name-c))
            (if (/= nm "")
              (setq rows
                (cons (list nm
                        (xyp:parse-log (xyp:xl-cell sheet r x-c)
                                       (strcat nm " / X") nil)
                        (xyp:parse-log (xyp:xl-cell sheet r y-c)
                                       (strcat nm " / Y") nil))
                      rows)))
            (setq r (1+ r)))
          (xyp:report-fixes)
          ;; --- close up --------------------------------------------------
          (vl-catch-all-apply '(lambda () (vlax-invoke-method wb "Close" :vlax-false)))
          (if created (vl-catch-all-apply '(lambda () (vlax-invoke-method xl "Quit"))))
          (vl-catch-all-apply '(lambda () (vlax-release-object wb)))
          (vl-catch-all-apply '(lambda () (vlax-release-object wbs)))
          (vl-catch-all-apply '(lambda () (vlax-release-object xl)))
          (reverse rows))))))

;; Pick the reader for .csv, else Excel COM automation.
(defun xyp:read-file (file / ext n)
  (setq n (strlen file) ext "")
  (if (> n 4) (setq ext (strcase (substr file (- n 3)))))
  (if (= ext ".CSV")
    (xyp:read-csv file)
    (xyp:read-excel file)))

;;; --------------------------------------------------------------------------
;;;  Drawing helpers
;;; --------------------------------------------------------------------------

(defun xyp:point (pt layer)
  (entmake (list '(0 . "POINT") (cons 8 layer)
                 (list 10 (car pt) (cadr pt) 0.0))))

(defun xyp:line (p1 p2 layer)
  (entmake (list '(0 . "LINE") (cons 8 layer)
                 (list 10 (car p1) (cadr p1) 0.0)
                 (list 11 (car p2) (cadr p2) 0.0))))

;; Closed rectangle through the four corners, given in perimeter order.
(defun xyp:box (p1 p2 p3 p4 layer)
  (entmake (list '(0 . "LWPOLYLINE") '(100 . "AcDbEntity") (cons 8 layer)
                 '(100 . "AcDbPolyline") '(90 . 4) '(70 . 1)
                 (cons 10 p1) (cons 10 p2) (cons 10 p3) (cons 10 p4))))

;; A rotated linear dimension between P1 and P2, its dimension line through
;; LOC.  ROT is 0.0 for a dimension that measures the X difference and
;; pi/2 for one that measures the Y difference, which is what makes each
;; chain read as one straight run of numbers however the points scatter.
;; The extension lines grow from P1 and P2 themselves, so every rung is
;; visibly tied to the two points it spans.
(defun xyp:dim (p1 p2 loc rot layer)
  (entmake (list '(0 . "DIMENSION") '(100 . "AcDbEntity") (cons 8 layer)
                 '(100 . "AcDbDimension")
                 (list 10 (car loc) (cadr loc) 0.0)
                 '(70 . 32) '(1 . "")
                 '(100 . "AcDbAlignedDimension")
                 (list 13 (car p1) (cadr p1) 0.0)
                 (list 14 (car p2) (cadr p2) 0.0)
                 '(100 . "AcDbRotatedDimension")
                 (cons 50 rot))))

;; The ab_pt survey block, built if this drawing has never seen one.
;; (ABCDEF's definition, made the same way, so a drawing can hold imports
;; from both commands without a clash.)
(defun xyp:ensure-block (/ sty)
  (if (not (tblsearch "BLOCK" xyp:*point-block*))
    (progn
      (setq sty (if (tblsearch "STYLE" "STANDARD")
                  "STANDARD"
                  (getvar "TEXTSTYLE")))
      (entmake (list '(0 . "BLOCK") '(100 . "AcDbEntity") '(8 . "0")
                     '(100 . "AcDbBlockBegin")
                     (cons 2 xyp:*point-block*) '(70 . 2)
                     '(10 0.0 0.0 0.0)
                     (cons 3 xyp:*point-block*) '(1 . "")))
      (entmake '((0 . "POINT") (100 . "AcDbEntity") (8 . "0")
                 (100 . "AcDbPoint") (10 0.0 0.0 0.0)))
      (entmake (list '(0 . "ATTDEF") '(100 . "AcDbEntity") '(8 . "0")
                     '(100 . "AcDbText") '(10 1.0 -2.0 0.0) '(40 . 1.0)
                     '(1 . "0") (cons 7 sty)
                     '(100 . "AcDbAttributeDefinition")
                     '(3 . "Type_Point_Number")
                     (cons 2 xyp:*point-tag*) '(70 . 4)))
      (entmake '((0 . "ENDBLK") (100 . "AcDbEntity") (8 . "0")
                 (100 . "AcDbBlockEnd")))
      (princ (strcat "\n  block \"" xyp:*point-block*
                     "\" was not in this drawing - created it."))))
  (tblsearch "BLOCK" xyp:*point-block*))

(defun xyp:insert-pt (pt name th)
  (entmake (list '(0 . "INSERT") '(100 . "AcDbEntity")
                 (cons 8 xyp:*point-layer*)
                 '(100 . "AcDbBlockReference") '(66 . 1)
                 (cons 2 xyp:*point-block*)
                 (list 10 (car pt) (cadr pt) 0.0)
                 (cons 41 th) (cons 42 th) (cons 43 th)))
  (entmake (list '(0 . "ATTRIB") '(100 . "AcDbEntity")
                 (cons 8 xyp:*point-layer*) '(100 . "AcDbText")
                 (list 10 (+ (car pt) th) (- (cadr pt) (* 2.0 th)) 0.0)
                 (cons 40 th) (cons 1 name) '(100 . "AcDbAttribute")
                 (cons 2 xyp:*point-tag*) '(70 . 0)))
  (entmake (list '(0 . "SEQEND") '(100 . "AcDbEntity")
                 (cons 8 xyp:*point-layer*))))

;; Every ab_pt INSERT made since MARK, as a selection set.  (Walking
;; forward from a mark rather than filtering the whole drawing is what
;; keeps a second import from handing ABHD two surveys at once.)
(defun xyp:new-points (mark / ss e ed)
  (setq ss (ssadd) e (if mark (entnext mark) (entnext)))
  (while e
    (setq ed (entget e))
    (if (and (= (cdr (assoc 0 ed)) "INSERT")
             (= (strcase (cdr (assoc 2 ed))) (strcase xyp:*point-block*)))
      (ssadd e ss))
    (setq e (entnext e)))
  ss)

;;; --------------------------------------------------------------------------
;;;  The dimension chains
;;;
;;;  A chain is one continuous run of linear dimensions along an axis,
;;;  passing through every point's offset in order and through the origin
;;;  wherever the origin falls among them.  Read left to right (or bottom to
;;;  top) it is the sheet's column of X (or Y) values turned into the gaps
;;;  between them, which is the form a fitter actually lays out from.
;;;
;;;  Two rules keep it readable.  Offsets closer together than xyp:*same*
;;;  share one stop - a rung a sixteenth of an inch wide is unreadable and
;;;  tells nobody anything.  And the sort is written out longhand rather
;;;  than handed to vl-sort, because vl-sort DROPS elements its comparison
;;;  calls equal: two points on the same X would go in and one would come
;;;  out, silently, which is the worst way for a survey to lose a point.
;;; --------------------------------------------------------------------------

;; STOPS along AXIS ('x or 'y): a list of (VALUE ANCHOR LABELS) sorted by
;; VALUE ascending, including the origin, with points closer than
;; xyp:*same* collapsed onto one stop.  ANCHOR is the drawing point a
;; dimension's extension line grows from; LABELS names the points there.
;;
;; PTS are (NAME X Y) offsets and ORG is where the graph's origin sits.
(defun xyp:chain-stops (pts axis org / raw p v ins out i n cur st)
  ;; --- every offset, plus the origin, as (value anchor label) ------------
  (setq raw (list (list 0.0 org "0")))
  (foreach p pts
    (setq v (if (eq axis 'x) (cadr p) (caddr p)))
    (setq raw (cons (list v
                          (list (+ (car org) (cadr p))
                                (+ (cadr org) (caddr p)))
                          (car p))
                    raw)))
  ;; --- insertion sort by value, ascending, keeping every element ---------
  (setq out '())
  (foreach ins raw
    (setq n (length out) i 0 cur '())
    (while (and (< i n) (<= (car (nth i out)) (car ins)))
      (setq cur (cons (nth i out) cur) i (1+ i)))
    (setq cur (cons ins cur))
    (while (< i n)
      (setq cur (cons (nth i out) cur) i (1+ i)))
    (setq out (reverse cur)))
  ;; --- collapse stops that sit on top of each other ----------------------
  (setq raw '() cur nil)
  (foreach st out
    (if (and cur (<= (abs (- (car st) (car cur))) xyp:*same*))
      ;; same stop: keep the first anchor, add the name to its label
      (setq cur (list (car cur) (cadr cur)
                      (strcat (caddr cur) "," (caddr st))))
      (progn (if cur (setq raw (cons cur raw))) (setq cur st))))
  (if cur (setq raw (cons cur raw)))
  (reverse raw))

;; Draw one chain through STOPS.  AXIS is 'x or 'y; LOC is the coordinate
;; the dimension line sits at (a Y for the X chain, an X for the Y chain).
;; Returns the number of rungs drawn.
(defun xyp:chain (stops axis loc layer / n prev st pa pb dl)
  (setq n 0 prev nil)
  (foreach st stops
    (if prev
      (progn
        (setq pa (cadr prev) pb (cadr st))
        (setq dl (if (eq axis 'x)
                   (list (* 0.5 (+ (car pa) (car pb))) loc)
                   (list loc (* 0.5 (+ (cadr pa) (cadr pb))))))
        (xyp:dim pa pb dl (if (eq axis 'x) 0.0 (/ pi 2.0)) layer)
        (setq n (1+ n))))
    (setq prev st))
  n)

;;; --------------------------------------------------------------------------
;;;  Asking, reporting, handing on
;;; --------------------------------------------------------------------------

;; Keyword question in the house format (STANDARDS.md section 1).  Back and
;; Undo come back as the symbol XY-BACK.
(defun xyp:askkw (msg kws shown dflt back / v)
  (initget (if dflt 0 (if back 0 1))
           (if back (strcat kws " Back Undo") kws))
  (setq v (getkword (strcat "\n" msg " [" shown
                            (if back "/Back" "") "]"
                            (if dflt (strcat " <" dflt ">") "") ": ")))
  (cond ((member v '("Back" "Undo")) 'XY-BACK)
        ((null v) (if dflt dflt (xyp:askkw msg kws shown dflt back)))
        (T v)))

;; Push one report line onto the accumulating list (newest first).
(defun xyp:say (rep line)
  (cons line rep))

;; SHEET with its extension replaced by SUFFIX.
(defun xyp:sibling (sheet suffix / n i cut)
  (setq n (strlen sheet) i n cut nil)
  (while (and (> i 0) (null cut))
    (cond ((= (substr sheet i 1) ".") (setq cut i))
          ((member (substr sheet i 1) '("\\" "/")) (setq i 1)))
    (setq i (1- i)))
  (strcat (if cut (substr sheet 1 (1- cut)) sheet) suffix))

;; Write the report beside the sheet it came from.  Returns the path, or
;; nil - a report that cannot be saved is worth a note, never worth losing
;; the drawing over.
(defun xyp:write-report (sheet lines / path fp ln)
  (setq path (xyp:sibling sheet "_XYPLOT_report.txt"))
  (setq fp (vl-catch-all-apply 'open (list path "w")))
  (if (or (vl-catch-all-error-p fp) (null fp))
    nil
    (progn
      (foreach ln (reverse lines) (write-line ln fp))
      (close fp)
      path)))

;; Pre-select graph 1's points and start ABHD on them.  (ABCDEF's handoff,
;; for the same reason and with the same caveat when ABHD is not loaded.)
(defun xyp:to-abhd (ss / n)
  (setq n (if ss (sslength ss) 0))
  (cond
    ((= n 0)
     (princ "\n  Nothing was plotted, so there is no survey to fit."))
    ((null (boundp 'c:ABHD))
     (princ (strcat "\n  ABHD is not loaded in this drawing, so the points"
                    "\n  were left ready for it instead: they are ab_pt"
                    "\n  blocks on layer " xyp:*point-layer*
                    ".  APPLOAD abhd.lsp (or the"
                    "\n  whole LAZPASS.lsp build), then run ABHD and"
                    "\n  window graph 1's points.")))
    (T
     (princ (strcat "\n  Starting ABHD on the " (itoa n)
                    " point(s) of graph 1 ..."))
     (sssetfirst nil ss)
     (vl-cmdf "_.ABHD"))))

;;; --------------------------------------------------------------------------
;;;  Main command
;;; --------------------------------------------------------------------------

(defun c:XYPLOT (/ *error* undo-open
                    file base bpx bpy rows r nm x y pts skipped
                    minx miny maxx maxy spanx spany th org2 gap
                    xstops ystops xline yline nxd nyd mark ss
                    rep p path stage done g1 g2 pad)
  ;; an Esc mid-plot used to leave a half-drawn plot that took N undos
  ;; to clear and printed a raw AutoLISP message (STANDARDS section 5)
  (defun *error* (msg)
    (if undo-open (command "_.UNDO" "_End"))
    (setq undo-open nil)
    (if (and msg (not (wcmatch (strcase msg)
                               "*BREAK*,*CANCEL*,*QUIT*,*EXIT*")))
        (princ (strcat "\nXYPLOT error: " msg)))
    (princ))
  (vl-load-com)
  (princ (strcat "\nXYPLOT " *xyplot-version*))
  ;; ---- the questions: Back at the second re-opens the first -------------
  (setq stage 1 done nil)
  (while (not done)
    (cond
      ((= stage 1)
       (setq file (getfiled "Select X/Y points spreadsheet"
                            "" "xlsx;xls;xlsm;csv" 16))
       (if (null file) (setq done 'quit) (setq stage 2)))
      (T
       ;; take the pick in WCS so the plot is built square to the world axes
       ;; even under a rotated UCS (entmake writes WCS)
       (initget "Back Undo")
       (setq base (getpoint "\nInsertion point for the origin (X=0, Y=0) <0,0> [Back]: "))
       (if (= (type base) 'STR) (setq stage 1) (setq done T)))))
  (if (eq done 'quit)
    (progn (princ "\nCancelled.") (princ))
    (progn
      (command "_.UNDO" "_Begin")
      (setq undo-open T)
      (if base (setq base (trans base 1 0)) (setq base '(0.0 0.0 0.0)))
      (setq bpx (car base) bpy (cadr base))
      (princ "\nReading spreadsheet ... ")
      (setq rows (xyp:read-file file))
      (if (null rows)
        (progn (princ "\nNo usable rows found - nothing plotted.") (princ))
        (progn
          (princ (strcat (itoa (length rows)) " row(s) found."))
          ;; ---- keep the rows that have both an X and a Y ------------------
          (setq pts '() skipped '())
          (foreach r rows
            (setq nm (car r) x (cadr r) y (caddr r))
            (if (and x y)
              (setq pts (cons (list nm x y) pts))
              (setq skipped (cons (list nm (if x "Y" (if y "X" "X and Y")))
                                  skipped))))
          (setq pts (reverse pts) skipped (reverse skipped))
          (if (null pts)
            (progn
              (princ "\nNo row had both an X and a Y - nothing plotted.")
              (princ))
            (progn
              ;; ---- extents, and the sizes everything is drawn from --------
              (setq minx 0.0 maxx 0.0 miny 0.0 maxy 0.0)
              (foreach p pts
                (setq minx (min minx (cadr p)) maxx (max maxx (cadr p))
                      miny (min miny (caddr p)) maxy (max maxy (caddr p))))
              (setq spanx (- maxx minx) spany (- maxy miny))
              (if (< spanx 1.0) (setq spanx 1.0))
              (if (< spany 1.0) (setq spany 1.0))
              (setq th (/ (max spanx spany) 60.0))
              (if (< th 0.5) (setq th 0.5))
              (setq pad (* 2.0 th))
              ;; graph 2 sits a clear gutter to the right of graph 1, far
              ;; enough that its Y chain never overruns graph 1's frame
              (setq gap  (+ (* spanx xyp:*gutter*) (* 12.0 th))
                    org2 (list (+ bpx spanx gap) bpy))
              ;; ---- layers -------------------------------------------------
              (cal:ensure-layer "XYPLOT-FRAME"  1)    ; red   - frames and axes
              (cal:ensure-layer "XYPLOT-POINTS" 2)    ; yellow- graph 2's markers
              (cal:ensure-layer "XYPLOT-LABELS" 3)    ; green - graph 2's names
              (cal:ensure-layer "DIMENSION"     3)    ; green - the chains
              (cal:ensure-layer xyp:*point-layer* 2)  ; yellow- graph 1's survey
              (xyp:ensure-block)
              ;; =============================================================
              ;;  GRAPH 1 - the points as given
              ;; =============================================================
              (setq mark (entlast))
              (foreach p pts
                (xyp:insert-pt (list (+ bpx (cadr p)) (+ bpy (caddr p)))
                               (car p) th))
              (setq ss (xyp:new-points mark))
              ;; axes through the origin, and a frame round the lot
              (xyp:line (list (+ bpx minx (- pad)) bpy)
                        (list (+ bpx maxx pad) bpy) "XYPLOT-FRAME")
              (xyp:line (list bpx (+ bpy miny (- pad)))
                        (list bpx (+ bpy maxy pad)) "XYPLOT-FRAME")
              (setq g1 (list (+ bpx minx (- pad)) (+ bpy miny (- pad))))
              (xyp:box (list (car g1) (cadr g1))
                       (list (+ bpx maxx pad) (cadr g1))
                       (list (+ bpx maxx pad) (+ bpy maxy pad))
                       (list (car g1) (+ bpy maxy pad))
                       "XYPLOT-FRAME")
              (cal:text (list (car g1) (+ bpy maxy pad (* 0.8 th)))
                        (* 1.6 th) "GRAPH 1 - POINTS AS GIVEN"
                        "XYPLOT-FRAME")
              ;; =============================================================
              ;;  GRAPH 2 - the same points, dimensioned linearly
              ;;  Plain POINTs, not ab_pt: a second ab_pt copy of one survey
              ;;  would hand ABHD the same pool twice.
              ;; =============================================================
              (foreach p pts
                (xyp:point (list (+ (car org2) (cadr p))
                                 (+ (cadr org2) (caddr p)))
                           "XYPLOT-POINTS")
                (cal:text (list (+ (car org2) (cadr p) (* 0.6 th))
                                (+ (cadr org2) (caddr p) (* 0.6 th)))
                          th (car p) "XYPLOT-LABELS"))
              (xyp:line (list (+ (car org2) minx (- pad)) (cadr org2))
                        (list (+ (car org2) maxx pad) (cadr org2))
                        "XYPLOT-FRAME")
              (xyp:line (list (car org2) (+ (cadr org2) miny (- pad)))
                        (list (car org2) (+ (cadr org2) maxy pad))
                        "XYPLOT-FRAME")
              (setq g2 (list (+ (car org2) minx (- pad))
                             (+ (cadr org2) miny (- pad))))
              (xyp:box (list (car g2) (cadr g2))
                       (list (+ (car org2) maxx pad) (cadr g2))
                       (list (+ (car org2) maxx pad) (+ (cadr org2) maxy pad))
                       (list (car g2) (+ (cadr org2) maxy pad))
                       "XYPLOT-FRAME")
              (cal:text (list (car g2) (+ (cadr org2) maxy pad (* 0.8 th)))
                        (* 1.6 th) "GRAPH 2 - THE SAME POINTS, DIMENSIONED"
                        "XYPLOT-FRAME")
              ;; the X chain below and the Y chain to the left, each clear
              ;; of the frame so the numbers never sit on the geometry
              (setq xline (- (+ (cadr org2) miny) (* 6.0 th))
                    yline (- (+ (car  org2) minx) (* 6.0 th)))
              (setq xstops (xyp:chain-stops pts 'x org2)
                    ystops (xyp:chain-stops pts 'y org2))
              (setq nxd (xyp:chain xstops 'x xline "DIMENSION")
                    nyd (xyp:chain ystops 'y yline "DIMENSION"))
              (cal:text (list (car g2) (- xline (* 3.0 th)))
                        th (strcat "X chain: " (itoa nxd) " rungs")
                        "XYPLOT-FRAME")
              (cal:text (list (- yline (* 2.0 th)) (cadr g2))
                        th (strcat "Y chain: " (itoa nyd) " rungs")
                        "XYPLOT-FRAME")
              ;; ---- report -------------------------------------------------
              (setq rep '())
              (setq rep (xyp:say rep (strcat "===== XYPLOT " *xyplot-version*
                                             " results =====")))
              (setq rep (xyp:say rep (strcat "  sheet  : " file)))
              (setq rep (xyp:say rep (strcat "  origin : "
                                             (rtos bpx 2 3) ", " (rtos bpy 2 3)
                                             " (drawing units = inches)")))
              (setq rep (xyp:say rep ""))
              (setq rep (xyp:say rep
                "  POINT                    X               Y            X (in)      Y (in)"))
              (foreach p pts
                (setq rep (xyp:say rep (strcat
                  "  " (cal:pad (car p) 20)
                  (cal:pad (xyp:in->ftin (cadr p)) 16)
                  (cal:pad (xyp:in->ftin (caddr p)) 14)
                  (xyp:padnum (cadr p) 10)
                  (xyp:padnum (caddr p) 12)))))
              (setq rep (xyp:say rep
                "-------------------------------------------------------------"))
              (setq rep (xyp:say rep (strcat
                "  " (itoa (length pts)) " point(s) plotted in both graphs.")))
              (if skipped
                (progn
                  (setq rep (xyp:say rep (strcat
                    "  " (itoa (length skipped))
                    " row(s) skipped for a missing coordinate:")))
                  (foreach p skipped
                    (setq rep (xyp:say rep (strcat "      " (cal:pad (car p) 20)
                                                   "no " (cadr p)))))))
              (setq rep (xyp:say rep (strcat
                "  extents: X " (xyp:in->ftin minx) " to " (xyp:in->ftin maxx)
                ",  Y " (xyp:in->ftin miny) " to " (xyp:in->ftin maxy))))
              (setq rep (xyp:say rep (strcat
                "  chains : " (itoa nxd) " X rungs, " (itoa nyd) " Y rungs"
                " (offsets within " (rtos xyp:*same* 2 4)
                "\" share a rung).")))
              (setq rep (xyp:say rep ""))
              (setq rep (xyp:say rep
                "  GRAPH 1 holds the survey: ab_pt blocks on layer POINTS,"))
              (setq rep (xyp:say rep (strcat
                "  numbered from the sheet, which is what ABHD reads.")))
              (setq rep (xyp:say rep
                "  GRAPH 2 is the same points drawn again with the X and Y"))
              (setq rep (xyp:say rep
                "  offsets dimensioned as two continuous chains.  Its markers"))
              (setq rep (xyp:say rep
                "  are plain POINTs on XYPLOT-POINTS, deliberately: a second"))
              (setq rep (xyp:say rep
                "  ab_pt copy would hand ABHD the same pool twice.  The"))
              (setq rep (xyp:say rep
                "  dimensions measure the drawn geometry, so one that"))
              (setq rep (xyp:say rep
                "  disagrees with its column above is a value that did not"))
              (setq rep (xyp:say rep
                "  survive the trip from the sheet."))
              (foreach p (reverse rep) (princ (strcat "\n" p)))
              (setq path (xyp:write-report file rep))
              (princ (if path
                       (strcat "\n\n  Report saved: " path)
                       "\n\n  ** the report file could not be written (read-only folder?)"))
              (vl-catch-all-apply
                '(lambda ()
                   (vl-cmdf "_.plan" "_World")
                   (vl-cmdf "_.zoom" "_Extents"))
                '())
              (princ "\n  View reset to plan (top).")
              ;; close the group before any ABHD handoff - the whole plot
              ;; is one U, and ABHD grouped separately is ABHD's own U
              (command "_.UNDO" "_End")
              (setq undo-open nil)
              ;; ---- on to the pool perimeter ------------------------------
              (if (= "Yes" (xyp:askkw
                             "Fit a pool perimeter through graph 1's points now?"
                             "Yes No" "Yes/No" "Yes" nil))
                (xyp:to-abhd ss)
                (princ "\n  Left as points - run ABHD (or CABHD) when ready."))
              (princ)))))))
  (princ))

;; Print the loaded version.
(defun c:XYPLOTVER ()
  (princ (strcat "\nXYPLOT " *xyplot-version* " (XYPLOT.lsp)"))
  (princ))

(princ (strcat "\nXYPLOT.lsp " *xyplot-version*
               " loaded.  Type XYPLOT to graph an X/Y sheet."))
(princ)


;;; ======================================================================
;;; >>> LAZSPA.lsp
;;; ======================================================================

;;; ======================================================================
;;; LAZSPA.lsp  --  fill a spa dimension chart in, then draw the spa
;;; ----------------------------------------------------------------------
;;; For AutoCAD 2018 and later (plain AutoLISP, no external libraries).
;;;
;;; Commands:  LAZSPA         fill in a spa chart and run SPA from it
;;;            LAZSPAVER      print the loaded version
;;;
;;; SHARED BUILD: requires CALOFIN-LIB.lsp (load via CALOFIN-LOADER.lsp).
;;; Generic helpers live there under cal: - see STANDARDS.md.
;;;
;;; What LAZFORM is to POOL, this is to SPA.  SPA grew an answer store
;;; this week -- spa:*form*, spa:run-with-answers, and the hooks in its
;;; ask helpers -- and nothing in AutoCAD could drive it: the VB palette
;;; in ui/ needs a DLL NETLOADed on every machine.  LAZFORM proved a
;;; plain DCL chart can drive POOL with nothing to install, so this is
;;; that chart for SPA.
;;;
;;; The chart on screen is the one off the order sheet: the outline, the
;;; dimension chain and its letters.  Type a number against a letter and
;;; the letter is REPLACED by what you typed -- which is what the letter
;;; was standing in for all along.  Fill in what you know, leave the
;;; rest blank, press Insert: SPA runs and asks only for the gaps.
;;;
;;; NA in a box means "not measured" and is passed through as such --
;;; different from leaving it blank, which just means SPA should ask.
;;;
;;; ZERO INSTALL, like LAZFORM and LAZPANEL: the dialog is plain DCL
;;; written to the temp folder at run time, and the chart is drawn with
;;; vector_image, so there is no artwork file to ship and nothing to
;;; NETLOAD.
;;;
;;; WHY THE BOXES ARE BESIDE AND INSIDE THE PICTURE, NEVER ON IT.  DCL
;;; packs tiles into rows and columns: no absolute positioning, no
;;; overlapping, no z-order, so an edit box cannot sit on an image tile
;;; -- and DCL cannot display a raster at all, an image tile takes
;;; vectors or an AutoCAD slide and nothing else.  So the chart is
;;; DRAWN, and cut into horizontal bands at the heights where its
;;; across dimensions run; those rows are real edit boxes wedged
;;; between the bands, pushed to their letters' positions by spacers.
;;; The dimensions that run UP cannot be wedged -- a box cannot stand
;;; sideways in a row -- so they keep boxes in the side column and what
;;; is typed there is drawn onto the chart in the letter's place.
;;;
;;; THE PICTURE IS PASSIVE AND MUST STAY PASSIVE.  It is an "image"
;;; tile, never an "image_button".  A DCL image tile is NOT retained by
;;; AutoCAD: any repaint clears it to its own colour attribute and
;;; everything the application drew into it is gone, and there is no
;;; expose callback to draw it again.  An image_button is repainted on
;;; mouse-enter and mouse-leave, so the chart vanishes the first time
;;; the cursor crosses it -- which is exactly how LAZFORM lost its
;;; drawing before the button was taken back out.  The same rule is why
;;; every dropdown on this form repaints the chart: a list unrolling
;;; over it does the same damage and nothing else would repair it.
;;;
;;; WHY THE FONT AND THE DRAWING CODE ARE NOT SHARED WITH LAZFORM.  They
;;; are the same idea twice, and that is deliberate: only
;;; CALOFIN-LIB.lsp may define cal: symbols, and a tool may not define a
;;; top-level name another shared file defines -- so borrowing lzf:
;;; names would make LAZSPA depend on LAZFORM being loaded, which it
;;; never is at the standalone tier.  Everything here is lzs:.
;;;
;;; ADDING A SHAPE is adding data, not code -- one entry in lzs:*charts*
;;; with an outline, a dimension list and its SPA keys, plus a line in
;;; the tables under it.  Three charts, one per shape SPA draws:
;;; Rectangle, OCtagon, ROund.  The chart sends the word the legend
;;; prints; SPA's own keyword is "ROUnd" (one capitalisation repo-wide
;;; -- POOL needs RO for ROman), and spa:fshape matches the shape word
;;; WITHOUT case and returns the canonical spelling, so either reaches
;;; the right branch.  A word that is not a shape at all still falls
;;; through to the prompt rather than drawing the wrong spa silently.
;;; ======================================================================

(vl-load-com)

(setq *lazspa-version* "v1.0")

;;; -------------------- the stroke font ---------------------------------
;;;  DCL has no way to draw text into an image tile -- vector_image draws
;;;  line segments and that is the whole of it -- so the letters and the
;;;  numbers on the chart are stroked out of segments here.
;;;
;;;  One entry per character: the glyph as a list of polylines, each a
;;;  flat list of x y x y ... in TENTHS of a font unit, on a cell 4 wide
;;;  and 6 tall with y running DOWN the way image-tile pixels do.
;;;  Integers, so nothing here depends on float formatting.

(setq lzs:*font* '(
    ("A" (0 60 20 0 40 60) (8 40 32 40))
    ("B" (0 0 0 60) (0 0 30 0 40 10 40 20 30 30 0 30) (30 30 40 40 40 50 30 60 0 60))
    ("C" (40 10 30 0 10 0 0 10 0 50 10 60 30 60 40 50))
    ("D" (0 0 0 60) (0 0 30 0 40 10 40 50 30 60 0 60))
    ("E" (40 0 0 0 0 60 40 60) (0 30 30 30))
    ("F" (40 0 0 0 0 60) (0 30 30 30))
    ("G" (40 10 30 0 10 0 0 10 0 50 10 60 30 60 40 50 40 30 20 30))
    ("H" (0 0 0 60) (40 0 40 60) (0 30 40 30))
    ("I" (10 0 30 0) (20 0 20 60) (10 60 30 60))
    ("J" (30 0 30 50 20 60 10 60 0 50))
    ("K" (0 0 0 60) (40 0 0 35) (14 25 40 60))
    ("L" (0 0 0 60 40 60))
    ("M" (0 60 0 0 20 30 40 0 40 60))
    ("N" (0 60 0 0 40 60 40 0))
    ("O" (10 0 30 0 40 10 40 50 30 60 10 60 0 50 0 10 10 0))
    ("P" (0 60 0 0 30 0 40 10 40 20 30 30 0 30))
    ("Q" (10 0 30 0 40 10 40 50 30 60 10 60 0 50 0 10 10 0) (25 45 40 60))
    ("R" (0 60 0 0 30 0 40 10 40 20 30 30 0 30) (20 30 40 60))
    ("S" (40 10 30 0 10 0 0 10 0 20 10 30 30 30 40 40 40 50 30 60 10 60 0 50))
    ("T" (0 0 40 0) (20 0 20 60))
    ("U" (0 0 0 50 10 60 30 60 40 50 40 0))
    ("V" (0 0 20 60 40 0))
    ("W" (0 0 10 60 20 20 30 60 40 0))
    ("X" (0 0 40 60) (40 0 0 60))
    ("Y" (0 0 20 30 40 0) (20 30 20 60))
    ("Z" (0 0 40 0 0 60 40 60))
    ("0" (10 0 30 0 40 10 40 50 30 60 10 60 0 50 0 10 10 0) (5 55 35 5))
    ("1" (10 10 20 0 20 60) (10 60 30 60))
    ("2" (0 10 10 0 30 0 40 10 40 20 0 60 40 60))
    ("3" (0 0 40 0 20 25) (20 25 40 35 40 50 30 60 10 60 0 50))
    ("4" (30 60 30 0 0 40 40 40))
    ("5" (40 0 0 0 0 25 30 25 40 35 40 50 30 60 10 60 0 50))
    ("6" (40 0 20 0 0 20 0 50 10 60 30 60 40 50 40 40 30 30 10 30 0 40))
    ("7" (0 0 40 0 15 60))
    ("8" (10 30 0 20 0 10 10 0 30 0 40 10 40 20 30 30 10 30 0 40 0 50 10 60 30 60 40 50 40 40 30 30))
    ("9" (0 60 20 60 40 40 40 10 30 0 10 0 0 10 0 20 10 30 30 30 40 20))
    ("." (17 54 23 54 23 60 17 60 17 54))
    ("-" (5 30 35 30))
    ("'" (20 0 20 16))
    ("\"" (13 0 13 16) (27 0 27 16))
    ("/" (0 60 40 0))
    (":" (20 16 20 22) (20 40 20 46))
    ("%" (0 60 40 0) (5 5 12 5) (28 55 35 55))
    ("#" (10 0 6 60) (30 0 26 60) (0 20 40 20) (0 40 40 40))
    (" ")
))

(setq lzs:*font-w* 40)          ; glyph cell width, tenths
(setq lzs:*font-h* 60)          ; glyph cell height, tenths
(setq lzs:*font-adv* 56)        ; pen advance per character, tenths

;;; -------------------- the charts --------------------------------------
;;;  Everything is in PER-MILLE of the picture, x and y, y DOWN -- the
;;;  same convention as an image tile, so the only conversion at draw
;;;  time is a multiply.  Integers again.  y running down is why the
;;;  BOTTOM of a spa is the LARGER y here: corner A, bottom left on the
;;;  order sheet, is the low x and the high y.
;;;
;;;  A chart is:
;;;    (key  spa-shape  title
;;;      (outline-element ...)
;;;      (dimension ...)
;;;      (column-only-field ...)
;;;      (mark ...))
;;;
;;;  An outline element is a flat per-mille polyline, x y x y ..., or an
;;;  ARC written ("A" cx cy rx ry from to) with the centre and both
;;;  radii in per-mille and the angles in degrees, 0 due east and
;;;  counting anticlockwise ON SCREEN.
;;;
;;;  A dimension is (letter spakey x1 y1 x2 y2 side label), where side
;;;  is "h" or "v" -- which way the measurement runs, and so where its
;;;  text sits.  The arrow, the letter and the typed value all come off
;;;  those two endpoints, so there is no separate position table that
;;;  could fall out of step with the drawing.
;;;
;;;  A column-only field is (spakey label): a real SPA answer with no
;;;  place on the plan.  The octagon's S2 is the only one -- it measures
;;;  a diagonal cut FACE, and a dimension on this chart is "h" or "v"
;;;  and nothing else, so a diagonal has nowhere to be drawn and is
;;;  answered in the list instead.  (LAZFORM's grecian charts do exactly
;;;  this with their own S2, for exactly this reason.)
;;;
;;;  A mark is (text cx cy): a letter drawn on the picture at that
;;;  per-mille CENTRE, answering nothing.  The rectangle's A B C D are
;;;  the whole of it -- SPA names its corner questions after those
;;;  letters, so the Corners rows and the drawing have to agree about
;;;  which corner is which.

(setq lzs:*charts* '(

  ;; ---------------- Rectangle ----------------
  ;;  SPA's own header: "Corners: A bottom-left, B bottom-right, C
  ;;  top-right, D top-left", and its two overalls are named for them --
  ;;  W runs A-B across the bottom and L runs A-D up the left end.  So W
  ;;  is drawn UNDER the shape, on the side it is actually taped, rather
  ;;  than borrowed from the top edge because there was room up there.
  ("Rectangle" "Rectangle" "Rectangle"
   ((150 250 850 250 850 820 150 820 150 250))
   (("W" "w" 150 920 850 920 "h" "W - overall WIDTH across (A-B)")
    ("L" "l"  75 250  75 820 "v" "L - overall LENGTH up (A-D)"))
   nil
   (("D" 105 210) ("C" 895 210) ("A" 105 860) ("B" 895 860)))

  ;; ---------------- Octagon ----------------
  ;;  SPA's eight corners, counter-clockwise from the left end of the
  ;;  bottom flat:
  ;;
  ;;                 F ---------- E
  ;;                /              \      B = overall across
  ;;               G                D     A = overall up
  ;;               |                |     T = the flats across
  ;;               H                C     V = the flats up
  ;;                \              /      S  = cut along the side
  ;;                 A ---------- B       S1 = cut up the end
  ;;                                      S2 = the cut face itself
  ;;
  ;;  The letters have to CLOSE against the overalls, because spa:octov
  ;;  resolves them that way: S + T + S = B and S1 + V + S1 = A.  The
  ;;  drawing below is built to those sums (100 + 600 + 100 = 800 across,
  ;;  90 + 320 + 90 = 500 up), and tests/test_lazspa.py re-checks them,
  ;;  so a picture that lies about the measurement it names fails the
  ;;  suite rather than misleading the person reading it off.
  ;;
  ;;  The corner letters are NOT marked on this chart on purpose: SPA
  ;;  calls its corners A..H and its dimensions A, B, S, S1, T, V, S2,
  ;;  so an A on the outline and an A on a dimension line would be two
  ;;  different things a hand's breadth apart.
  ("OCtagon" "OCtagon" "Octagon"
   ((200 250 800 250 900 340 900 660 800 750 200 750
     100 660 100 340 200 250))
   (("B"  "b"  100 130 900 130 "h" "B - overall size ACROSS")
    ("S"  "ss" 100 200 200 200 "h" "S - corner cut along the side")
    ("T"  "tt" 200 200 800 200 "h" "T - flat across (top & bottom)")
    ("A"  "a"   30 250  30 750 "v" "A - overall size UP")
    ("S1" "s1"  65 250  65 340 "v" "S1 - corner cut up the end")
    ("V"  "vv"  65 340  65 660 "v" "V - flat up (left & right)"))
   (("s2" "S2 - corner cut FACE (tape across it)"))
   nil)

  ;; ---------------- Round ----------------
  ;;  SPA asks ONE question here -- "Overall diameter [Outofround]" --
  ;;  and only takes the two axes when the answer is the keyword.  Its
  ;;  roundflow reads the store like this:
  ;;
  ;;      (cond ((spa:fhas 'a) "Outofround")
  ;;            ((and (spa:fhas 'b) (numberp ...)) <the diameter>)
  ;;            (t <ask>))
  ;;
  ;;  -- so A is only PEEKED at, and its mere PRESENCE is what takes the
  ;;  out-of-round branch; B alone is the diameter.  That is why A's box
  ;;  says "only if out of round" and why an NA typed into it is treated
  ;;  as an empty box rather than sent (see lzs:*naok*): an NA there
  ;;  would open the out-of-round branch to say nothing at all.
  ("ROund" "ROund" "Round"
   (("A" 500 500 250 250 0 360))
   (("B" "b" 250 150 750 150 "h" "B - overall diameter (across)")
    ("A" "a" 175 250 175 750 "v" "A - overall UP (only if out of round)"))
   nil
   nil)
))

;;; -------------------- chart access ------------------------------------

(defun lzs:chart (key / c out)
  (foreach c lzs:*charts*
    (if (and (not out) (= (car c) key)) (setq out c)))
  out)

(defun lzs:outline (c) (nth 3 c))
(defun lzs:dims (c) (nth 4 c))
(defun lzs:extra (c) (nth 5 c))
(defun lzs:marks (c) (nth 6 c))

;;; -------------------- where the chart is cut ---------------------------
;;;  The closest DCL comes to boxes ON the drawing: the chart is cut
;;;  into horizontal bands at the heights where its horizontal
;;;  dimension rows run, and those rows are REAL edit boxes wedged
;;;  between the bands, pushed to their letters' positions by spacers.
;;;  The vertical dimensions cannot be wedged -- a box cannot stand
;;;  sideways in a row -- so they keep their boxes in the side column
;;;  with their values drawn on the chart instead.
;;;
;;;  A cut is a per-mille y that must land EXACTLY on a horizontal
;;;  dimension's line; every "h" dimension at that y becomes a wedge box
;;;  and loses its drawn arrow, since the row of boxes IS that row of
;;;  the drawing now.

(setq lzs:*cuts* '(("Rectangle" 920)
                   ("OCtagon" 130 200)
                   ("ROund" 150)))

(defun lzs:cuts (c) (cdr (assoc (car c) lzs:*cuts*)))

;;; -------------------- corners -----------------------------------------
;;;  A corner is a treatment plus, when the treatment is Radius or
;;;  Diagonal, a size -- so each gets a dropdown and a size box that is
;;;  greyed until a sized treatment is picked.  The dropdown's first
;;;  entry is "(ask)": the form's version of leaving a box empty, and
;;;  the only honest default, since SPA offers no default on corner A
;;;  either.
;;;
;;;  THE DROPDOWN SPEAKS THE SHEET LEGEND -- 90 / Radius / Diagonal, the
;;;  words printed on the order sheet a drafter copies from.  SPA itself
;;;  now asks the canonical Treatment question (Square / Radius / Cut /
;;;  NotGiven, STANDARDS.md section 2) and normalises the legend words
;;;  on the way in, so the chart keeps the drafter's vocabulary and the
;;;  routine keeps the standard's.  Send a word that is neither and
;;;  spa:askcorner consumes it, throws it away, and asks the corner at
;;;  the keyboard as if the box had been
;;;  left empty.  ("Square" SPA does accept, as a synonym it normalises
;;;  to 90; the dropdown offers 90 because that is what the sheet says.)
;;;
;;;  Only the Rectangle carries corner rows: it is the only shape SPA
;;;  asks corner treatments for.  An octagon's corners ARE its S / S1 /
;;;  S2 letters, already on the chart, and a round spa has none.

(setq lzs:*ctreat* '("(ask)" "90" "Radius" "Diagonal"))

(setq lzs:*corners*
  '(("Rectangle"
     ("cornera" "Corner A (bottom left)")
     ("cornerb" "Corner B (bottom right)")
     ("cornerc" "Corner C (top right)")
     ("cornerd" "Corner D (top left)"))))

(defun lzs:corners (c) (cdr (assoc (car c) lzs:*corners*)))

;; is selection I a treatment that carries a size?  2 = Radius,
;; 3 = Diagonal; 90 sets back nothing and asks for no number.
(defun lzs:sized (i) (member i '(2 3)))

;;; -------------------- the other outline --------------------------------
;;;  SPA offers to draw the second outline once the first is down, and
;;;  "by dims" asks for its overalls under keys that are PER SHAPE --
;;;  the rectangle's second pair is w2/l2, the octagon's is b2/a2 plus
;;;  the cut face f2, the round one's is b2/a2.  Same question, three
;;;  key sets, so the table is per chart rather than one shared row.

(setq lzs:*second*
  '(("Rectangle"
     ("w2" "Other outline ACROSS")
     ("l2" "Other outline UP"))
    ("OCtagon"
     ("b2" "Other outline ACROSS")
     ("a2" "Other outline UP")
     ("f2" "Other outline cut FACE"))
    ("ROund"
     ("b2" "Other outline ACROSS")
     ("a2" "Other outline UP"))))

(defun lzs:second (c) (cdr (assoc (car c) lzs:*second*)))

(defun lzs:secondkeys (c / d out)
  (foreach d (lzs:second c) (setq out (cons (car d) out)))
  (reverse out))

;;; -------------------- where NA is a real answer ------------------------
;;;  The three-state contract sends NA as (key . nil), and SPA reads
;;;  that as "not measured" -- but only where the question ACCEPTS an
;;;  NA.  Its measurement sequences mark each item REQ / SUG / NAX, and
;;;  a REQ item fed a nil is not asked again: spa:askseqb stores the nil
;;;  straight into its answers and the flow then does arithmetic on it,
;;;  which in AutoLISP is an error, not a fallback.  (w and b are REQ;
;;;  so are the second outline's w2 and b2.)
;;;
;;;  So an NA typed against a key SPA has no NA for is demoted to an
;;;  EMPTY BOX -- nothing is sent and SPA asks, which is what the person
;;;  who typed it meant and is the same fail-safe direction as an
;;;  unparseable typo.  This list is the keys where NA really is an
;;;  answer, per chart.
;;;
;;;  Round's A is deliberately not here even though the sequence would
;;;  take it: its presence is the out-of-round GATE (see the chart note
;;;  above), so an NA there would switch branches to say nothing.

(setq lzs:*naok*
  '(("Rectangle" "l" "l2")
    ("OCtagon" "a" "s2" "tt" "ss" "s1" "vv" "a2" "f2")
    ("ROund" "a2")))

(defun lzs:naok (c) (cdr (assoc (car c) lzs:*naok*)))

;;; -------------------- the dropdowns every page carries -----------------
;;;  (key label (item ...)) -- item 0 is always "(ask)", the dropdown's
;;;  version of an empty box: nothing is sent and SPA asks as usual.
;;;
;;;  MODE is SPA's very first question and it changes the layer, the
;;;  linetype and the dimension style the whole run draws in, so it sits
;;;  at the top of the page rather than in with the rest.
;;;
;;;  GRADE and TAPER are what the Spa Cover Details block would have
;;;  supplied; answering them here does not remove the block pick (SPA
;;;  offers that up front, before anything else, and an entsel is not
;;;  something a form can answer) but it does settle the hinge maths.

(setq lzs:*lists*
  '(("mode"      "Water's edge or cover size"
     ("(ask)" "Watersedge" "Coversize"))
    ("second"    "Draw the other outline as well"
     ("(ask)" "Yes" "No"))
    ("method"    "Take the other outline from"
     ("(ask)" "Offset" "Dims"))
    ("autohinge" "Auto-hinge the cover"
     ("(ask)" "Yes" "No"))
    ("grade"     "Cover grade"
     ("(ask)" "STANDARD" "THERMOLIGHT"))
    ("taper"     "Taper"
     ("(ask)" "3-2" "4-2" "4-3" "5-3" "5-4" "3-3" "1-3/8"))))

(defun lzs:lvals (key) (caddr (assoc key lzs:*lists*)))
(defun lzs:llabel (key) (cadr (assoc key lzs:*lists*)))

(defun lzs:listkeys ( / d out)
  (foreach d lzs:*lists* (setq out (cons (car d) out)))
  (reverse out))

;;; -------------------- the per-page hint --------------------------------

(setq lzs:*hints*
  '(("Rectangle"
     "A B C D run from the bottom left, the way SPA numbers them.")
    ("OCtagon"
     "B and A alone draw a true square octagon -- NA the cut letters.")
    ("ROund"
     "Leave A empty for a circle; fill it in and the spa is out of round.")))

(defun lzs:hint (c) (cadr (assoc (car c) lzs:*hints*)))

;;; -------------------- which dims are wedged, and the bands -------------

;; The horizontal dims whose line IS this cut.
(defun lzs:cutdims (c y / d out)
  (foreach d (lzs:dims c)
    (if (and (= (nth 6 d) "h") (= (nth 3 d) y) (= (nth 5 d) y))
        (setq out (cons d out))))
  (reverse out))

;; Keys of every dim that lives in a wedge row rather than the column.
(defun lzs:wedge-keys (c / y d out)
  (foreach y (lzs:cuts c)
    (foreach d (lzs:cutdims c y)
      (setq out (cons (cadr d) out))))
  (reverse out))

;; The bands between the cuts: ((y0 . y1) ...), whole chart when a
;; chart declares no cuts.
(defun lzs:bands (c / ys prev out y)
  (setq ys (append (list 0) (lzs:cuts c) (list 1000))
        prev (car ys))
  (foreach y (cdr ys)
    (setq out (cons (cons prev y) out)
          prev y))
  (reverse out))

;; Every SPA key the chart's own picture and list can answer, drawn ones
;; first, in order.
(defun lzs:keys (c / d out)
  (foreach d (lzs:dims c) (setq out (cons (cadr d) out)))
  (foreach d (lzs:extra c) (setq out (cons (car d) out)))
  (reverse out))

;; Every key on the page that is a TYPED box: the chart's own, the
;; second outline's overalls, and the cover lap.
(defun lzs:boxkeys (c)
  (append (lzs:keys c) (lzs:secondkeys c) (list "gap")))

;;; -------------------- the answers -------------------------------------
;;;  What is typed is kept as the STRING the user typed, so the chart can
;;;  show it back exactly as entered -- 6'10" stays 6'10" -- and it is
;;;  only turned into a number when SPA is handed the form.

(setq lzs:*vals* nil)           ; ((key . "typed") ...)
(setq lzs:*picks* nil)          ; ((dropdown-key . index) ...)
(setq lzs:*focus* nil)          ; the key whose box has the caret
(setq lzs:*chart* nil)          ; the chart being filled in
(setq lzs:*pos* nil)            ; where the dialog was last standing
(setq lzs:*go* nil)             ; the chart a tab click asked for

(defun lzs:get (key / p)
  (if (setq p (assoc key lzs:*vals*)) (cdr p) ""))

(defun lzs:put (key v / out p)
  (foreach p lzs:*vals* (if (/= (car p) key) (setq out (cons p out))))
  (setq lzs:*vals* (reverse (cons (cons key v) out))))

(defun lzs:pget (key / p)
  (if (setq p (assoc key lzs:*picks*)) (cdr p) 0))

(defun lzs:pput (key i / out p)
  (foreach p lzs:*picks* (if (/= (car p) key) (setq out (cons p out))))
  (setq lzs:*picks* (reverse (cons (cons key i) out))))

;; The word a dropdown is standing on, or nil when it is still on
;; "(ask)" -- which is the form's way of sending nothing at all.
(defun lzs:pick (key / i v)
  (setq i (lzs:pget key)
        v (lzs:lvals key))
  (if (and v (> i 0)) (nth i v)))

;;; -------------------- drawing the chart -------------------------------
;;;  Pixel coordinates, origin top-left, y down -- image-tile convention,
;;;  which is why the per-mille data is stored that way too and needs no
;;;  flipping here.  dimx_tile / dimy_tile report the LARGEST legal
;;;  coordinate, not the size, and are only answerable while the dialog
;;;  is up, so everything below runs between new_dialog and start_dialog.

(setq lzs:*dx* 0)               ; the tile's extent this time round
(setq lzs:*dy* 0)
(setq lzs:*y0* 0)               ; the band being drawn, in per-mille --
(setq lzs:*y1* 1000)            ; the whole chart when nothing is cut

(setq lzs:*col-line* -16)       ; dialog foreground: the outline
(setq lzs:*col-back* -15)       ; dialog background: the clear
(setq lzs:*col-dim* 8)          ; grey: the dimension arrows
(setq lzs:*col-val* 30)         ; orange: a value that has been typed
(setq lzs:*col-hi* 5)           ; blue: the box round the active one

;; per-mille -> pixels
(defun lzs:px (v) (fix (/ (* v lzs:*dx*) 1000.0)))
(defun lzs:py (v)
  (fix (/ (* (- v lzs:*y0*) lzs:*dy*) (float (- lzs:*y1* lzs:*y0*)))))

(defun lzs:iny (v) (and (<= lzs:*y0* v) (<= v lzs:*y1*)))
(defun lzs:inband (v) (and (<= lzs:*y0* v) (< v lzs:*y1*)))

;; The segment, clipped to the band, or nil when none of it is inside.
;; Everything the bands draw goes through this, so a cut is one rule
;; applied everywhere rather than per-shape case work.
(defun lzs:clipseg (x1 y1 x2 y2 / ta tb lo hi)
  (cond
    ((= y1 y2)
     (if (lzs:iny y1) (list x1 y1 x2 y2)))
    (t
     (setq ta (/ (- lzs:*y0* y1) (float (- y2 y1)))
           tb (/ (- lzs:*y1* y1) (float (- y2 y1)))
           lo (max 0.0 (min ta tb))
           hi (min 1.0 (max ta tb)))
     (if (< lo hi)
         (list (+ x1 (* (- x2 x1) lo)) (+ y1 (* (- y2 y1) lo))
               (+ x1 (* (- x2 x1) hi)) (+ y1 (* (- y2 y1) hi)))))))

;; An arc as per-mille points.  DCL draws line segments and nothing
;; else, so an arc has to become a polyline sooner or later; doing it
;; here means the chart data can say what it means and say it once.
(defun lzs:arcpts (a / cx cy rx ry f to n i ang out)
  (setq cx (nth 1 a) cy (nth 2 a) rx (nth 3 a) ry (nth 4 a)
        f (nth 5 a) to (nth 6 a))
  (setq n (fix (/ (abs (- to f)) 6.0)))
  (if (< n 4) (setq n 4))
  (setq i 0)
  (while (<= i n)
    ;; NB: the angle local is not called t -- a local of that name would
    ;; shadow TRUE for the length of the call
    (setq ang (/ (* pi (+ f (/ (* (- to f) i) (float n)))) 180.0)
          out (cons (fix (- cy (* ry (sin ang))))
                    (cons (fix (+ cx (* rx (cos ang)))) out))
          i (1+ i)))
  (reverse out))

;; An outline element as a flat per-mille polyline, whichever it was.
(defun lzs:flatten (e)
  (if (= (type (car e)) 'STR) (lzs:arcpts e) e))

;; A polyline given as a flat per-mille list, clipped to the band.
(defun lzs:pline (flat col / s)
  (while (and flat (cddr flat))
    (if (setq s (lzs:clipseg (car flat) (cadr flat)
                             (caddr flat) (cadddr flat)))
        (vector_image (lzs:px (car s)) (lzs:py (cadr s))
                      (lzs:px (caddr s)) (lzs:py (cadddr s)) col))
    (setq flat (cddr flat))))

;; A polyline already in pixels, given as (x y x y ...).
(defun lzs:plinepx (flat col)
  (while (and flat (cddr flat))
    (vector_image (car flat) (cadr flat) (caddr flat) (cadddr flat) col)
    (setq flat (cddr flat))))

(defun lzs:glyph (ch / p)
  (if (setq p (assoc (strcase ch) lzs:*font*)) (cdr p)))

;; The width one string will occupy, in pixels, at SC tenths per unit.
(defun lzs:textw (s sc)
  (if (= s "") 0
      (fix (/ (* (- (* (strlen s) lzs:*font-adv*)
                    (- lzs:*font-adv* lzs:*font-w*))
                 sc)
              100.0))))

(defun lzs:texth (sc) (fix (/ (* lzs:*font-h* sc) 100.0)))

;; The size to letter the chart at.  Derived from the tile rather than
;; fixed: an image tile's pixel size falls out of the user's dialog font
;; and display DPI, and is not knowable until the dialog is up.
(defun lzs:basesc ( / sc)
  (setq sc (/ (* lzs:*dy* 100) 1560))
  (if (< sc 12) 12 sc))

;; Stroke S with its top-left corner at pixel X Y.  SC is a percentage
;; of the font's own tenth-units, so the caller can size text to fit.
(defun lzs:text (s x y sc col / i ch pen poly out n)
  (setq i 1 pen x)
  (while (<= i (strlen s))
    (setq ch (substr s i 1))
    (foreach poly (lzs:glyph ch)
      (setq out nil n poly)
      (while n
        (setq out (cons (+ y (fix (/ (* (cadr n) sc) 100.0)))
                        (cons (+ pen (fix (/ (* (car n) sc) 100.0))) out))
              n (cddr n)))
      (lzs:plinepx (reverse out) col))
    (setq pen (+ pen (fix (/ (* lzs:*font-adv* sc) 100.0)))
          i (1+ i)))
  pen)

;; The dimension line with an arrowhead at each end, in per-mille,
;; clipped to the band.  A head is drawn only when its own end is
;; inside the band -- the shaft of a vertical dimension can run through
;; several bands, and each draws just its stretch.
(defun lzs:arrow (x1 y1 x2 y2 col / s a b p q)
  (if (setq s (lzs:clipseg x1 y1 x2 y2))
      (vector_image (lzs:px (car s)) (lzs:py (cadr s))
                    (lzs:px (caddr s)) (lzs:py (cadddr s)) col))
  (setq a 6 b 3)
  (cond
    ((= y1 y2)                          ; horizontal: heads point in
     (if (lzs:iny y1)
         (progn
           (setq p (list (lzs:px (min x1 x2)) (lzs:py y1))
                 q (list (lzs:px (max x1 x2)) (lzs:py y1)))
           (vector_image (car p) (cadr p) (+ (car p) a) (- (cadr p) b) col)
           (vector_image (car p) (cadr p) (+ (car p) a) (+ (cadr p) b) col)
           (vector_image (car q) (cadr q) (- (car q) a) (- (cadr q) b) col)
           (vector_image (car q) (cadr q) (- (car q) a) (+ (cadr q) b) col))))
    (t                                  ; vertical
     (if (lzs:iny (min y1 y2))
         (progn
           (setq p (list (lzs:px x1) (lzs:py (min y1 y2))))
           (vector_image (car p) (cadr p) (- (car p) b) (+ (cadr p) a) col)
           (vector_image (car p) (cadr p) (+ (car p) b) (+ (cadr p) a) col)))
     (if (lzs:iny (max y1 y2))
         (progn
           (setq q (list (lzs:px x1) (lzs:py (max y1 y2))))
           (vector_image (car q) (cadr q) (- (car q) b) (- (cadr q) a) col)
           (vector_image (car q) (cadr q) (+ (car q) b) (- (cadr q) a) col))))))

;; Keep a text box inside the tile, whatever it was asked for.
(defun lzs:clampx (lx w)
  (cond ((< lx 2) 2)
        ((> (+ lx w) (- lzs:*dx* 2)) (- lzs:*dx* w 2))
        (t lx)))

(defun lzs:clampy (ly h)
  (cond ((< ly 2) 2)
        ((> (+ ly h) (- lzs:*dy* 2)) (- lzs:*dy* h 2))
        (t ly)))

;; Where one dimension's text belongs, and what it says: the LETTER
;; until a value is typed, then the value in the letter's place.  A
;; value too wide for its own span is shrunk to fit rather than allowed
;; to run into its neighbours.
(defun lzs:label (d / letter key x1 y1 x2 y2 side txt sc w h lx ly span mx my)
  (setq letter (car d) key (cadr d)
        x1 (lzs:px (nth 2 d)) y1 (lzs:py (nth 3 d))
        x2 (lzs:px (nth 4 d)) y2 (lzs:py (nth 5 d))
        side (nth 6 d)
        txt (lzs:get key)
        mx (/ (+ x1 x2) 2) my (/ (+ y1 y2) 2))
  (if (= txt "")
      (setq txt letter sc (lzs:basesc))
      (setq sc (/ (* (lzs:basesc) 90) 100)))
  (setq w (lzs:textw txt sc))
  (if (and (= side "h") (> w 0))
      (progn
        (setq span (abs (- x2 x1)))
        (if (> w span)
            (progn
              (setq sc (/ (* sc span) w))
              (if (< sc (/ (* (lzs:basesc) 55) 100))
                  (setq sc (/ (* (lzs:basesc) 55) 100)))
              (setq w (lzs:textw txt sc))))))
  (setq h (lzs:texth sc))
  (if (= side "h")
      (setq lx (- mx (/ w 2)) ly (- y1 h 4))
      ;; a vertical dimension labels at the TOP of its span, centred on
      ;; its own line, EXCEPT when that would run off the left edge --
      ;; an overall sits hard against the boundary with no room on its
      ;; outside, so its label goes on the inside rather than clipping
      (progn
        (setq ly (+ (min y1 y2) 5))
        (setq lx (if (< (- mx (/ w 2)) 2) (+ mx 4) (- mx (/ w 2))))))
  (setq lx (lzs:clampx lx w)
        ly (lzs:clampy ly h))
  ;; blank the strip behind it so the dimension line does not run
  ;; through the characters
  (fill_image (- lx 3) (- ly 2) (+ w 6) (+ h 4) lzs:*col-back*)
  (if (= key lzs:*focus*)
      (lzs:plinepx (list (- lx 3) (- ly 2) (+ lx w 3) (- ly 2)
                         (+ lx w 3) (+ ly h 2) (- lx 3) (+ ly h 2)
                         (- lx 3) (- ly 2))
                   lzs:*col-hi*))
  (lzs:text txt lx ly sc
            (if (= (lzs:get key) "") lzs:*col-line* lzs:*col-val*)))

;; A corner letter, centred on its per-mille point.  It answers nothing
;; -- it is there so the Corners rows and the picture agree about which
;; corner is which.
(defun lzs:mark (m / txt sc w h lx ly)
  (setq txt (car m)
        sc (lzs:basesc)
        w (lzs:textw txt sc)
        h (lzs:texth sc)
        lx (lzs:clampx (- (lzs:px (cadr m)) (/ w 2)) w)
        ly (lzs:clampy (- (lzs:py (caddr m)) (/ h 2)) h))
  (lzs:text txt lx ly sc lzs:*col-line*))

;; The band a dimension's TEXT belongs to: a horizontal dim sits on its
;; own line, a vertical one labels at the top of its span.
(defun lzs:anchor (d)
  (if (= (nth 6 d) "h")
      (nth 3 d)
      (min (nth 3 d) (nth 5 d))))

;; The whole picture: every band painted once, each between its own
;; start_image and end_image.  Wedge dims draw nothing at all -- their
;; row of the drawing IS a row of real boxes now -- while every other
;; dim draws its clipped arrow in every band it crosses and its text in
;; the band its anchor falls in.
(defun lzs:redraw ( / c wk bands b i key poly d m)
  (setq c lzs:*chart*
        wk (lzs:wedge-keys c)
        bands (lzs:bands c)
        i 0)
  (foreach b bands
    (setq key (strcat "chart" (itoa i))
          lzs:*y0* (car b)
          lzs:*y1* (cdr b)
          lzs:*dx* (dimx_tile key)
          lzs:*dy* (dimy_tile key))
    (start_image key)
    (fill_image 0 0 lzs:*dx* lzs:*dy* lzs:*col-back*)
    (foreach poly (lzs:outline c)
      (lzs:pline (lzs:flatten poly) lzs:*col-line*))
    (foreach d (lzs:dims c)
      (if (not (member (cadr d) wk))
          (lzs:arrow (nth 2 d) (nth 3 d) (nth 4 d) (nth 5 d)
                     lzs:*col-dim*)))
    (foreach m (lzs:marks c)
      (if (lzs:inband (caddr m)) (lzs:mark m)))
    (foreach d (lzs:dims c)
      (if (and (not (member (cadr d) wk))
               (lzs:inband (lzs:anchor d)))
          (lzs:label d)))
    (end_image)
    (setq i (1+ i)))
  (setq lzs:*y0* 0
        lzs:*y1* 1000)
  (princ))

;;; -------------------- what SPA will and will not ask -------------------
;;;  A page offers every question SPA could ask, and some of them stop
;;;  being questions the moment another one is answered.  These are the
;;;  keys the run will not reach, so they are greyed AND not sent -- a
;;;  form that quietly carries dead answers is harder to reason about
;;;  than one that does not, and SPA drops them unread on the way out
;;;  either way.
;;;
;;;    grade THERMOLIGHT  a Thermo-Light cover's water's edge and cover
;;;                       size are the SAME thing, so c:SPA sets the
;;;                       mode itself (Coversize), spa:askother declines
;;;                       to offer the second outline at all, and
;;;                       spa:askdetails forces the taper to 1-3/8.
;;;                       Mode, the whole cover block and the taper are
;;;                       therefore dead.
;;;    second No          spa:askother2 stops at the Yes/No, so the
;;;                       method, the lap and the by-dims overalls are
;;;                       never asked.
;;;    method Offset      the lap is asked, the by-dims overalls are not.
;;;    method Dims        the by-dims overalls are asked, the lap is not.
;;;
;;;  Auto-hinge survives all of it: Thermo-Light covers are hinged like
;;;  any other, only in velcro throughout.

(defun lzs:dead (c / g s m)
  (setq g (lzs:pick "grade")
        s (lzs:pick "second")
        m (lzs:pick "method"))
  (cond
    ((= g "THERMOLIGHT")
     (append (list "mode" "second" "method" "gap" "taper")
             (lzs:secondkeys c)))
    ((= s "No")
     (append (list "method" "gap") (lzs:secondkeys c)))
    ((= m "Offset") (lzs:secondkeys c))
    ((= m "Dims") (list "gap"))))

;; The tiles greying is allowed to touch on this page.  mode_tile on a
;; key that is not on the page would error, and every one of these is on
;; every page.
(defun lzs:greyable (c)
  (append (list "mode" "second" "method" "gap" "taper")
          (lzs:secondkeys c)))

(defun lzs:grey (c / dead k)
  (setq dead (lzs:dead c))
  (foreach k (lzs:greyable c)
    (mode_tile k (if (member k dead) 1 0)))
  (princ))

;;; -------------------- the dialog --------------------------------------
;;  Two columns: the chart on the left as a passive image cut into
;;  bands, the boxes on the right in the chart's own order, each
;;  labelled with its letter so the list and the picture read as one
;;  thing.

;; Chart keys packed into rows no wider than the budget.  Three charts
;; run about 39 cells, so this never wraps today -- it is here because
;; DCL does not scroll and a fourth shape must cost a row rather than
;; the whole form.
(setq lzs:*tabbudget* 84)

(defun lzs:tabrows ( / out row w c cw)
  (setq row nil w 0)
  (foreach c lzs:*charts*
    (setq cw (+ (strlen (car c)) 6))
    (if (and row (> (+ w cw) lzs:*tabbudget*))
      (setq out (cons (reverse row) out) row nil w 0))
    (setq row (cons (car c) row) w (+ w cw)))
  (if row (setq out (cons (reverse row) out)))
  (reverse out))

;; The tab strip: one button per chart.  DCL has no tab tile, so a tab
;; is a button that closes this page and reopens the next.
(defun lzs:tabstrip ( / out c n)
  (foreach c (lzs:tabrows)
    (setq out (cons "  : row {" out))
    (foreach n c
      (setq out (cons (strcat "    : button { key = \"tab_" n
                              "\"; label = \"" n "\"; }")
                      out)))
    (setq out (cons "  }" out)))
  (reverse out))

(setq lzs:*chart-w* 52)         ; the chart column, in character cells
(setq lzs:*chart-h* 19)         ; its total height, spread over the bands

;; character cells across for a per-mille x
(defun lzs:cellx (v) (/ (* v lzs:*chart-w*) 1000.0))

;; One wedge row: the cut's dims as real edit boxes, pushed to their
;; letters' positions by spacers.  Positions are in character cells and
;; a box has its own minimum size, so this is honest about being
;; approximate: a box lands within a cell or so of its letter, and two
;; that would collide get pushed apart rather than overlapped.
(defun lzs:wedgerow (c y / out d lbl w want pos)
  (setq out (list "      : row {")
        pos 0.0)
  ;; LEFT TO RIGHT, whatever order the chart lists them in: the row is
  ;; built by walking a cursor across it, and a dim listed before its
  ;; left-hand neighbour would shove that neighbour to the wrong side
  ;; of the chart
  (foreach d (vl-sort (lzs:cutdims c y)
                      '(lambda (p q)
                         (< (+ (nth 2 p) (nth 4 p))
                            (+ (nth 2 q) (nth 4 q)))))
    (setq lbl (car d)
          w (+ (strlen lbl) 10.0)       ; label + borders + 6-char box
          want (- (lzs:cellx (/ (+ (nth 2 d) (nth 4 d)) 2)) (/ w 2)))
    (if (< want (+ pos 0.5)) (setq want (+ pos 0.5)))
    (setq out (cons (strcat "        : spacer { width = "
                            (rtos (- want pos) 2 1) "; }")
                    out))
    (setq out (cons (strcat "        : edit_box { key = \"" (cadr d)
                            "\"; label = \"" lbl
                            "\"; edit_width = 6; fixed_width = true; }")
                    out))
    (setq pos (+ want w)))
  (setq out (cons "        spacer;" out))
  (reverse (cons "      }" out)))

;; The chart as a stack: an image tile per band, a wedge row at every
;; cut, heights split in proportion to the bands they show.
(defun lzs:bandtiles (c / out bands b i h)
  (setq i 0
        bands (lzs:bands c))
  (foreach b bands
    (setq h (/ (* (- (cdr b) (car b)) lzs:*chart-h*) 1000.0))
    (if (< h 0.8) (setq h 0.8))
    (setq out (append out
                      (list (strcat "      : image { key = \"chart" (itoa i)
                                    "\"; width = " (itoa lzs:*chart-w*)
                                    "; height = " (rtos h 2 1)
                                    "; fixed_width = true; "
                                    "fixed_height = true; color = -15; }"))))
    (if (< (1+ i) (length bands))
        (setq out (append out (lzs:wedgerow c (cdr b)))))
    (setq i (1+ i)))
  out)

(defun lzs:box (key label w)
  (strcat "        : edit_box { key = \"" key "\"; edit_width = "
          (itoa w) "; label = \"" label "\"; }"))

(defun lzs:popup (key w)
  (strcat "        : popup_list { key = \"" key "\"; label = \""
          (lzs:llabel key) "\"; edit_width = " (itoa w) "; }"))

;; The DCL name of a chart's page.
(defun lzs:dlgname (key) (strcat "lazspa_" (strcase key t)))

;; One dialog per chart.  They all live in one generated file so the
;; page loop can load_dialog once and switch pages without touching the
;; disk again.
(defun lzs:dcl-one (c / out d wk l)
  ;; out is consed newest-first and reversed once at the end, so this
  ;; seed list reads BACKWARDS: the label second here puts it second in
  ;; the file, after the line that opens the dialog.  The other way
  ;; round emits an attribute before its own dialog, which is not DCL.
  (setq out (list (strcat "  label = \"LazSpa - " (caddr c) "\";")
                  (strcat (lzs:dlgname (car c)) " : dialog {")))
  (setq out (append (reverse (lzs:tabstrip)) out))
  ;; MODE first, and on its own: it is SPA's opening question and it
  ;; settles the layer, the linetype and the dimension style everything
  ;; below is drawn in.
  (setq out (cons "  : boxed_row {" out))
  (setq out (cons "    label = \"This drawing\";" out))
  (setq out (cons (strcat "    : popup_list { key = \"mode\"; label = \""
                          (lzs:llabel "mode") "\"; edit_width = 12; }")
                  out))
  (setq out (cons "  }" out))
  (setq out (cons "  : row {" out))
  ;; PASSIVE image tiles, deliberately -- see the header -- stacked with
  ;; the wedge rows between them.
  (setq wk (lzs:wedge-keys c))
  (setq out (cons "    : column {" out))
  (foreach l (lzs:bandtiles c)
    (setq out (cons l out)))
  (setq out (cons "    }" out))
  (setq out (cons "    : column {" out))
  (setq out (cons "      : boxed_column {" out))
  (setq out (cons "        label = \"Dimensions\";" out))
  ;; only the dims that could NOT be wedged into the drawing -- the
  ;; vertical ones -- keep a row here; the across chains live on the
  ;; chart itself.  Each is its LETTER as a button and then the box:
  ;; clicking the letter puts the caret in that box and rings the
  ;; dimension on the chart, which is as close to clicking the drawing
  ;; itself as DCL allows.
  (foreach d (lzs:dims c)
    (if (not (member (cadr d) wk))
        (progn
          (setq out (cons "        : row {" out))
          (setq out (cons (strcat "          : button { key = \"pick_"
                                  (cadr d) "\"; label = \"" (car d)
                                  "\"; fixed_width = true; }")
                          out))
          (setq out (cons (strcat "          : edit_box { key = \"" (cadr d)
                                  "\"; edit_width = 9; label = \"" (nth 7 d)
                                  "\"; }")
                          out))
          (setq out (cons "        }" out)))))
  (setq out (cons "      }" out))
  (if (lzs:extra c)
    (progn
      (setq out (cons "      : boxed_column {" out))
      (setq out (cons "        label = \"Not on this view\";" out))
      (foreach d (lzs:extra c)
        (setq out (cons (lzs:box (car d) (cadr d) 9) out)))
      (setq out (cons "      }" out))))
  (if (lzs:corners c)
    (progn
      (setq out (cons "      : boxed_column {" out))
      (setq out (cons "        label = \"Corners\";" out))
      (foreach d (lzs:corners c)
        (setq out (cons "        : row {" out))
        (setq out (cons (strcat "          : popup_list { key = \"" (car d)
                                "\"; label = \"" (cadr d)
                                "\"; edit_width = 11; }")
                        out))
        (setq out (cons (strcat "          : edit_box { key = \"" (car d)
                                "-sz\"; label = \"size\"; "
                                "edit_width = 6; fixed_width = true; }")
                        out))
        (setq out (cons "        }" out)))
      (setq out (cons "      }" out))))
  (setq out (cons "      : boxed_column {" out))
  (setq out (cons "        label = \"The other outline\";" out))
  (setq out (cons (lzs:popup "second" 9) out))
  (setq out (cons (lzs:popup "method" 9) out))
  (setq out (cons (lzs:box "gap" "How far the cover laps the water's edge" 9)
                  out))
  (foreach d (lzs:second c)
    (setq out (cons (lzs:box (car d) (cadr d) 9) out)))
  (setq out (cons "      }" out))
  (setq out (cons "      : boxed_column {" out))
  (setq out (cons "        label = \"Hinges and cover details\";" out))
  (setq out (cons (lzs:popup "autohinge" 9) out))
  (setq out (cons (lzs:popup "grade" 13) out))
  (setq out (cons (lzs:popup "taper" 9) out))
  (setq out (cons "      }" out))
  (setq out (cons "    }" out))
  (setq out (cons "  }" out))
  (setq out (cons "  spacer;" out))
  (setq out (cons (strcat "  : text { key = \"hint\"; width = 62; label = \""
                          (lzs:hint c) "\"; }")
                  out))
  (setq out (cons (strcat "  : text { width = 62; label = \""
                          "Type NA where nothing was measured; leave a box "
                          "empty and SPA will ask.\"; }")
                  out))
  ;; the two things no form can answer, said on the form itself rather
  ;; than discovered at the command line
  (setq out (cons (strcat "  : text { width = 62; label = \""
                          "The Spa Cover Details block pick and the "
                          "spillaway questions stay at the command line.\"; }")
                  out))
  (setq out (cons "  : row {" out))
  (setq out (cons (strcat "    : button { key = \"accept\"; label = \"Insert\"; "
                          "is_default = true; fixed_width = true; }")
                  out))
  (setq out (cons (strcat "    : button { key = \"cancel\"; label = \"Cancel\"; "
                          "is_cancel = true; fixed_width = true; }")
                  out))
  (setq out (cons "  }" out))
  (reverse (cons "}" out)))

;; Every page, one after another, in one file.
(defun lzs:dcl-lines ( / out c)
  (foreach c lzs:*charts*
    (setq out (append out (lzs:dcl-one c) (list ""))))
  out)

(defun lzs:write-lines (fh / l)
  (foreach l (lzs:dcl-lines) (write-line l fh)))

(defun lzs:write-dcl ( / f fh err)
  (setq f (vl-filename-mktemp "lazspa" nil ".dcl"))
  (if (and f (setq fh (open f "w")))
    (progn
      (setq err (vl-catch-all-apply 'lzs:write-lines (list fh)))
      (close fh)
      (cond
        ((vl-catch-all-error-p err) (vl-file-delete f) nil)
        (t f)))))

;;; -------------------- what SPA is handed ------------------------------
;;;  The three states of STANDARDS.md's form contract, decided here and
;;;  unchanged from LAZFORM's:
;;;
;;;    box left empty   the key is not sent at all -> SPA asks
;;;    NA typed in it   (key . nil) is sent        -> SPA takes NA
;;;    a measurement    (key . 84.0) is sent       -> SPA takes it
;;;
;;;  Anything that is neither NA nor a distance AutoCAD can read is
;;;  treated as an empty box: a typo must leave SPA asking rather than
;;;  quietly feeding it a nil that means something else entirely.
;;;  distof reads the architectural spellings, so 6'10" and 6'-10-1/2"
;;;  arrive as the numbers they look like.
;;;
;;;  A dropdown left on "(ask)" is the same as an empty box and sends
;;;  nothing.

(defun lzs:answer (v / n)
  (cond
    ((or (null v) (= v "")) 'SKIP)
    ((= (strcase (lzs:trim v)) "NA") nil)
    ((setq n (distof (lzs:trim v) 4)) n)
    ((setq n (distof (lzs:trim v) 2)) n)
    (t 'SKIP)))

(defun lzs:trim (s / i n)
  (setq i 1 n (strlen s))
  (while (and (<= i n) (= (substr s i 1) " ")) (setq i (1+ i)))
  (while (and (>= n i) (= (substr s n 1) " ")) (setq n (1- n)))
  (if (> i n) "" (substr s i (1+ (- n i)))))

;; One typed box, as SPA should hear it.  'SKIP means "send nothing".
;; An NA against a key SPA has no NA for is demoted to SKIP -- see
;; lzs:*naok* for why that is a fail-safe rather than a shrug.
(defun lzs:keyanswer (c key / a)
  (setq a (lzs:answer (lzs:get key)))
  (if (and (null a) (not (member key (lzs:naok c))))
      'SKIP
      a))

;; The (key . value) pairs the corner rows contribute.  A dropdown left
;; on (ask) sends nothing; a sized treatment carries its size when one
;; parses, and sends the treatment alone when it does not -- SPA then
;; asks for just the number.
(defun lzs:cornerpairs (c / out d stem i ty a)
  (foreach d (lzs:corners c)
    (setq stem (car d))
    (if (> (setq i (lzs:pget stem)) 0)
        (progn
          (setq ty (nth i lzs:*ctreat*))
          (setq out (cons (cons (read (strcat stem "-ty")) ty) out))
          (if (lzs:sized i)
              (progn
                (setq a (lzs:answer (lzs:get (strcat stem "-sz"))))
                (if (numberp a)
                    (setq out (cons (cons (read (strcat stem "-sz")) a)
                                    out))))))))
  (reverse out))

;; The alist SPA reads, built from what was typed.  The insertion base
;; point is NOT in it: SPA picks that in the drawing with the user's own
;; snaps live, which is where it belongs.
(defun lzs:form ( / c out dead k v a)
  (setq c lzs:*chart*
        dead (lzs:dead c)
        out (list (cons 'shape (cadr c))))
  (foreach k (lzs:listkeys)
    (if (and (not (member k dead)) (setq v (lzs:pick k)))
        (setq out (cons (cons (read k) v) out))))
  (foreach k (lzs:boxkeys c)
    (if (not (member k dead))
        (progn
          (setq a (lzs:keyanswer c k))
          (if (not (eq a 'SKIP))
              (setq out (cons (cons (read k) a) out))))))
  (foreach k (lzs:cornerpairs c)
    (setq out (cons k out)))
  (reverse out))

;;; -------------------- the run -----------------------------------------
;;  A helper rather than the command body, so its localized *error* is
;;  out of scope by the time SPA is started: SPA installs its own, and a
;;  SPA that fails must report as SPA.

;; A dropdown changed: remember it, re-grey what that answer kills, and
;; repaint the chart the list may have unrolled across.
(defun lzs:listpick (key v)
  (lzs:pput key (atoi v))
  (lzs:grey lzs:*chart*)
  (lzs:redraw)
  (princ))

;; A corner dropdown changed: remember it, grey or un-grey its size box,
;; and repaint the chart.
(defun lzs:cornerpick (stem v / i)
  (setq i (atoi v))
  (lzs:pput stem i)
  (mode_tile (strcat stem "-sz") (if (lzs:sized i) 0 1))
  (lzs:redraw)
  (princ))

;; Open a page where the user last had the dialog.  done_dialog reports
;; the position it was closed at and new_dialog takes one back, but only
;; as a 4-argument call -- and a build that answered done_dialog with
;; something other than a point would poison every reopen, so the shape
;; is checked before it is trusted and the plain 2-argument call is the
;; fallback.
(defun lzs:newdlg (name dcl)
  (if (and lzs:*pos* (listp lzs:*pos*) (= (length lzs:*pos*) 2)
           (numberp (car lzs:*pos*)) (numberp (cadr lzs:*pos*)))
      (new_dialog name dcl "" lzs:*pos*)
      (new_dialog name dcl)))

(defun lzs:show (chartkey / *error* f dcl rc c d n go done out)
  (defun *error* (msg)
    (term_dialog)
    (if (and dcl (>= dcl 0)) (unload_dialog dcl))
    (setq dcl nil)
    (if f (vl-file-delete f))
    (setq f nil)
    (if (and msg (not (wcmatch (strcase msg)
                               "*BREAK*,*CANCEL*,*QUIT*,*EXIT*")))
      (princ (strcat "\nLAZSPA error: " msg)))
    (princ))
  (setq lzs:*vals* nil
        lzs:*picks* nil                 ; every dropdown back to (ask)
        lzs:*pos* nil                   ; where the user last had it
        go chartkey)
  (cond
    ((not (lzs:chart go))
     (princ (strcat "\nLAZSPA: no chart called " go ".")))
    ((not (setq f (lzs:write-dcl)))
     (princ "\nLAZSPA error: could not write the dialog file."))
    ((< (setq dcl (load_dialog f)) 0)
     (princ "\nLAZSPA error: could not load the dialog file."))
    (t
     ;; The page loop.  DCL has no tab tile, so a tab is a button that
     ;; closes this page and reopens the next -- and because done_dialog
     ;; hands back where the dialog was standing, it reopens exactly
     ;; there instead of wandering off to the middle of the screen.
     ;; Everything typed lives in lzs:*vals* and lzs:*picks*, keyed, so
     ;; it survives the switch and is still there if you tab back.
     (while (not done)
       (setq lzs:*chart* (lzs:chart go)
             c lzs:*chart*
             lzs:*focus* nil)
       (cond
         ((not (lzs:newdlg (lzs:dlgname go) dcl))
          (princ "\nLAZSPA error: could not open the form.")
          (setq done t))
         (t
          ;; the plain dropdowns: filled, put back to their remembered
          ;; pick, and each harvests into its own store the moment it
          ;; changes -- get_tile answers about a LIVE dialog, and by the
          ;; time the answers are assembled this one is closed
          (foreach d (lzs:listkeys)
            (start_list d)
            (foreach n (lzs:lvals d) (add_list n))
            (end_list)
            (set_tile d (itoa (lzs:pget d)))
            (action_tile d
              (strcat "(lzs:listpick \"" d "\" $value)")))
          ;; the corner dropdowns, with their size boxes greyed unless
          ;; the remembered pick takes a size
          (foreach d (lzs:corners c)
            (start_list (car d))
            (foreach n lzs:*ctreat* (add_list n))
            (end_list)
            (set_tile (car d) (itoa (lzs:pget (car d))))
            (set_tile (strcat (car d) "-sz")
                      (lzs:get (strcat (car d) "-sz")))
            (mode_tile (strcat (car d) "-sz")
                       (if (lzs:sized (lzs:pget (car d))) 0 1))
            (action_tile (car d)
              (strcat "(lzs:cornerpick \"" (car d) "\" $value)"))
            (action_tile (strcat (car d) "-sz")
              (strcat "(lzs:put \"" (car d) "-sz\" $value)")))
          ;; put back what was typed before this page was opened
          (foreach d (lzs:boxkeys c) (set_tile d (lzs:get d)))
          (foreach d (lzs:boxkeys c)
            (action_tile d
              (strcat "(lzs:put \"" d "\" $value) (setq lzs:*focus* \"" d "\")"
                      " (lzs:redraw)")))
          ;; clicking a dimension's letter: caret into its box, with the
          ;; box's contents selected so the first keystroke replaces
          ;; rather than appends, and the dimension ringed on the chart.
          ;; Wedge dims have no pick button -- their box already sits on
          ;; the drawing where the letter was.
          (foreach d (lzs:dims c)
            (if (not (member (cadr d) (lzs:wedge-keys c)))
                (action_tile (strcat "pick_" (cadr d))
                  (strcat "(setq lzs:*focus* \"" (cadr d) "\") (lzs:redraw)"
                          " (mode_tile \"" (cadr d) "\" 2)"
                          " (mode_tile \"" (cadr d) "\" 3)"))))
          ;; the tabs -- each closes this page and names the next
          (foreach d lzs:*charts*
            (action_tile (strcat "tab_" (car d))
              (strcat "(setq lzs:*go* \"" (car d)
                      "\" lzs:*pos* (done_dialog 4))")))
          ;; the chart takes no action at all -- it is a passive image
          ;; tile, and an image_button would be wiped on hover
          (action_tile "accept" "(setq lzs:*pos* (done_dialog 1))")
          (action_tile "cancel" "(setq lzs:*pos* (done_dialog 0))")
          (lzs:redraw)
          (lzs:grey c)
          (setq rc (start_dialog))
          (cond
            ((= rc 4) (setq go lzs:*go*))     ; a tab: go round again
            (t (setq done t
                     out (if (= rc 1) (lzs:form))))))))))
  (if (and dcl (>= dcl 0)) (unload_dialog dcl))
  (setq dcl nil)
  (if f (vl-file-delete f))
  (setq f nil)
  out)

;;; -------------------- commands ----------------------------------------

(defun c:LAZSPA ( / form)
  (cond
    ;; the chart fills SPA's answers in, so SPA has to be here to
    ;; receive them -- say so plainly rather than opening a form whose
    ;; Insert button could only fail
    ((not spa:run-with-answers)
     (princ "\nLAZSPA: SPA is not loaded in this session -- APPLOAD")
     (princ "\n        lisp/spa/SPA.LSP, or LAZPASS.lsp which has both."))
    ((setq form (lzs:show (car (car lzs:*charts*))))
     (princ (strcat "\nLAZSPA: " (itoa (length form))
                    " answers to SPA; it will ask for whatever is left."))
     (spa:run-with-answers form))
    (t (princ "\nLAZSPA: cancelled, nothing drawn.")))
  (princ))

(defun c:LAZSPAVER ()
  (princ (strcat "\nLAZSPA " *lazspa-version* " (LAZSPA.lsp) - "
                 (itoa (length lzs:*charts*)) " chart(s)."))
  (princ))

(princ (strcat "\nLAZSPA " *lazspa-version*
               " loaded.  Type LAZSPA to fill a chart in and draw it."))
(princ)


;;; ======================================================================
;;; >>> LAZFORM.lsp
;;; ======================================================================

;;; ======================================================================
;;; LAZFORM.lsp  --  fill a dimension chart in, then draw the pool
;;; ----------------------------------------------------------------------
;;; For AutoCAD 2018 and later (plain AutoLISP, no external libraries).
;;;
;;; Commands:  LAZFORM        fill in a shape chart and run POOL from it
;;;            LAZASCII       probe: could the chart be drawn in text?
;;;            LAZTXT         the same form, drawn out of tiles
;;;            LAZFORMVER     print the loaded version
;;;
;;; SHARED BUILD: requires CALOFIN-LIB.lsp (load via CALOFIN-LOADER.lsp).
;;; Generic helpers live there under cal: - see STANDARDS.md.
;;;
;;; The chart on screen is the one off the paper: the pool outline, the
;;; hopper, and the dimension chain with its letters.  Type a number
;;; against a letter and the letter is REPLACED by what you typed --
;;; which is what the letter was standing in for all along.  Every box
;;; is labelled with its own letter, so the list and the picture read
;;; as one thing.  Fill in what you know, leave the rest blank, press
;;; Insert: POOL runs and asks only for the gaps.
;;;
;;; NA in a box means "not measured" and is passed through as such --
;;; different from leaving it blank, which just means POOL should ask.
;;;
;;; ZERO INSTALL, like LAZPANEL: the dialog is plain DCL written to the
;;; temp folder at run time, and the chart is drawn with vector_image,
;;; so there is no artwork file to ship and nothing to NETLOAD.
;;;
;;; WHY THE BOXES ARE BESIDE THE PICTURE AND NOT ON IT.  DCL packs tiles
;;; into rows and columns: no absolute positioning, no overlapping, so
;;; an edit box cannot sit on an image tile.  DCL also cannot display a
;;; raster at all -- an image tile takes vectors or an AutoCAD slide,
;;; nothing else.  Hence the chart is drawn rather than loaded, the
;;; numbers appear ON it as they are typed, and clicking it moves the
;;; caret: between them those two recover most of what a text box
;;; sitting on the artwork would have given, without a DLL to install.
;;; (An earlier version also let you click the picture to jump to a
;;; box; DCL took that back -- see "why the picture is not clickable".)
;;;
;;; ADDING A SHAPE is adding data, not code -- one entry in
;;; lzf:*charts* with an outline, a dimension list and its POOL keys,
;;; plus a row in whichever of lzf:*cuts*, lzf:*cross*, lzf:*picks*
;;; and lzf:*corners* the sheet needs.  Eight charts so far:
;;; Rectangle, True Oval, Roman, both Grecians, True L Left, Round and
;;; Octagon.  Watch the keys rather than the letters when you add one:
;;; the same letter means different things on different sheets -- a
;;; rectangle's B is the side length, an oval's B is the tip-to-tip
;;; total and its SIDE is T -- so the mapping is per chart and is
;;; checked against POOL's own question lists by tests/test_lazform.py.
;;;
;;; WHAT IS LIVE ON A PAGE IS ONE FUNCTION'S DECISION.  lzf:dead reads
;;; the whole state of the page -- the bottom type, the in-square
;;; toggle and the mode dropdowns -- and names every key POOL will not
;;; ask about.  lzf:btgrey greys exactly that set and lzf:form drops
;;; exactly that set, so what is greyed and what is sent cannot say
;;; different things.
;;; ======================================================================

(vl-load-com)

(setq *lazform-version* "v2.5")

;;; -------------------- the stroke font ---------------------------------
;;;  DCL has no way to draw text into an image tile -- vector_image draws
;;;  line segments and that is the whole of it -- so the letters and the
;;;  numbers on the chart are stroked out of segments here.
;;;
;;;  One entry per character: the glyph as a list of polylines, each a
;;;  flat list of x y x y ... in TENTHS of a font unit, on a cell 4 wide
;;;  and 6 tall with y running DOWN the way image-tile pixels do.
;;;  Integers, so nothing here depends on float formatting.

(setq lzf:*font* '(
    ("A" (0 60 20 0 40 60) (8 40 32 40))
    ("B" (0 0 0 60) (0 0 30 0 40 10 40 20 30 30 0 30) (30 30 40 40 40 50 30 60 0 60))
    ("C" (40 10 30 0 10 0 0 10 0 50 10 60 30 60 40 50))
    ("D" (0 0 0 60) (0 0 30 0 40 10 40 50 30 60 0 60))
    ("E" (40 0 0 0 0 60 40 60) (0 30 30 30))
    ("F" (40 0 0 0 0 60) (0 30 30 30))
    ("G" (40 10 30 0 10 0 0 10 0 50 10 60 30 60 40 50 40 30 20 30))
    ("H" (0 0 0 60) (40 0 40 60) (0 30 40 30))
    ("I" (10 0 30 0) (20 0 20 60) (10 60 30 60))
    ("J" (30 0 30 50 20 60 10 60 0 50))
    ("K" (0 0 0 60) (40 0 0 35) (14 25 40 60))
    ("L" (0 0 0 60 40 60))
    ("M" (0 60 0 0 20 30 40 0 40 60))
    ("N" (0 60 0 0 40 60 40 0))
    ("O" (10 0 30 0 40 10 40 50 30 60 10 60 0 50 0 10 10 0))
    ("P" (0 60 0 0 30 0 40 10 40 20 30 30 0 30))
    ("Q" (10 0 30 0 40 10 40 50 30 60 10 60 0 50 0 10 10 0) (25 45 40 60))
    ("R" (0 60 0 0 30 0 40 10 40 20 30 30 0 30) (20 30 40 60))
    ("S" (40 10 30 0 10 0 0 10 0 20 10 30 30 30 40 40 40 50 30 60 10 60 0 50))
    ("T" (0 0 40 0) (20 0 20 60))
    ("U" (0 0 0 50 10 60 30 60 40 50 40 0))
    ("V" (0 0 20 60 40 0))
    ("W" (0 0 10 60 20 20 30 60 40 0))
    ("X" (0 0 40 60) (40 0 0 60))
    ("Y" (0 0 20 30 40 0) (20 30 20 60))
    ("Z" (0 0 40 0 0 60 40 60))
    ("0" (10 0 30 0 40 10 40 50 30 60 10 60 0 50 0 10 10 0) (5 55 35 5))
    ("1" (10 10 20 0 20 60) (10 60 30 60))
    ("2" (0 10 10 0 30 0 40 10 40 20 0 60 40 60))
    ("3" (0 0 40 0 20 25) (20 25 40 35 40 50 30 60 10 60 0 50))
    ("4" (30 60 30 0 0 40 40 40))
    ("5" (40 0 0 0 0 25 30 25 40 35 40 50 30 60 10 60 0 50))
    ("6" (40 0 20 0 0 20 0 50 10 60 30 60 40 50 40 40 30 30 10 30 0 40))
    ("7" (0 0 40 0 15 60))
    ("8" (10 30 0 20 0 10 10 0 30 0 40 10 40 20 30 30 10 30 0 40 0 50 10 60 30 60 40 50 40 40 30 30))
    ("9" (0 60 20 60 40 40 40 10 30 0 10 0 0 10 0 20 10 30 30 30 40 20))
    ("." (17 54 23 54 23 60 17 60 17 54))
    ("-" (5 30 35 30))
    ("'" (20 0 20 16))
    ("\"" (13 0 13 16) (27 0 27 16))
    ("/" (0 60 40 0))
    (":" (20 16 20 22) (20 40 20 46))
    ("%" (0 60 40 0) (5 5 12 5) (28 55 35 55))
    ("#" (10 0 6 60) (30 0 26 60) (0 20 40 20) (0 40 40 40))
    (" ")
))

(setq lzf:*font-w* 40)          ; glyph cell width, tenths
(setq lzf:*font-h* 60)          ; glyph cell height, tenths
(setq lzf:*font-adv* 56)        ; pen advance per character, tenths

;;; -------------------- the charts --------------------------------------
;;;  Everything is in PER-MILLE of the picture, x and y, y down -- the
;;;  same convention as an image tile, so the only conversion at draw
;;;  time is a multiply.  Integers again.
;;;
;;;  A chart is:
;;;    (key  pool-shape  title
;;;      (outline-polyline ...)
;;;      (dimension ...)
;;;      (column-only-field ...))
;;;
;;;  A dimension is (letter poolkey x1 y1 x2 y2 side label), where side
;;;  is "h" or "v" -- which way the measurement runs, and so where its
;;;  text sits.  The arrow, the letter and the typed value all come off
;;;  those two endpoints, so there is no separate position table that
;;;  could fall out of step with the drawing.
;;;
;;;  A column-only field is (poolkey label): a real POOL answer with no
;;;  place on the plan -- the depths are read off a section, not this
;;;  view -- so it gets a box in the list and nothing on the picture.
;;;
;;;  THE SPORT CHAIN (E2 F2 G F1 E1) is column-only on every sheet
;;;  that carries it.  A sport bottom asks a different plan chain from
;;;  the one these charts are drawn with -- E2 F2 G F1 E1 M L K, not
;;;  H G F E M L K -- and only G, M, L and K are shared, so its own
;;;  letters have nowhere to sit on a drawing of a hopper.  They are
;;;  listed here with POOL's own prompts, and lzf:dead greys them
;;;  unless the bottom type actually is Sport.

(setq lzf:*charts* '(
  ("Rectangle" "Rectangle" "Rectangle"
   ;; pool outline, hopper flat, the four slopes, deep-end wall
   ((100 300 900 300 900 860 100 860 100 300)
    (275 475 400 475 400 700 275 700 275 475)
    (100 300 275 475)
    (100 860 275 700)
    (400 475 685 300)
    (400 700 685 860)
    (685 300 685 860))
   (("B"  "tp" 100 175 900 175 "h" "overall across, top side")
    ("A"  "le"  45 300  45 860 "v" "overall up, left end")
    ("H"  "h"  100 580 275 580 "h" "left end to the hopper")
    ("G"  "g"  275 580 400 580 "h" "hopper length (0 = slope bottom)")
    ("F"  "f"  400 580 685 580 "h" "hopper to the slope break")
    ("E"  "e"  685 580 900 580 "h" "slope break to the right end")
    ("M"  "m"  437 300 437 475 "v" "top side to the hopper")
    ("L"  "l"  437 475 437 700 "v" "hopper width")
    ("K"  "k"  437 700 437 860 "v" "hopper to the bottom side"))
   (("bo" "overall across, bottom side (out-of-square only)")
    ("ri" "overall up, right end (out-of-square only)")
    ("c"  "C - wall height (shallow depth)")
    ("d"  "D - deep end depth")
    ("c2" "C2 - shallow floor at the break")
    ("e2" "E2 - left end shallow flat")
    ("f2" "F2 - left slope")
    ("f1" "F1 - right slope")
    ("e1" "E1 - right end shallow flat")))

  ;; ---------------- True Oval ----------------
  ;;  Careful: B is NOT the key it is on the rectangle.  A rectangle's B
  ;;  is the side length (tp); an oval's B is the tip-to-tip total
  ;;  (tot), and it is the SIDE that becomes T.  The two charts share a
  ;;  letter and not a meaning, which is exactly the sort of thing this
  ;;  table exists to write down.
  ("Oval" "Oval" "True Oval"
   (("A" 310 500 250 250 90 270)
     (310 250 690 250)
     ("A" 690 500 250 250 90 -90)
     (310 750 690 750)
     ("A" 310 500 120 120 90 270)
     (310 380 400 380) (400 380 400 620) (310 620 400 620)
     (400 380 690 250) (400 620 690 750)
     (690 250 690 750))
   (("B"  "tot" 60 130 940 130 "h" "total length, arc tip to arc tip")
    ("T"  "tp" 310 205 690 205 "h" "straight side length, top and bottom")
    ("A"  "le"  35 250  35 750 "v" "end length, left and right")
    ("H"  "h"   60 580 190 580 "h" "H - pool left tip to hopper tip")
    ("G"  "g"  190 580 400 580 "h" "G - hopper length, tip to right edge")
    ("F"  "f"  400 580 690 580 "h" "F - hopper to slope break")
    ("E"  "e"  690 580 940 580 "h" "E - slope break to pool right tip")
    ("W"  "w"  310 345 400 345 "h" "W - hopper flat top")
    ("M"  "m"  437 250 437 380 "v" "M - top side to hopper")
    ("L"  "l"  437 380 437 620 "v" "L - hopper width")
    ("K"  "k"  437 620 437 750 "v" "K - hopper to bottom side"))
   (("lr" "R1 - LEFT oval end radius")
    ("rr" "R2 - RIGHT oval end radius")
    ("r3" "R3 - hopper end radius")
    ("bo" "side length BOTTOM (out-of-square only)")
    ("ri" "end length RIGHT (out-of-square only)")
    ("c"  "C - wall height (shallow depth)")
    ("d"  "D - deep end depth")
    ("c2" "C2 - shallow floor at the break")
    ;; the Normal bottom re-asks the side as a CHECK, under a key of
    ;; its own (pool:hopoval), so it is a second box and not the T on
    ;; the drawing
    ("tt" "T - straight side length (check)")
    ("e2" "E2 - left end shallow flat")
    ("f2" "F2 - left slope")
    ("f1" "F1 - right slope")
    ("e1" "E1 - right end shallow flat")))

  ;; ---------------- Roman ----------------
  ;;  S / S1 / V / R are asked once per end when both ends are "perfect"
  ;;  and twice when they are not, so the right-hand halves sit in the
  ;;  column below: fill them in and answer No to the perfect question.
  ("ROman" "ROman" "Roman"
   ((160 250 840 250)
     ("A" 840 500 100 250 90 -90)
     (840 750 160 750)
     (160 750 100 621)
     ("A" 140 500 80 140 120 240)
     (160 250 100 379)
     ("A" 330 500 110 120 90 270)
     (330 380 420 380) (420 380 420 620) (330 620 420 620)
     (420 380 700 250) (420 620 700 750)
     (700 250 700 750)
     (160 250 300 385) (160 750 300 615))
   (("B"  "b"   60 130 940 130 "h" "B - overall length")
    ("T"  "tt" 160 205 840 205 "h" "T - side length, top and bottom")
    ("A"  "a"   35 250  35 750 "v" "A - overall width")
    ("S"  "sl"  60 205 160 205 "h" "S - end setback")
    ("S1" "s1l" 90 250  90 379 "v" "S1 - corner drop")
    ("V"  "vl" 125 379 125 621 "v" "V - end width")
    ("H"  "h"   60 580 220 580 "h" "H - left end to hopper")
    ("G"  "g"  220 580 420 580 "h" "G - hopper length")
    ("F"  "f"  420 580 700 580 "h" "F - hopper to slope break")
    ("E"  "e"  700 580 940 580 "h" "E - slope break to right end")
    ("W"  "w"  330 345 420 345 "h" "W - hopper flat top")
    ("M"  "m"  455 250 455 380 "v" "M - top side to hopper")
    ("L"  "l"  455 380 455 620 "v" "L - hopper width")
    ("K"  "k"  455 620 455 750 "v" "K - hopper to bottom side"))
   (("r1" "R1 - LEFT end radius (check)")
    ("r2" "R2 - RIGHT end radius (check)")
    ("r3" "R3 - hopper end radius")
    ("sr"  "S - RIGHT end setback (ends not perfect)")
    ("s1r" "S1 - RIGHT corner drop (ends not perfect)")
    ("vr"  "V - RIGHT end width (ends not perfect)")
    ("c"  "C - wall height (shallow depth)")
    ("d"  "D - deep end depth")
    ("c2" "C2 - shallow floor at the break")
    ("e2" "E2 - left end shallow flat")
    ("f2" "F2 - left slope")
    ("f1" "F1 - right slope")
    ("e1" "E1 - right end shallow flat")))

  ;; ---------------- Grecian, six-sided hopper ----------------
  ;;  These letters exist only on the Overall input path with a SIX
  ;;  hopper taped by Letters, so the form answers those three gates
  ;;  itself rather than filling in boxes nothing would ever read.
  ("Grecian" "Grecian" "Grecian (6-Sided Hopper)"
   ((190 250 780 250) (780 250 900 380) (900 380 900 620)
     (900 620 780 750) (780 750 190 750) (190 750 100 620)
     (100 620 100 380) (100 380 190 250)
     (250 440 330 380) (330 380 420 380) (420 380 420 620)
     (330 620 420 620) (250 560 330 620) (250 440 250 560)
     (420 380 690 250) (420 620 690 750) (690 250 690 750)
     (190 250 250 440) (190 750 250 560))
   (("B"  "b"  100 120 900 120 "h" "B - overall length")
    ("S"  "ss" 100 205 190 205 "h" "S - corner cut along the side")
    ("T"  "tt" 190 205 780 205 "h" "T - top side length")
    ("S1" "s1"  70 250  70 380 "v" "S1 - corner cut down the end")
    ("A"  "a"   20 250  20 750 "v" "A - overall width")
    ("V"  "vv"  55 380  55 620 "v" "V - end width")
    ("H"  "h"  100 580 250 580 "h" "H - left end to hopper")
    ("G"  "g"  250 580 420 580 "h" "G - hopper length")
    ("W"  "w"  270 330 350 330 "h" "W - top flat, cut corner to hopper end")
    ("L1" "l1" 225 440 225 560 "v" "L1 - hopper left edge length")
    ("M"  "m"  455 250 455 380 "v" "M - top side to hopper")
    ("L"  "l"  455 380 455 620 "v" "L - hopper width")
    ("K"  "k"  455 620 455 750 "v" "K - hopper to bottom side")
    ("F"  "f"  420 580 690 580 "h" "F - hopper to slope break")
    ("E"  "e"  690 580 900 580 "h" "E - slope break to right end"))
   (("x"  "X - hopper cut face length (check)")
    ("s2" "S2 - corner cut face (check)")
    ("c"  "C - wall height (shallow depth)")
    ("d"  "D - deep end depth")
    ("c2" "C2 - shallow floor at the break")
    ("e2" "E2 - left end shallow flat")
    ("f2" "F2 - left slope")
    ("f1" "F1 - right slope")
    ("e1" "E1 - right end shallow flat"))
   (("imeth" . "Overall") ("htype" . "SIX") ("hmode" . "Letters")))

  ;; ---------------- Grecian, square hopper ----------------
  ("GRSquare" "Grecian" "Grecian (Square Hopper)"
   ((190 250 780 250) (780 250 900 380) (900 380 900 620)
     (900 620 780 750) (780 750 190 750) (190 750 100 620)
     (100 620 100 380) (100 380 190 250)
     (250 380 420 380) (420 380 420 620) (250 620 420 620)
     (250 380 250 620)
     (420 380 690 250) (420 620 690 750) (690 250 690 750)
     (190 250 250 380) (190 750 250 620))
   (("B"  "b"  100 120 900 120 "h" "B - overall length")
    ("S"  "ss" 100 205 190 205 "h" "S - corner cut along the side")
    ("T"  "tt" 190 205 780 205 "h" "T - top side length")
    ("S1" "s1"  70 250  70 380 "v" "S1 - corner cut down the end")
    ("A"  "a"   20 250  20 750 "v" "A - overall width")
    ("V"  "vv"  55 380  55 620 "v" "V - end width")
    ("H"  "h"  100 580 250 580 "h" "H - left end to hopper")
    ("G"  "g"  250 580 420 580 "h" "G - hopper length")
    ("M"  "m"  455 250 455 380 "v" "M - top side to hopper")
    ("L"  "l"  455 380 455 620 "v" "L - hopper width")
    ("K"  "k"  455 620 455 750 "v" "K - hopper to bottom side")
    ("F"  "f"  420 580 690 580 "h" "F - hopper to slope break")
    ("E"  "e"  690 580 900 580 "h" "E - slope break to right end"))
   (("s2" "S2 - corner cut face (check)")
    ("c"  "C - wall height (shallow depth)")
    ("d"  "D - deep end depth")
    ("c2" "C2 - shallow floor at the break")
    ("e2" "E2 - left end shallow flat")
    ("f2" "F2 - left slope")
    ("f1" "F1 - right slope")
    ("e1" "E1 - right end shallow flat"))
   (("imeth" . "Overall") ("htype" . "Square")))

  ;; ---------------- True L Left ----------------
  ;;  The six sides are POOL's ab..fa, and the chart letters walk the
  ;;  same ring: B is the bottom (A-B), A1 the right end (B-C), B2 the
  ;;  wing top (C-D), A2 the step down to the reverse corner (D-E), B1
  ;;  the main-section top (E-F), A the left end (F-A).  The "Reverse
  ;;  Corner" the sheet names is POOL's inner corner E, asked as a
  ;;  treatment and not answerable from here -- it is a corner, not a
  ;;  measurement, so it gets no box.
  ("L" "L" "True L Left"
   ((100 400 640 400) (640 400 640 150) (640 150 900 150)
     (900 150 900 850) (900 850 100 850) (100 850 100 400)
     (250 520 400 520) (400 520 400 730) (250 730 400 730)
     (250 520 250 730)
     (100 400 250 520) (100 850 250 730)
     (400 520 640 400) (400 730 640 850)
     (640 400 640 850))
   (("B"  "ab" 100 920 900 920 "h" "side A-B, bottom, full length")
    ("A1" "bc" 960 150 960 850 "v" "end B-C, right end, full height")
    ("B2" "cd" 640  90 900  90 "h" "side C-D, top of the wing")
    ("A2" "de" 600 150 600 400 "v" "step D-E, down to the reverse corner")
    ("B1" "ef" 100 340 640 340 "h" "side E-F, top of the main section")
    ("A"  "fa"  45 400  45 850 "v" "end F-A, left end")
    ("H"  "h"  100 625 250 625 "h" "H - left end to deep end")
    ("G"  "g"  250 625 400 625 "h" "G - hopper length")
    ("F"  "f"  400 625 640 625 "h" "F - hopper to slope break")
    ("E"  "e"  640 625 900 625 "h" "E - slope break to right end")
    ("M"  "m"  430 400 430 520 "v" "M - top side to hopper")
    ("L"  "l"  430 520 430 730 "v" "L - hopper width")
    ("K"  "k"  430 730 430 850 "v" "K - hopper to bottom side"))
   (("c" "C - wall height (shallow depth)")
    ("d" "D - deep end depth")
    ("c2" "C2 - shallow floor at the break")))

  ;; ---------------- Round ----------------
  ;;  POOL's ROUnd flow asks two overalls -- B across and A up, both
  ;;  through the middle -- and then hands the bottom to the SAME
  ;;  hopper routine the oval uses (pool:hopovaldsp), so the hopper
  ;;  letters here are the oval's: H G F E, W, M L K.  The plan pair is
  ;;  NOT the oval's: a round pool answers b and a, where an oval
  ;;  answers tot, tp and le.
  ;;
  ;;  In square, POOL asks one diameter and keys it 'b -- so B is the
  ;;  box that matters and A goes unread.  Tick the in-square toggle
  ;;  and fill B in.
  ;;
  ;;  M L K RUN THROUGH THE CENTRE, and they have to.  POOL resolves
  ;;  that chain against the overall width, so M+L+K must equal A --
  ;;  and on a circle the only vertical that is a full diameter is the
  ;;  one through the middle.  Measured anywhere else it comes up short
  ;;  (the first draft put them at the hopper's own x and the chain
  ;;  closure test caught it: 460 against an A of 500).  So the hopper
  ;;  is drawn wide enough to cross that centre line, which is also
  ;;  where the tape goes.
  ;;
  ;;  H G F E ARE COLUMN BOXES HERE, not a wedge row on the drawing.
  ;;  A wedge box is its letter plus ten cells, so four of them need 44
  ;;  of the chart's 52 -- and a round pool spans about 31.  On the
  ;;  rectangle the chain runs the full width and just fits; on a
  ;;  circle it cannot, and forcing it makes boxes that sit nowhere
  ;;  near the letters they belong to.  So this chart declares cuts for
  ;;  B and W only and the chain is answered in the list, where it has
  ;;  room.  Every dimension is still enterable; only the position of
  ;;  four boxes differs.
  ("ROUnd" "ROUnd" "Round"
   (("A" 500 500 250 250 0 360)
    ("A" 390 500 70 70 90 270)
    (390 430 540 430) (540 430 540 570) (390 570 540 570)
    (540 430 660 350) (540 570 660 650)
    (660 350 660 650))
   (("B"  "b"  250 150 750 150 "h" "B - overall length (across)")
    ("A"  "a"  175 250 175 750 "v" "A - overall width (up)")
    ("H"  "h"  250 600 320 600 "h" "H - pool left edge to hopper tip")
    ("G"  "g"  320 600 540 600 "h" "G - hopper length, tip to right edge")
    ("F"  "f"  540 600 660 600 "h" "F - hopper to slope break")
    ("E"  "e"  660 600 750 600 "h" "E - slope break to pool right edge")
    ("W"  "w"  390 405 540 405 "h" "W - hopper flat top")
    ("M"  "m"  500 250 500 430 "v" "M - top of pool to hopper")
    ("L"  "l"  500 430 500 570 "v" "L - hopper width")
    ("K"  "k"  500 570 500 750 "v" "K - hopper to bottom of pool"))
   (("c"  "C - wall height (shallow depth)")
    ("d"  "D - deep end depth")
    ("c2" "C2 - shallow floor at the break")
    ;; the round pool hands its bottom to the oval's routine, which
    ;; re-asks the straight side as a check even on a circle
    ("tt" "T - straight side length (check)")
    ("e2" "E2 - left end shallow flat")
    ("f2" "F2 - left slope")
    ("f1" "F1 - right slope")
    ("e1" "E1 - right end shallow flat")))

  ;; ---------------- Octagon ----------------
  ;;  POOL reaches the octagon through the SAME flow as the grecian --
  ;;  (pool:grecflow t) -- so the letters are the grecian square-hopper
  ;;  set exactly: B S T on the top, A S1 V down the end, H G F E across
  ;;  the middle, M L K at the hopper, and S2 for the far corner cut.
  ;;  The sheet bears that out.  The geometry is GRSquare's, deliberately
  ;;  and to the coordinate: that outline already IS an eight-sided pool
  ;;  with a cut at every corner, and its numbers are the ones the
  ;;  box-position audit has been passing all along.
  ;;
  ;;  S2 IS A COLUMN BOX, like GRSquare's.  It measures the far corner's
  ;;  cut FACE, which runs diagonally; a dim on this chart is "h" or "v"
  ;;  and nothing else, so a diagonal has no place to be drawn and is
  ;;  answered in the list.
  ;;
  ;;  The gates pin what the drawing assumes, the way both grecians do:
  ;;  Overall input (which is what an octagon defaults to anyway, since
  ;;  A and B are enough), and the square hopper this chart draws.  An
  ;;  octagon with a SIX-sided hopper asks for W and L1 as well and
  ;;  wants a sheet of its own; we do not have one.
  ("OCtagon" "OCtagon" "Octagon"
   ((190 250 780 250) (780 250 900 380) (900 380 900 620)
     (900 620 780 750) (780 750 190 750) (190 750 100 620)
     (100 620 100 380) (100 380 190 250)
     (250 380 420 380) (420 380 420 620) (250 620 420 620)
     (250 380 250 620)
     (420 380 690 250) (420 620 690 750) (690 250 690 750)
     (190 250 250 380) (190 750 250 620))
   (("B"  "b"  100 120 900 120 "h" "B - overall length")
    ("S"  "ss" 100 205 190 205 "h" "S - corner cut along the side")
    ("T"  "tt" 190 205 780 205 "h" "T - top side length")
    ("S1" "s1"  70 250  70 380 "v" "S1 - corner cut down the end")
    ("A"  "a"   20 250  20 750 "v" "A - overall width")
    ("V"  "vv"  55 380  55 620 "v" "V - end width")
    ("H"  "h"  100 580 250 580 "h" "H - left end to hopper")
    ("G"  "g"  250 580 420 580 "h" "G - hopper length")
    ("M"  "m"  455 250 455 380 "v" "M - top side to hopper")
    ("L"  "l"  455 380 455 620 "v" "L - hopper width")
    ("K"  "k"  455 620 455 750 "v" "K - hopper to bottom side")
    ("F"  "f"  420 580 690 580 "h" "F - hopper to slope break")
    ("E"  "e"  690 580 900 580 "h" "E - slope break to right end"))
   (("s2" "S2 - corner cut face (check)")
    ("c"  "C - wall height (shallow depth)")
    ("d"  "D - deep end depth")
    ("c2" "C2 - shallow floor at the break")
    ("e2" "E2 - left end shallow flat")
    ("f2" "F2 - left slope")
    ("f1" "F1 - right slope")
    ("e1" "E1 - right end shallow flat"))
   (("imeth" . "Overall") ("htype" . "Square")))
))

;;; -------------------- chart access ------------------------------------

(defun lzf:chart (key / c out)
  (foreach c lzf:*charts*
    (if (and (not out) (= (car c) key)) (setq out c)))
  out)

(defun lzf:outline (c) (nth 3 c))
(defun lzf:dims (c) (nth 4 c))
(defun lzf:extra (c) (nth 5 c))

;; Answers a chart implies rather than asks for.  The Grecian letters
;; exist only on the Overall input path with the hopper type the chart
;; draws -- pick "Measured" instead and every letter typed here goes
;; unread -- so the chart answers those gates itself.  A chart with
;; nothing to imply simply has none.
(defun lzf:gates (c) (nth 6 c))

;;; -------------------- cross dims and the mode dropdowns ----------------
;;;  A cross dim is a tape run corner to corner, and it is the one
;;;  measurement that has no place at all on a chart drawn square: it
;;;  runs diagonally, and a dim here is "h" or "v" and nothing else.
;;;  So every one of them is a column box.
;;;
;;;  HOW MANY OF THEM POOL ASKS FOR DEPENDS ON A QUESTION OF ITS OWN,
;;;  and that question is a dropdown here:
;;;
;;;    Rectangle / Oval   cmode   Corner | Middle | Ends
;;;                       Corner and Middle tape two diagonals, Ends
;;;                       tapes four (pool:crosstemplate).
;;;    the Grecians       gcross  Simple | Center | Complex
;;;                       Simple tapes the two body diagonals; Center
;;;                       and Complex tape 14 and 18, far more than a
;;;                       sheet has boxes for, so the dropdown answers
;;;                       the gate and the dims are typed at the
;;;                       command line (pool:grecmode).
;;;
;;;  Left on "(ask)" the boxes are all dead and none of them travels:
;;;  which box is which diagonal is undefined until the mode is, so a
;;;  number typed into one would be attached to the wrong tape.
;;;
;;;  The L's nine diagonals need no such question -- POOL asks for the
;;;  same nine every time -- so that chart carries the boxes and no
;;;  mode dropdown.  Its "mirror" dropdown is a different sort of
;;;  thing: a plain keyword question with a home on this page, which is
;;;  why a pick declares the section it belongs to.

(setq lzf:*cross*
  '(("Rectangle" ("x0" "Cross dim 1") ("x1" "Cross dim 2")
                 ("x2" "Cross dim 3") ("x3" "Cross dim 4"))
    ("Oval"      ("x0" "Cross dim 1") ("x1" "Cross dim 2")
                 ("x2" "Cross dim 3") ("x3" "Cross dim 4"))
    ("ROman"     ("ac" "Cross dim body A-C") ("bd" "Cross dim body B-D"))
    ("Grecian"   ("x0" "Cross dim 1") ("x1" "Cross dim 2"))
    ("GRSquare"  ("x0" "Cross dim 1") ("x1" "Cross dim 2"))
    ("OCtagon"   ("x0" "Cross dim 1") ("x1" "Cross dim 2"))
    ("L"         ("ac" "Cross dim A-C") ("bd" "Cross dim B-D")
                 ("ce" "Cross dim C-E") ("df" "Cross dim D-F")
                 ("ae" "Cross dim A-E") ("bf" "Cross dim B-F")
                 ("ad" "Cross dim A-D") ("be" "Cross dim B-E")
                 ("cf" "Cross dim C-F"))))

(defun lzf:cross (c) (cdr (assoc (car c) lzf:*cross*)))

;; The keyword dropdowns a page carries beyond the bottom type:
;;   (key label section (choice ...))
;; section "cross" puts the dropdown at the head of the cross-dim box
;; and ties its life to them -- in square there are no cross dims, so
;; there is no mode to pick either; section "run" is a question in its
;; own right and sits with the toggle and the bottom type.
(setq lzf:*picks*
  '(("Rectangle" ("cmode" "Cross dims measured from" "cross"
                  ("(ask)" "Corner" "Middle" "Ends")))
    ("Oval"      ("cmode" "Cross dims measured from" "cross"
                  ("(ask)" "Corner" "Middle" "Ends")))
    ("Grecian"   ("gcross" "Cross-dim detail" "cross"
                  ("(ask)" "Simple" "Center" "Complex")))
    ("GRSquare"  ("gcross" "Cross-dim detail" "cross"
                  ("(ask)" "Simple" "Center" "Complex")))
    ("OCtagon"   ("gcross" "Cross-dim detail" "cross"
                  ("(ask)" "Simple" "Center" "Complex")))
    ("L"         ("mirror" "Mirror the pool (wing swaps sides)" "run"
                  ("(ask)" "Yes" "No")))))

(defun lzf:picks (c) (cdr (assoc (car c) lzf:*picks*)))

;; How many of a chart's cross boxes each mode leaves live.  A mode
;; this table does not name -- "(ask)" above all -- leaves none.
(setq lzf:*crosslive* '(("Corner" 2) ("Middle" 2) ("Ends" 4) ("Simple" 2)))

;; The dropdown that decides how many cross boxes are live, or nil.
(defun lzf:crossmode (c / d out)
  (foreach d (lzf:picks c)
    (if (and (not out) (= (caddr d) "cross")) (setq out (car d))))
  out)

;; the dropdown selections, by key: (("cmode" . 3) ...)
(setq lzf:*pvals* nil)

(defun lzf:pget (key / p)
  (if (setq p (assoc key lzf:*pvals*)) (cdr p) 0))

(defun lzf:pput (key i / out p)
  (foreach p lzf:*pvals* (if (/= (car p) key) (setq out (cons p out))))
  (setq lzf:*pvals* (reverse (cons (cons key i) out))))

;; What a dropdown is set to, as the word POOL would read -- "" while
;; it is still on "(ask)", which is the form's version of an empty box.
(defun lzf:pickval (c key / d i)
  (if (setq d (assoc key (lzf:picks c)))
      (progn
        (setq i (lzf:pget key))
        (if (and (> i 0) (< i (length (cadddr d)))) (nth i (cadddr d)) ""))
      ""))

;; The cross boxes this page's mode leaves live, counted off the front
;; of the chart's list -- the order the template asks them in.
(defun lzf:crosslive (c / m p)
  (if (setq m (lzf:crossmode c))
      (if (setq p (assoc (lzf:pickval c m) lzf:*crosslive*)) (cadr p) 0)
      (length (lzf:cross c))))

;; The charts POOL never asks a bottom type on.  The L family takes
;; the standard hopper and nothing else, so the popup is greyed, btype
;; is not sent, and the page is greyed against "Normal" -- the bottom
;; those flows really draw.
(setq lzf:*nobtype* '("L" "LAzyl"))

(defun lzf:btlive (c) (not (member (car c) lzf:*nobtype*)))

;; The charts whose flow puts a yes/no gate in front of the corner
;; questions ("Anything to record about the corners?").  Answer a
;; corner row on one of these and the gate is answered Yes for you;
;; leave every row on "(ask)" and the gate is left for POOL to ask.
;; The rectangle and the oval have no such gate.
(setq lzf:*crecharts*
  '("L" "LAzyl" "Grecian" "GRSquare" "OCtagon" "ROman"))

;;; -------------------- where the chart is cut ---------------------------
;;;  The closest DCL comes to boxes ON the drawing: the chart is cut
;;;  into horizontal bands at the heights where its horizontal
;;;  dimension rows run, and those rows are REAL edit boxes wedged
;;;  between the bands, pushed to their letters' positions by spacers.
;;;  The vertical dimensions cannot be wedged -- a box cannot stand
;;;  sideways in a row -- so they keep their boxes in the side column
;;;  with their values drawn on the chart as before.
;;;
;;;  A cut is a per-mille y that must land EXACTLY on a horizontal
;;;  dimension's line; every "h" dimension at that y becomes a wedge
;;;  box and loses its drawn arrow, since the row of boxes IS that row
;;;  of the drawing now.  tests/test_lazform.py checks both ways: no
;;;  cut without dims on it, and the wedge boxes sitting where the
;;;  letters were, within the tolerance spacer widths allow.

(setq lzf:*cuts* '(("Rectangle" 175 580)
                   ("Oval" 130 205 345 580)
                   ("ROman" 130 205 345 580)
                   ("Grecian" 120 205 330 580)
                   ("GRSquare" 120 205 580)
                   ("L" 90 340 625 920)
                   ("ROUnd" 150 405)
                   ("OCtagon" 120 205 580)))

(defun lzf:cuts (c) (cdr (assoc (car c) lzf:*cuts*)))

;;; -------------------- corners -----------------------------------------
;;;  A corner is a treatment plus, when the treatment is Radius or Cut,
;;;  a size -- so each gets a dropdown and a size box that is greyed
;;;  until a sized treatment is picked.  The dropdown's first entry is
;;;  "(ask)": the form's version of leaving a box empty, and the only
;;;  honest default, since POOL offers no default on a first corner
;;;  either.
;;;
;;;  IN SQUARE AND OUT OF SQUARE ARE DIFFERENT QUESTIONS, and that is
;;;  the whole reason a row carries two lists of POOL stems rather than
;;;  one name.  A row is
;;;
;;;      (stem  label  (in-square stem ...)  (out-of-square stem ...))
;;;
;;;  where stem is the row's own tile key and each list is the POOL
;;;  corner questions that row answers in that state.  An EMPTY list
;;;  means the row is not read at all there.  Three shapes of that:
;;;
;;;    Rectangle, Roman   four rows out of square, one question in
;;;                       square -- so corner A's row maps to "corners"
;;;                       and B, C and D map to nothing.
;;;    the Grecians       two collective rows.  In square POOL asks
;;;                       exactly those two (bodycorners, endcorners);
;;;                       out of square it asks all eight individually,
;;;                       so each row FANS OUT to its four, carrying
;;;                       one treatment and one size to all of them.
;;;    True L             two rows, the same two questions either way.
;;;
;;;  On the shapes that gate their corner questions behind a yes/no
;;;  (lzf:*crecharts*), picking any row answers that gate too.

(setq lzf:*ctreat* '("(ask)" "Square" "Radius" "Cut" "NotGiven"))

(setq lzf:*corners*
  '(("Rectangle"
     ("cornera" "Corner A (bottom left)"  ("corners") ("cornera"))
     ("cornerb" "Corner B (bottom right)" ()          ("cornerb"))
     ("cornerc" "Corner C (top right)"    ()          ("cornerc"))
     ("cornerd" "Corner D (top left)"     ()          ("cornerd")))
    ("ROman"
     ("cornera" "Corner A (bottom left)"  ("corners") ("cornera"))
     ("cornerb" "Corner B (bottom right)" ()          ("cornerb"))
     ("cornerc" "Corner C (top right)"    ()          ("cornerc"))
     ("cornerd" "Corner D (top left)"     ()          ("cornerd")))
    ("Grecian"
     ("bodycorners" "Body corners (all four)" ("bodycorners")
      ("cornera" "cornerb" "cornerc" "cornerd"))
     ("endcorners" "End-tip corners (LT LB RT RB)" ("endcorners")
      ("cornerlt" "cornerlb" "cornerrt" "cornerrb")))
    ("GRSquare"
     ("bodycorners" "Body corners (all four)" ("bodycorners")
      ("cornera" "cornerb" "cornerc" "cornerd"))
     ("endcorners" "End-tip corners (LT LB RT RB)" ("endcorners")
      ("cornerlt" "cornerlb" "cornerrt" "cornerrb")))
    ("OCtagon"
     ("bodycorners" "Body corners (all four)" ("bodycorners")
      ("cornera" "cornerb" "cornerc" "cornerd"))
     ("endcorners" "End-tip corners (LT LB RT RB)" ("endcorners")
      ("cornerlt" "cornerlb" "cornerrt" "cornerrb")))
    ("L"
     ("outercorners" "Outer corners (all five)"
      ("outercorners") ("outercorners"))
     ("innercorner" "Reverse corner E"
      ("innercorner") ("innercorner")))))

(defun lzf:corners (c) (cdr (assoc (car c) lzf:*corners*)))

;; the dropdown selections, by stem: ((\"cornera\" . 3) ...)
(setq lzf:*cvals* nil)

(defun lzf:cget (stem / p)
  (if (setq p (assoc stem lzf:*cvals*)) (cdr p) 0))

(defun lzf:cput (stem i / out p)
  (foreach p lzf:*cvals* (if (/= (car p) stem) (setq out (cons p out))))
  (setq lzf:*cvals* (reverse (cons (cons stem i) out))))

;; is selection I a sized treatment?  2 = Radius, 3 = Cut
(defun lzf:csized (i) (member i '(2 3)))

;; the dropdown changed: remember it, grey or un-grey the size box,
;; and repaint the chart the list may have unrolled across
(defun lzf:cornerpick (stem v / i)
  (setq i (atoi v))
  (lzf:cput stem i)
  (mode_tile (strcat stem "-sz") (if (lzf:csized i) 0 1))
  (lzf:redraw)
  (princ))

;; A mode dropdown changed: remember it, repaint the chart the list
;; unrolled across, and re-decide what is live -- a cross-dim mode is
;; one of the things lzf:dead reads, so the boxes under it change
;; state as the mode is picked.
(defun lzf:pickpick (key v)
  (lzf:pput key (atoi v))
  (lzf:redraw)
  (lzf:btgrey lzf:*chart*)
  (princ))

;; The horizontal dims whose line IS this cut.
(defun lzf:cutdims (c y / d out)
  (foreach d (lzf:dims c)
    (if (and (= (nth 6 d) "h") (= (nth 3 d) y) (= (nth 5 d) y))
        (setq out (cons d out))))
  (reverse out))

;; Keys of every dim that lives in a wedge row rather than the column.
(defun lzf:wedge-keys (c / y d out)
  (foreach y (lzf:cuts c)
    (foreach d (lzf:cutdims c y)
      (setq out (cons (cadr d) out))))
  (reverse out))

;; The bands between the cuts: ((y0 . y1) ...), whole chart when a
;; chart declares no cuts.
(defun lzf:bands (c / ys prev out y)
  (setq ys (append (list 0) (lzf:cuts c) (list 1000))
        prev (car ys))
  (foreach y (cdr ys)
    (setq out (cons (cons prev y) out)
          prev y))
  (reverse out))

;; Every POOL key the chart can answer with a BOX, drawn ones first,
;; then the column-only fields, then the cross dims.
(defun lzf:keys (c / d out)
  (foreach d (lzf:dims c) (setq out (cons (cadr d) out)))
  (foreach d (lzf:extra c) (setq out (cons (car d) out)))
  (foreach d (lzf:cross c) (setq out (cons (car d) out)))
  (reverse out))

;; Everything on the page that can be greyed and can be sent: the
;; boxes, the dropdowns that carry a keyword answer, and the bottom
;; type.  lzf:dead is measured against this, so a rule may name a key
;; no chart carries without anything having to know.
(defun lzf:pagekeys (c / out d)
  (setq out (lzf:keys c))
  (foreach d (lzf:picks c) (setq out (append out (list (car d)))))
  (append out (list "btype")))

;;; -------------------- the answers -------------------------------------
;;;  What is typed is kept as the STRING the user typed, so the chart can
;;;  show it back exactly as entered -- 12'6" stays 12'6" -- and it is
;;;  only turned into a number when POOL is handed the form.

(setq lzf:*vals* nil)           ; ((key . "typed") ...)
(setq lzf:*focus* nil)          ; the key whose box has the caret
(setq lzf:*chart* nil)          ; the chart being filled in
(setq lzf:*insq* nil)           ; the in-square toggle, as it is set
(setq lzf:*btype* 0)            ; the bottom-type row, as it is picked
(setq lzf:*pos* nil)            ; where the dialog was last standing
(setq lzf:*go* nil)             ; the chart a tab click asked for

(defun lzf:get (key / p)
  (if (setq p (assoc key lzf:*vals*)) (cdr p) ""))

(defun lzf:put (key v / out p)
  (foreach p lzf:*vals* (if (/= (car p) key) (setq out (cons p out))))
  (setq lzf:*vals* (reverse (cons (cons key v) out))))

;;; -------------------- drawing the chart -------------------------------
;;;  Pixel coordinates, origin top-left, y down -- image-tile convention,
;;;  which is why the per-mille data is stored that way too and needs no
;;;  flipping here.  dimx_tile / dimy_tile report the LARGEST legal
;;;  coordinate, not the size, and are only answerable while the dialog
;;;  is up, so everything below runs between new_dialog and start_dialog.

(setq lzf:*dx* 0)               ; the tile's extent this time round
(setq lzf:*dy* 0)
(setq lzf:*y0* 0)               ; the band being drawn, in per-mille --
(setq lzf:*y1* 1000)            ; the whole chart when nothing is cut

(setq lzf:*col-line* -16)       ; dialog foreground: the outline
(setq lzf:*col-back* -15)       ; dialog background: the clear
(setq lzf:*col-dim* 8)          ; grey: the dimension arrows
(setq lzf:*col-val* 30)         ; orange: a value that has been typed
(setq lzf:*col-hi* 5)           ; blue: the box round the active one

;; per-mille -> pixels
(defun lzf:px (v) (fix (/ (* v lzf:*dx*) 1000.0)))
(defun lzf:py (v)
  (fix (/ (* (- v lzf:*y0*) lzf:*dy*) (float (- lzf:*y1* lzf:*y0*)))))

(defun lzf:iny (v) (and (<= lzf:*y0* v) (<= v lzf:*y1*)))

;; The segment, clipped to the band, or nil when none of it is inside.
;; Everything the bands draw goes through this, so a cut is one rule
;; applied everywhere rather than per-shape case work.
(defun lzf:clipseg (x1 y1 x2 y2 / ta tb lo hi)
  (cond
    ((= y1 y2)
     (if (lzf:iny y1) (list x1 y1 x2 y2)))
    (t
     (setq ta (/ (- lzf:*y0* y1) (float (- y2 y1)))
           tb (/ (- lzf:*y1* y1) (float (- y2 y1)))
           lo (max 0.0 (min ta tb))
           hi (min 1.0 (max ta tb)))
     (if (< lo hi)
         (list (+ x1 (* (- x2 x1) lo)) (+ y1 (* (- y2 y1) lo))
               (+ x1 (* (- x2 x1) hi)) (+ y1 (* (- y2 y1) hi)))))))

;;  An outline element is either a POLYLINE -- a flat list of per-mille
;;  numbers, x y x y ... -- or an ARC, written
;;
;;      ("A" cx cy rx ry from to)
;;
;;  with the centre and both radii in per-mille and the angles in
;;  degrees, 0 due east and counting anticlockwise ON SCREEN.  Since
;;  image-tile y runs DOWN, that is a minus on the y term and nowhere
;;  else.  Two radii rather than one because these charts want half of
;;  an ellipse as often as half of a circle.
;;
;;  DCL draws line segments and nothing else, so an arc has to become a
;;  polyline sooner or later; doing it here means the chart data can say
;;  what it means and say it once.

(defun lzf:arcpts (a / cx cy rx ry f to n i ang out)
  (setq cx (nth 1 a) cy (nth 2 a) rx (nth 3 a) ry (nth 4 a)
        f (nth 5 a) to (nth 6 a))
  (setq n (fix (/ (abs (- to f)) 6.0)))
  (if (< n 4) (setq n 4))
  (setq i 0)
  (while (<= i n)
    ;; NB: the angle local is not called t -- a local of that name would
    ;; shadow TRUE for the length of the call
    (setq ang (/ (* pi (+ f (/ (* (- to f) i) (float n)))) 180.0)
          out (cons (fix (- cy (* ry (sin ang))))
                    (cons (fix (+ cx (* rx (cos ang)))) out))
          i (1+ i)))
  (reverse out))

;; An outline element as a flat per-mille polyline, whichever it was.
(defun lzf:flatten (e)
  (if (= (type (car e)) 'STR) (lzf:arcpts e) e))

;; A polyline given as a flat per-mille list, clipped to the band.
(defun lzf:pline (flat col / s)
  (while (and flat (cddr flat))
    (if (setq s (lzf:clipseg (car flat) (cadr flat)
                             (caddr flat) (cadddr flat)))
        (vector_image (lzf:px (car s)) (lzf:py (cadr s))
                      (lzf:px (caddr s)) (lzf:py (cadddr s)) col))
    (setq flat (cddr flat))))

;; A polyline already in pixels, given as (x y x y ...).
(defun lzf:plinepx (flat col)
  (while (and flat (cddr flat))
    (vector_image (car flat) (cadr flat) (caddr flat) (cadddr flat) col)
    (setq flat (cddr flat))))

(defun lzf:glyph (ch / p out)
  (if (setq p (assoc (strcase ch) lzf:*font*)) (cdr p)))

;; The width one string will occupy, in pixels, at SC tenths per unit.
(defun lzf:textw (s sc)
  (if (= s "") 0
      (fix (/ (* (- (* (strlen s) lzf:*font-adv*)
                    (- lzf:*font-adv* lzf:*font-w*))
                 sc)
              100.0))))

(defun lzf:texth (sc) (fix (/ (* lzf:*font-h* sc) 100.0)))

;; The size to letter the chart at.  Derived from the tile rather than
;; fixed: an image tile's pixel size falls out of the user's dialog font
;; and display DPI, and is not knowable until the dialog is up.  This
;; puts a glyph at about a twenty-sixth of the picture's height, which
;; is the size the paper charts letter at.
(defun lzf:basesc ( / sc)
  (setq sc (/ (* lzf:*dy* 100) 1560))
  (if (< sc 12) 12 sc))

;; Stroke S with its top-left corner at pixel X Y.  SC is a percentage
;; of the font's own tenth-units, so the caller can size text to fit.
(defun lzf:text (s x y sc col / i ch pen poly out n)
  (setq i 1 pen x)
  (while (<= i (strlen s))
    (setq ch (substr s i 1))
    (foreach poly (lzf:glyph ch)
      (setq out nil n poly)
      (while n
        (setq out (cons (+ y (fix (/ (* (cadr n) sc) 100.0)))
                        (cons (+ pen (fix (/ (* (car n) sc) 100.0))) out))
              n (cddr n)))
      (lzf:plinepx (reverse out) col))
    (setq pen (+ pen (fix (/ (* lzf:*font-adv* sc) 100.0)))
          i (1+ i)))
  pen)

;; The dimension line with an arrowhead at each end, in per-mille,
;; clipped to the band.  A head is drawn only when its own end is
;; inside the band -- the shaft of a vertical dimension can run
;; through several bands, and each draws just its stretch.
(defun lzf:arrow (x1 y1 x2 y2 col / s a b p q)
  (if (setq s (lzf:clipseg x1 y1 x2 y2))
      (vector_image (lzf:px (car s)) (lzf:py (cadr s))
                    (lzf:px (caddr s)) (lzf:py (cadddr s)) col))
  (setq a 6 b 3)
  (cond
    ((= y1 y2)                          ; horizontal: heads point in
     (if (lzf:iny y1)
         (progn
           (setq p (list (lzf:px (min x1 x2)) (lzf:py y1))
                 q (list (lzf:px (max x1 x2)) (lzf:py y1)))
           (vector_image (car p) (cadr p) (+ (car p) a) (- (cadr p) b) col)
           (vector_image (car p) (cadr p) (+ (car p) a) (+ (cadr p) b) col)
           (vector_image (car q) (cadr q) (- (car q) a) (- (cadr q) b) col)
           (vector_image (car q) (cadr q) (- (car q) a) (+ (cadr q) b) col))))
    (t                                  ; vertical
     (if (lzf:iny (min y1 y2))
         (progn
           (setq p (list (lzf:px x1) (lzf:py (min y1 y2))))
           (vector_image (car p) (cadr p) (- (car p) b) (+ (cadr p) a) col)
           (vector_image (car p) (cadr p) (+ (car p) b) (+ (cadr p) a) col)))
     (if (lzf:iny (max y1 y2))
         (progn
           (setq q (list (lzf:px x1) (lzf:py (max y1 y2))))
           (vector_image (car q) (cadr q) (- (car q) b) (- (cadr q) a) col)
           (vector_image (car q) (cadr q) (+ (car q) b) (- (cadr q) a) col))))))

;; Where one dimension's text belongs, and what it says: the LETTER
;; until a value is typed, then the value in the letter's place.  A
;; value too wide for its own span is shrunk to fit rather than allowed
;; to run into its neighbours -- H, G, F and E sit shoulder to shoulder
;; along the middle of the chart and every one of them can carry a
;; five-character feet-and-inches number.
(defun lzf:label (d / letter key x1 y1 x2 y2 side txt sc w h lx ly span mx my)
  (setq letter (car d) key (cadr d)
        x1 (lzf:px (nth 2 d)) y1 (lzf:py (nth 3 d))
        x2 (lzf:px (nth 4 d)) y2 (lzf:py (nth 5 d))
        side (nth 6 d)
        txt (lzf:get key)
        mx (/ (+ x1 x2) 2) my (/ (+ y1 y2) 2))
  (if (= txt "")
      (setq txt letter sc (lzf:basesc))
      (setq sc (/ (* (lzf:basesc) 90) 100)))
  (setq w (lzf:textw txt sc))
  (if (and (= side "h") (> w 0))
      (progn
        (setq span (abs (- x2 x1)))
        (if (> w span)
            (progn
              (setq sc (/ (* sc span) w))
              (if (< sc (/ (* (lzf:basesc) 55) 100))
                  (setq sc (/ (* (lzf:basesc) 55) 100)))
              (setq w (lzf:textw txt sc))))))
  (setq h (lzf:texth sc))
  (if (= side "h")
      (setq lx (- mx (/ w 2)) ly (- y1 h 4))
      ;; a vertical dimension labels at the TOP of its span: the middle
      ;; row already carries the H/G/F/E chain across the pool.  It is
      ;; centred on its own line, EXCEPT when that would run off the
      ;; left edge -- an overall like A sits hard against the boundary
      ;; with no room on its outside, so its label goes on the inside
      ;; rather than being clipped down to a stub
      (progn
        (setq ly (+ (min y1 y2) 5))
        (setq lx (if (< (- mx (/ w 2)) 2) (+ mx 4) (- mx (/ w 2))))))
  ;; and nothing is allowed off the edge of the picture
  (if (< lx 2) (setq lx 2))
  (if (> (+ lx w) (- lzf:*dx* 2)) (setq lx (- lzf:*dx* w 2)))
  (if (< ly 2) (setq ly 2))
  (if (> (+ ly h) (- lzf:*dy* 2)) (setq ly (- lzf:*dy* h 2)))
  ;; blank the strip behind it so the dimension line does not run
  ;; through the characters
  (fill_image (- lx 3) (- ly 2) (+ w 6) (+ h 4) lzf:*col-back*)
  (if (= key lzf:*focus*)
      (lzf:plinepx (list (- lx 3) (- ly 2) (+ lx w 3) (- ly 2)
                         (+ lx w 3) (+ ly h 2) (- lx 3) (+ ly h 2)
                         (- lx 3) (- ly 2))
                   lzf:*col-hi*))
  (lzf:text txt lx ly sc
            (if (= (lzf:get key) "") lzf:*col-line* lzf:*col-val*)))

;; The band a dimension's TEXT belongs to: a horizontal dim sits on
;; its own line, a vertical one labels at the top of its span.
(defun lzf:anchor (d)
  (if (= (nth 6 d) "h")
      (nth 3 d)
      (min (nth 3 d) (nth 5 d))))

(defun lzf:inband (v) (and (<= lzf:*y0* v) (< v lzf:*y1*)))

;; The whole picture: every band painted once, each between its own
;; start_image and end_image.  Wedge dims draw nothing at all -- their
;; row of the drawing IS a row of real boxes now -- while every other
;; dim draws its clipped arrow in every band it crosses and its text
;; in the band its anchor falls in.
(defun lzf:redraw ( / c wk bands b i key poly d)
  (setq c lzf:*chart*
        wk (lzf:wedge-keys c)
        bands (lzf:bands c)
        i 0)
  (foreach b bands
    (setq key (strcat "chart" (itoa i))
          lzf:*y0* (car b)
          lzf:*y1* (cdr b)
          lzf:*dx* (dimx_tile key)
          lzf:*dy* (dimy_tile key))
    (start_image key)
    (fill_image 0 0 lzf:*dx* lzf:*dy* lzf:*col-back*)
    (foreach poly (lzf:outline c)
      (lzf:pline (lzf:flatten poly) lzf:*col-line*))
    (foreach d (lzf:dims c)
      (if (not (member (cadr d) wk))
          (lzf:arrow (nth 2 d) (nth 3 d) (nth 4 d) (nth 5 d)
                     lzf:*col-dim*)))
    (foreach d (lzf:dims c)
      (if (and (not (member (cadr d) wk))
               (lzf:inband (lzf:anchor d)))
          (lzf:label d)))
    (end_image)
    (setq i (1+ i)))
  (setq lzf:*y0* 0
        lzf:*y1* 1000)
  (princ))

;;; -------------------- why the picture is not clickable ----------------
;;;
;;;  It was, once: an image_button reports the point it was picked at,
;;;  so a click near a dimension could move the caret to that box.  It
;;;  had to go.  An image_button is repainted when the mouse enters it
;;;  and again when it leaves, and a DCL image tile is NOT retained by
;;;  AutoCAD -- a repaint clears the tile to its own colour attribute
;;;  and everything the application drew into it is gone.  There is no
;;;  expose callback to redraw from, so the chart vanished the first
;;;  time the cursor crossed it.
;;;
;;;  A plain image tile is passive: no highlight, no repaint, nothing
;;;  to vanish.  The cost is that the picture is read rather than
;;;  clicked, and the letter at the front of each box's label is what
;;;  ties the two together instead.
;;;
;;;  The same retention rule is why lzf:redraw runs after the
;;;  bottom-type list and the in-square toggle as well as after every
;;;  edit box: a list unrolling over the chart damages it the same way,
;;;  and nothing else would repair it.

;;; -------------------- the dialog --------------------------------------
;;  Two columns: the chart on the left as a passive image, the boxes on
;;  the right in the chart's own order, each labelled with its letter so
;;  the list and the picture read as one thing.

(setq lzf:*btypes* '("Normal" "Sport" "Wedge" "SLope" "MOdflat" "SHallow"))

(defun lzf:tabstrip (cur / out c n)
  ;; The tab strip: one button per chart, the current one disabled so
  ;; it reads as the page you are on.  DCL has no tab tile and no way
  ;; to hide or restyle one, so "which page am I on" is carried by that
  ;; greyed button and by the dialog's own title bar.
  ;; the KEY, not the title: six full chart titles make a row 117
  ;; characters wide, twice the chart it sits above, and a dialog wider
  ;; than the screen has nowhere to go -- DCL does not scroll.
  ;;
  ;; The keys alone were not enough either.  Eight of them run about 94
  ;; cells against a budget of 90, which is a dialog that does not open
  ;; -- so they WRAP, greedily, the way the panel's pinned row does.
  ;; Adding a ninth chart costs a row rather than the whole form.
  (foreach c (lzf:tabrows)
    (setq out (cons "  : row {" out))
    (foreach n c
      (setq out (cons (strcat "    : button { key = \"tab_" n
                              "\"; label = \"" n "\"; }")
                      out)))
    (setq out (cons "  }" out)))
  (reverse out))

;; Chart keys packed into rows no wider than the budget.
(setq lzf:*tabbudget* 84)

(defun lzf:tabrows ( / out row w c cw)
  (setq row nil w 0)
  (foreach c lzf:*charts*
    (setq cw (+ (strlen (car c)) 6))
    (if (and row (> (+ w cw) lzf:*tabbudget*))
      (setq out (cons (reverse row) out) row nil w 0))
    (setq row (cons (car c) row) w (+ w cw)))
  (if row (setq out (cons (reverse row) out)))
  (reverse out))

(setq lzf:*chart-w* 52)         ; the chart column, in character cells
(setq lzf:*chart-h* 19)         ; its total height, spread over the bands

;; character cells across for a per-mille x
(defun lzf:cellx (v) (/ (* v lzf:*chart-w*) 1000.0))

;;; -------------------- packing the column boxes ------------------------
;;;  A DCL DIALOG TALLER THAN THE SCREEN DOES NOT OPEN, and nothing
;;;  here can measure a screen: DCL reports a tile's size only while
;;;  the dialog is already up, which is too late to lay it out.  So the
;;;  column-only boxes are packed TWO TO A ROW wherever the pair still
;;;  fits across.  Nine of them stacked -- which is what a Roman sheet
;;;  with the Sport chain on it would be -- is nine rows for nine
;;;  numbers; five rows carries the same nine.
;;;
;;;  A row wider than the screen does not open either, though, and both
;;;  labels of a pair sit on one line.  So the pair is only made when
;;;  the two labels and their boxes fit the budget below; a field whose
;;;  label is a sentence keeps a row of its own, at its full width.
;;;  That is why the pairing does not always fall on the group
;;;  boundaries a reader might expect -- it follows the width, and
;;;  every box is labelled for itself either way.

(setq lzf:*rowbudget* 92)       ; cells a packed row may occupy

;; One column-only box, at the given width and indent.
(defun lzf:extbox (d w ind)
  (strcat ind ": edit_box { key = \"" (car d) "\"; label = \"" (cadr d)
          "\"; edit_width = " (itoa w) "; }"))

;; (key label) fields as DCL lines, two to a row where they fit.
(defun lzf:packrows (items ind / out a b)
  (while items
    (setq a (car items) b (cadr items))
    (if (and b (<= (+ (strlen (cadr a)) (strlen (cadr b)) 20) lzf:*rowbudget*))
      (setq out (append out
                        (list (strcat ind ": row {")
                              (lzf:extbox a 6 (strcat ind "  "))
                              (lzf:extbox b 6 (strcat ind "  "))
                              (strcat ind "}")))
            items (cddr items))
      (setq out (append out (list (lzf:extbox a 9 ind)))
            items (cdr items))))
  out)

;; The Sport chain is packed on its own so it reads as the chain it is
;; rather than being broken across a row boundary by whatever the
;; depths happened to leave over.  It is a group in the greying rules
;; too -- lzf:dead names it from here.
(setq lzf:*sportchain* '("e2" "f2" "f1" "e1"))

(defun lzf:sportof (items / d out)
  (foreach d items
    (if (member (car d) lzf:*sportchain*) (setq out (cons d out))))
  (reverse out))

(defun lzf:notsport (items / d out)
  (foreach d items
    (if (not (member (car d) lzf:*sportchain*)) (setq out (cons d out))))
  (reverse out))

;; A keyword dropdown as a DCL line.
(defun lzf:pickline (d ind)
  (strcat ind ": popup_list { key = \"" (car d) "\"; label = \"" (cadr d)
          "\"; edit_width = 12; }"))

;; A second line under the form, for what only this page has to
;; explain.  The Grecians earn one: two of their three cross-dim modes
;; ask for far more diagonals than a sheet has boxes, so the dropdown
;; answers the gate and the tape numbers are typed at the command line
;; -- which is worth saying on the page rather than in a README.
(setq lzf:*grechint*
  (strcat "Cross dims: Simple takes the two boxes here; Center and "
          "Complex answer the gate and ask their 14 or 18 diagonals at "
          "the command line."))

(setq lzf:*hints*
  (list (cons "Grecian" lzf:*grechint*)
        (cons "GRSquare" lzf:*grechint*)
        (cons "OCtagon" lzf:*grechint*)))

(defun lzf:hint (c) (cdr (assoc (car c) lzf:*hints*)))

;; One wedge row: the cut's dims as real edit boxes, pushed to their
;; letters' positions by spacers.  Positions are in character cells and
;; a box has its own minimum size, so this is honest about being
;; approximate: a box lands within a cell or so of its letter, and two
;; that would collide get pushed apart rather than overlapped.
(defun lzf:wedgerow (c y / out d lbl w want pos)
  (setq out (list "      : row {")
        pos 0.0)
  ;; LEFT TO RIGHT, whatever order the chart lists them in: the row is
  ;; built by walking a cursor across it, and a dim listed before its
  ;; left-hand neighbour would shove that neighbour to the wrong side
  ;; of the chart
  (foreach d (vl-sort (lzf:cutdims c y)
                      '(lambda (p q)
                         (< (+ (nth 2 p) (nth 4 p))
                            (+ (nth 2 q) (nth 4 q)))))
    (setq lbl (car d)
          w (+ (strlen lbl) 10.0)       ; label + borders + 6-char box
          want (- (lzf:cellx (/ (+ (nth 2 d) (nth 4 d)) 2)) (/ w 2)))
    (if (< want (+ pos 0.5)) (setq want (+ pos 0.5)))
    (setq out (cons (strcat "        : spacer { width = "
                            (rtos (- want pos) 2 1) "; }")
                    out))
    (setq out (cons (strcat "        : edit_box { key = \"" (cadr d)
                            "\"; label = \"" lbl
                            "\"; edit_width = 6; fixed_width = true; }")
                    out))
    (setq pos (+ want w)))
  (setq out (cons "        spacer;" out))
  (reverse (cons "      }" out)))

;; The chart as a stack: an image tile per band, a wedge row at every
;; cut, heights split in proportion to the bands they show.
(defun lzf:bandtiles (c / out bands b i h)
  (setq i 0
        bands (lzf:bands c))
  (foreach b bands
    (setq h (/ (* (- (cdr b) (car b)) lzf:*chart-h*) 1000.0))
    (if (< h 0.8) (setq h 0.8))
    (setq out (append out
                      (list (strcat "      : image { key = \"chart" (itoa i)
                                    "\"; width = " (itoa lzf:*chart-w*)
                                    "; height = " (rtos h 2 1)
                                    "; fixed_width = true; "
                                    "fixed_height = true; color = -15; }"))))
    (if (< (1+ i) (length bands))
        (setq out (append out (lzf:wedgerow c (cdr b)))))
    (setq i (1+ i)))
  out)

;; One dialog per chart.  They all live in one generated file so the
;; page loop can load_dialog once and switch pages without touching
;; the disk again.
(defun lzf:dcl-one (c / out d wk l)
  ;; out is consed newest-first and reversed once at the end, so this
  ;; seed list reads BACKWARDS: the label second here puts it second in
  ;; the file, after the line that opens the dialog.  The other way
  ;; round emits an attribute before its own dialog, which is not DCL.
  (setq out (list (strcat "  label = \"LazForm - " (caddr c) "\";")
                  (strcat (lzf:dlgname (car c)) " : dialog {")))
  (setq out (append (reverse (lzf:tabstrip (car c))) out))
  (setq out (cons "  : row {" out))
  ;; PASSIVE image tiles, deliberately -- see "why the picture is not
  ;; clickable" above -- stacked with the wedge rows between them.
  (setq wk (lzf:wedge-keys c))
  (setq out (cons "    : column {" out))
  (foreach l (lzf:bandtiles c)
    (setq out (cons l out)))
  (setq out (cons "    }" out))
  (setq out (cons "    : column {" out))
  (setq out (cons "      : boxed_column {" out))
  (setq out (cons "        label = \"Dimensions\";" out))
  ;; Each dimension is a row: its LETTER as a button, then the box.
  ;; Clicking the letter puts the caret in that box and rings the
  ;; dimension on the chart -- which is as close to clicking the
  ;; drawing itself as DCL allows, and the button sits against the box
  ;; it fills rather than off in a separate list.
  ;; only the dims that could NOT be wedged into the drawing -- the
  ;; vertical ones -- keep a row here; the horizontal chains live on
  ;; the chart itself now
  (foreach d (lzf:dims c)
    (if (not (member (cadr d) wk))
        (progn
          (setq out (cons "        : row {" out))
          (setq out (cons (strcat "          : button { key = \"pick_"
                                  (cadr d) "\"; label = \"" (car d)
                                  "\"; fixed_width = true; }")
                          out))
          (setq out (cons (strcat "          : edit_box { key = \"" (cadr d)
                                  "\"; edit_width = 9; label = \"" (nth 7 d)
                                  "\"; }")
                          out))
          (setq out (cons "        }" out)))))
  (setq out (cons "      }" out))
  (if (lzf:extra c)
    (progn
      (setq out (cons "      : boxed_column {" out))
      (setq out (cons "        label = \"Not on this view\";" out))
      (foreach l (append
                   (lzf:packrows (lzf:notsport (lzf:extra c)) "        ")
                   (lzf:packrows (lzf:sportof (lzf:extra c)) "        "))
        (setq out (cons l out)))
      (setq out (cons "      }" out))))
  ;; the cross dims, with the question that decides how many of them
  ;; POOL will ask for at the head of the box
  (if (lzf:cross c)
    (progn
      (setq out (cons "      : boxed_column {" out))
      (setq out (cons "        label = \"Cross dims (out-of-square only)\";" out))
      (foreach d (lzf:picks c)
        (if (= (caddr d) "cross")
            (setq out (cons (lzf:pickline d "        ") out))))
      (foreach l (lzf:packrows (lzf:cross c) "        ")
        (setq out (cons l out)))
      (setq out (cons "      }" out))))
  (if (lzf:corners c)
    (progn
      (setq out (cons "      : boxed_column {" out))
      (setq out (cons "        label = \"Corners\";" out))
      (foreach d (lzf:corners c)
        (setq out (cons "        : row {" out))
        (setq out (cons (strcat "          : popup_list { key = \"" (car d)
                                "\"; label = \"" (cadr d)
                                "\"; edit_width = 9; }")
                        out))
        (setq out (cons (strcat "          : edit_box { key = \"" (car d)
                                "-sz\"; label = \"size\"; "
                                "edit_width = 6; fixed_width = true; }")
                        out))
        (setq out (cons "        }" out)))
      (setq out (cons "      }" out))))
  (setq out (cons "      : boxed_column {" out))
  (setq out (cons "        label = \"The rest of the run\";" out))
  (setq out (cons (strcat "        : toggle { key = \"insq\"; "
                          "label = \"Pool is in-square (no cross dims)\"; }")
                  out))
  (setq out (cons (strcat "        : popup_list { key = \"btype\"; "
                          "label = \"Bottom type\"; }")
                  out))
  ;; the keyword questions that are not about cross dims live here,
  ;; with the toggle and the bottom type
  (foreach d (lzf:picks c)
    (if (= (caddr d) "run")
        (setq out (cons (lzf:pickline d "        ") out))))
  (setq out (cons "      }" out))
  (setq out (cons "    }" out))
  (setq out (cons "  }" out))
  (setq out (cons "  spacer;" out))
  (setq out (cons (strcat "  : text { key = \"hint\"; width = 62; "
                          "label = \"The chain boxes sit on the drawing itself.  "
                          "Type NA where nothing was measured; leave a box "
                          "empty and POOL will ask.\"; }")
                  out))
  (if (lzf:hint c)
    (setq out (cons (strcat "  : text { key = \"hint2\"; width = 62; label = \""
                            (lzf:hint c) "\"; }")
                    out)))
  (setq out (cons "  : row {" out))
  (setq out (cons (strcat "    : button { key = \"accept\"; label = \"Insert\"; "
                          "is_default = true; fixed_width = true; }")
                  out))
  (setq out (cons (strcat "    : button { key = \"cancel\"; label = \"Cancel\"; "
                          "is_cancel = true; fixed_width = true; }")
                  out))
  (setq out (cons "  }" out))
  (reverse (cons "}" out)))

;; The DCL name of a chart's page.
(defun lzf:dlgname (key) (strcat "lazform_" (strcase key t)))

;; Every page, one after another, in one file.
(defun lzf:dcl-lines ( / out c)
  (foreach c lzf:*charts*
    (setq out (append out (lzf:dcl-one c) (list ""))))
  (setq out (append out (lzf:dcl-ascii) (list "")))
  (append out (lzf:dcl-txt (lzf:chart "Rectangle")) (list "")))

;;; -------------------- the character-drawing probe ----------------------
;;;  Could the chart be drawn in CHARACTERS instead of vectors, with the
;;;  edit boxes sitting in the drawing rather than beside it?
;;;
;;;  There is a real prize in it.  DCL does not RETAIN an image tile:
;;;  anything that repaints the dialog clears the picture, and there is
;;;  no expose callback to draw it again -- which is why the chart has
;;;  vanished on people twice.  A text tile is retained by the dialog
;;;  manager like any other control, so a chart drawn in characters
;;;  could not vanish at all.
;;;
;;;  It turns on one thing this file cannot answer for itself: whether
;;;  the DCL dialog font is FIXED-PITCH.  Character art needs every
;;;  glyph the same width; a proportional font makes "WWWW" far wider
;;;  than "iiii" and the drawing shears apart line by line.  DCL gives
;;;  no way to choose a font, and widths are quoted in "character
;;;  cells" that are an AVERAGE, not a guarantee.
;;;
;;;  ANSWERED, on AutoCAD 2018+: the font is PROPORTIONAL.  Twelve W's
;;;  came out about three times the width of twelve i's, the bars were
;;;  nowhere near a column, and the pool drawn in characters sheared
;;;  apart line by line.  Leading spaces do survive -- the staircase in
;;;  section 2 was clean -- but that does not help on its own.
;;;
;;;  Section 4 is the half that works, and it is what the wedge rows
;;;  already do: a row of text tiles with explicit widths and an edit
;;;  box between them lines up in a proportional font, because the
;;;  alignment comes from tile widths and not from glyphs.  So the
;;;  boxes-in-the-line half was already here and the ASCII half never
;;;  will be.  Kept because the answer belongs to the AutoCAD build,
;;;  not to this code, and is worth re-asking elsewhere.
;;;
;;;  So this asks AutoCAD instead of guessing.  Run LAZASCII and look:
;;;  section 1 says whether the font is fixed-pitch, section 2 shows
;;;  what a pool would look like if it is, and section 3 shows the
;;;  fallback that works either way -- a row of tiles, where alignment
;;;  comes from tile widths rather than from glyphs.
;; The pool exactly as it is drawn on paper, in characters.  If a list
;; box turns out to be fixed-pitch this is what the form could show --
;; retained, never wiped by a repaint, and the real shape rather than a
;; rectangle standing in for one.
(setq lzf:*poolart* (list
    "    <--------------------------------- B --------------------------------->"
    "    +---------------------------------------------------------------------+"
    " ^  |\\                  ^                        ______/|                 |"
    " |  | \\                 M                 ______/       |                 |"
    " |  |  \\                |          ______/              |                 |"
    " |  |   \\               v   ______/                     |                 |"
    " |  |    \\+-----------+_____                            |                 |"
    " |  |     |           |  ^                              |                 |"
    " |  |     |           |  L                              |                 |"
    " A  |<-H->|<--- G --->|<-------------- F -------------->|<------ E ------>|"
    " |  |     |           |  |                              |                 |"
    " |  |     |           |  v                              |                 |"
    " |  |    /+-----------+_____                            |                 |"
    " |  |   /               ^   \\______                     |                 |"
    " |  |  /                |          \\______              |                 |"
    " |  | /                 K                 \\______       |                 |"
    " v  |/                  v                        \\______|                 |"
    "    +---------------------------------------------------------------------+"
  ))

(defun lzf:dcl-ascii ( / out)
  (setq out (list
    "lazform_ascii : dialog {"
    "  label = \"LAZFORM  -  can this dialog draw in characters?\";"
    "  : boxed_column {"
    "    label = \"1.  Is the dialog font fixed-pitch?\";"
    "    : text { label = \"Twelve characters sit between the bars on every line.\"; }"
    "    : text { label = \"|iiiiiiiiiiii|  thin letters\"; }"
    "    : text { label = \"|WWWWWWWWWWWW|  wide letters\"; }"
    "    : text { label = \"|000000000000|  digits\"; }"
    "    : text { label = \"|------------|  dashes\"; }"
    "    : text { label = \"|            |  spaces\"; }"
    "    : text { label = \"FIXED-PITCH if the right-hand bars form one straight column.\"; }"
    "  }"
    "  : boxed_column {"
    "    label = \"2.  Do leading spaces survive?\";"
    "    : text { label = \"|column zero\"; }"
    "    : text { label = \"    |four spaces in\"; }"
    "    : text { label = \"        |eight spaces in\"; }"
    "    : text { label = \"A staircase means indenting works; three bars in one\"; }"
    "    : text { label = \"column means DCL trimmed the spaces and art is impossible.\"; }"
    "  }"
    "  : boxed_column {"
    "    label = \"3.  The pool, drawn in characters\";"
    "    : text { label = \"    +--------------------------+\"; }"
    "    : text { label = \"    |                          |\"; }"
    "    : text { label = \"    |      +------------+      |\"; }"
    "    : text { label = \"    |      |            |      |\"; }"
    "    : text { label = \"    |      +------------+      |\"; }"
    "    : text { label = \"    |                          |\"; }"
    "    : text { label = \"    +--------------------------+\"; }"
    "  }"
    "  : boxed_column {"
    "    label = \"4.  A box IN the dimension line -- works either way\";"
    "    : text { label = \"Alignment here comes from tile widths, not from glyphs,\"; }"
    "    : text { label = \"so this reads straight even in a proportional font.\"; }"
    "    : row {"
    "      : text { label = \"B\"; width = 3; }"
    "      : text { label = \"|<---\"; width = 7; }"
    "      : edit_box { key = \"probe_b\"; edit_width = 8; }"
    "      : text { label = \"--->|\"; width = 7; }"
    "    }"
    "    : row {"
    "      : text { label = \"A\"; width = 3; }"
    "      : text { label = \"|<---\"; width = 7; }"
    "      : edit_box { key = \"probe_a\"; edit_width = 8; }"
    "      : text { label = \"--->|\"; width = 7; }"
    "    }"
    "  }"
    "  : boxed_column {"
    "    label = \"5.  Is a LIST BOX fixed-pitch?\";"
    (strcat "    : text { label = \"A text tile is not.  A list box is a "
            "different control -- if ITS bars line up,\"; }")
    (strcat "    : text { label = \"the pool below can be drawn in "
            "characters after all.\"; }")
    "    : list_box { key = \"ruler\"; width = 32; height = 5; }"
    "    : list_box { key = \"pool\"; width = 78; height = 18; }"
    "  }"
    "  spacer;"
    "  : text { label = \"Tell the session which sections lined up.\"; alignment = centered; }"
    (strcat "  : button { label = \"Close\"; key = \"cancel\"; "
            "is_default = true; is_cancel = true; "
            "fixed_width = true; alignment = centered; }")
    "}"))
  out)

;; The probe, on its own loaded handle.  It draws nothing and answers
;; nothing -- it exists to be looked at.
(defun c:LAZASCII ( / f dcl l)
  (cond
    ((not (setq f (lzf:write-dcl)))
     (princ "\nLAZASCII error: could not write the dialog file."))
    ((< (setq dcl (load_dialog f)) 0)
     (princ "\nLAZASCII error: could not load the dialog file."))
    (t
     (if (new_dialog "lazform_ascii" dcl)
       (progn
         ;; the same twelve characters the text tiles got, and then the
         ;; pool -- populated at run time, which is how a list box is fed
         (start_list "ruler")
         (foreach l '("|iiiiiiiiiiii|" "|WWWWWWWWWWWW|" "|000000000000|"
                      "|------------|" "|            |")
           (add_list l))
         (end_list)
         (start_list "pool")
         (foreach l lzf:*poolart* (add_list l))
         (end_list)
         (action_tile "cancel" "(done_dialog 0)")
         (start_dialog)))
     (unload_dialog dcl)
     (vl-file-delete f)
     (princ (strcat "\nLAZASCII: if sections 1-3 lined up, the chart can be"
                    " drawn in characters -- and a text tile, unlike an"
                    " image tile, is never wiped by a repaint."))))
  (princ))

;;; -------------------- the text view -----------------------------------
;;;  LAZTXT: the pool drawn out of TILES rather than out of vectors,
;;;  with the boxes inside it.
;;;
;;;  The LAZASCII probe killed character art -- the dialog font is
;;;  proportional, so a pool drawn in "+---+" shears apart line by line.
;;;  But it also showed the half that works: a row of tiles with
;;;  declared widths lines up perfectly, because the alignment comes
;;;  from the tiles and not from the glyphs.
;;;
;;;  DCL has something better than dashes for the outline.  A
;;;  boxed_row or boxed_column draws a REAL etched border -- drawn by
;;;  the widget, so it is straight by construction and cannot shear.
;;;  Nest one inside another and you have a pool with a hopper in it;
;;;  put the edit boxes inside those clusters and the fields are IN the
;;;  drawing rather than beside it.
;;;
;;;  What it buys over the vector chart: every tile here is RETAINED.
;;;  DCL does not retain an image tile -- a repaint clears it and there
;;;  is no expose callback -- which is the standing hazard behind the
;;;  chart having vanished on people.  Nothing in this view can vanish.
;;;
;;;  What it costs: the outline is a rectangle whatever the pool is.  A
;;;  boxed cluster cannot be round, cut-cornered or L-shaped, so this
;;;  is a schematic of where the numbers sit, not a picture of the
;;;  pool.  Which is why it is a SECOND view and not a replacement.

;; The v dim that spans the most: the overall, which belongs outside the
;; hopper rather than in it.
(defun lzf:txt-tallest (c / d best bs sp)
  (foreach d (lzf:dims c)
    (if (= (nth 6 d) "v")
      (progn
        (setq sp (abs (- (nth 5 d) (nth 3 d))))
        (if (or (not best) (> sp bs)) (setq best d bs sp)))))
  best)

(defun lzf:txt-box (d w)
  (strcat "        : edit_box { key = \"" (cadr d) "\"; label = \""
          (car d) "\"; edit_width = " (itoa w) "; }"))

;; One row per cut, in drawing order: the across-chain the way it reads
;; on the sheet.
(defun lzf:txt-rows (c / out y ds d)
  (foreach y (lzf:cuts c)
    (setq ds (lzf:cutdims c y))
    (if ds
      (progn
        (setq out (cons "      : row {" out))
        (foreach d ds (setq out (cons (lzf:txt-box d 6) out)))
        (setq out (cons "      }" out)))))
  (reverse out))

;; Every h dim the cuts did not claim, plus the column-only fields.
(defun lzf:txt-rest (c / out d wk)
  (setq wk (lzf:wedge-keys c))
  (foreach d (lzf:dims c)
    (if (and (= (nth 6 d) "h") (not (member (cadr d) wk)))
      (setq out (cons (lzf:txt-box d 8) out))))
  (reverse out))

;; The first cut's row on its own -- the overall length, above the pool
;; the way the sheet has it.
(defun lzf:txt-firstrow (c / out ds d)
  (setq ds (lzf:cutdims c (car (lzf:cuts c))))
  (if ds
    (progn
      (setq out (list "    : row {"))
      (foreach d ds (setq out (cons (lzf:txt-box d 6) out)))
      (reverse (cons "    }" out)))))

;; Every cut row after the first.
(defun lzf:txt-restrows (c / out y ds d first)
  (setq first t)
  (foreach y (lzf:cuts c)
    (cond
      (first (setq first nil))
      (t
       (setq ds (lzf:cutdims c y))
       (if ds
         (progn
           (setq out (cons "      : row {" out))
           (foreach d ds (setq out (cons (lzf:txt-box d 6) out)))
           (setq out (cons "      }" out)))))))
  (reverse out))

(defun lzf:dcl-txt (c / out tall d rows)
  (setq tall (lzf:txt-tallest c))
  (setq out (list
    "lazform_txt : dialog {"
    (strcat "  label = \"LAZFORM text view  -  " (nth 2 c) "\";")
    (strcat "  : text { label = \"The boxes sit IN the drawing.\"; }")
    (strcat "  : text { label = \"Nothing here is an image tile, so "
            "nothing here can be wiped.\"; }")
    (strcat "  : boxed_column {")
    (strcat "    label = \"" (nth 2 c) "\";")))
  ;; the first across-row -- the overall length -- goes ABOVE the body,
  ;; where the sheet puts it
  (setq rows (lzf:txt-rows c))
  (if rows
    (progn
      (setq out (append out (lzf:txt-firstrow c)))
      (setq rows (lzf:txt-restrows c))))
  ;; the overall width, outside the hopper, then the pool body
  (setq out (append out (list "    : boxed_row {" "      label = \"\";")))
  (if tall
    (setq out (append out (list "      : boxed_column {"
                                "        label = \"Overall\";"
                                (lzf:txt-box tall 8)
                                "      }"))))
  (setq out (append out (list "      : boxed_column {"
                              "        label = \"Hopper\";")))
  (foreach d (lzf:dims c)
    (if (and (= (nth 6 d) "v") (not (equal d tall)))
      (setq out (append out (list (lzf:txt-box d 6))))))
  (setq out (append out (list "      }" "    }")))
  ;; the remaining across-chains, one row per cut, in drawing order
  (if rows
    (setq out (append out (list "    : boxed_column {"
                                "      label = \"Across\";")
                      rows
                      (list "    }"))))
  ;; anything the cuts did not claim, and the column-only fields
  (setq out (append out (list "    : boxed_column {"
                              "      label = \"And the rest\";")))
  (setq out (append out (lzf:txt-rest c)))
  (foreach d (append (lzf:extra c) (lzf:cross c))
    (setq out (append out (list (strcat "        : edit_box { key = \""
                                        (car d) "\"; label = \"" (cadr d)
                                        "\"; edit_width = 8; }")))))
  (setq out (append out (list "    }" "  }")))
  (append out
    (list "  spacer;"
          "  : row {"
          (strcat "    : button { key = \"accept\"; label = \"Insert\"; "
                  "is_default = true; fixed_width = true; }")
          (strcat "    : button { key = \"cancel\"; label = \"Cancel\"; "
                  "is_cancel = true; fixed_width = true; }")
          "  }"
          "}")))

;; Show it, collect it, and hand POOL the same alist LAZFORM would.
(defun lzf:txt-show (c / f dcl rc k out)
  (setq lzf:*vals* nil lzf:*cvals* nil lzf:*pvals* nil lzf:*chart* c)
  (cond
    ((not (setq f (lzf:write-dcl)))
     (princ "\nLAZTXT error: could not write the dialog file."))
    ((< (setq dcl (load_dialog f)) 0)
     (princ "\nLAZTXT error: could not load the dialog file."))
    (t
     (cond
       ((not (new_dialog "lazform_txt" dcl))
        (princ "\nLAZTXT error: could not open the view."))
       (t
        (foreach k (lzf:keys c)
          (action_tile k (strcat "(lzf:put \"" k "\" $value)")))
        (action_tile "accept" "(done_dialog 1)")
        (action_tile "cancel" "(done_dialog 0)")
        (setq rc (start_dialog))
        (if (= rc 1)
          (setq out (lzf:form (cadr c) lzf:*insq*
                              (nth lzf:*btype* lzf:*btypes*))))))
     (unload_dialog dcl)
     (vl-file-delete f)))
  out)

(defun c:LAZTXT ( / c form)
  (setq c (lzf:chart "Rectangle"))
  (cond
    ((not pool:run-with-answers)
     (princ "\nLAZTXT: POOL is not loaded in this session -- APPLOAD")
     (princ "\n        lisp/pool/POOL.LSP, or LAZPASS.lsp which has both."))
    ((setq form (lzf:txt-show c))
     (princ (strcat "\nLAZTXT: " (itoa (length form))
                    " answers to POOL; it will ask for whatever is left."))
     (pool:run-with-answers form))
    (t (princ "\nLAZTXT: cancelled, nothing drawn.")))
  (princ))

(defun lzf:write-lines (fh / l)
  (foreach l (lzf:dcl-lines) (write-line l fh)))

(defun lzf:write-dcl ( / f fh err)
  (setq f (vl-filename-mktemp "lazform" nil ".dcl"))
  (if (and f (setq fh (open f "w")))
    (progn
      (setq err (vl-catch-all-apply 'lzf:write-lines (list fh)))
      (close fh)
      (cond
        ((vl-catch-all-error-p err) (vl-file-delete f) nil)
        (t f)))))

;;; -------------------- what POOL is handed -----------------------------
;;;  The three states of STANDARDS.md's form contract, decided here:
;;;
;;;    box left empty   the key is not sent at all -> POOL asks
;;;    NA typed in it   (key . nil) is sent        -> POOL takes NA
;;;    a measurement    (key . 84.0) is sent       -> POOL takes it
;;;
;;;  Anything that is neither NA nor a distance AutoCAD can read is
;;;  treated as an empty box: a typo must leave POOL asking rather than
;;;  quietly feeding it a nil that means something else entirely.
;;;  distof reads the architectural spellings, so 25'6" and 25'-6-1/2"
;;;  arrive as the numbers they look like.

(defun lzf:answer (v / n)
  (cond
    ((or (null v) (= v "")) 'SKIP)
    ((= (strcase (lzf:trim v)) "NA") nil)
    ((setq n (distof (lzf:trim v) 4)) n)
    ((setq n (distof (lzf:trim v) 2)) n)
    (t 'SKIP)))

(defun lzf:trim (s / i n)
  (setq i 1 n (strlen s))
  (while (and (<= i n) (= (substr s i 1) " ")) (setq i (1+ i)))
  (while (and (>= n i) (= (substr s n 1) " ")) (setq n (1- n)))
  (if (> i n) "" (substr s i (1+ (- n i)))))

;; The alist POOL reads, built from what was typed.
;;; -------------------- what this page actually asks ---------------------
;;;  A page does not ask for every box on it, and the form used to
;;;  offer them all anyway: type a C against a Normal hopper and POOL
;;;  never asks for it, so the number went nowhere and nothing said so.
;;;  THREE things on the page decide, not one:
;;;
;;;    the bottom type    which of the plan and depth letters that
;;;                       bottom's own routine will ask for;
;;;    the in-square      whether there are cross dims at all, and
;;;    toggle             whether the second overalls are asked;
;;;    the mode dropdown  how many of the cross boxes map to a tape.
;;;
;;;  lzf:dead puts the three together and names the dead keys once.
;;;  lzf:btgrey greys exactly that set and lzf:form drops exactly that
;;;  set -- one function, two callers -- so the page cannot grey a box
;;;  and then send what is in it, or send a box it has greyed.
;;;
;;;  The bottom-type half comes from POOL'S OWN pool:btmspec rather
;;;  than a copy of it here -- (ask-G ask-E has-profile ask-C2 slack)
;;;  -- so the two cannot drift.  LAZFORM already refuses to open
;;;  without POOL loaded, so it is always there to ask.
;;;
;;;  The truth comes from POOL'S OWN pool:btmspec rather than a copy of
;;;  it here -- (ask-G ask-E has-profile ask-C2 slack) -- so the two
;;;  cannot drift.  LAZFORM already refuses to open without POOL loaded,
;;;  so it is always there to ask.
;;;
;;;  SPORT IS THE EXCEPTION, and not a small one.  btmspec's has-profile
;;;  flag reads nil for Sport, which would say "no C or D" -- but that
;;;  flag is only ever consulted inside pool:hopnormal, and a Sport
;;;  never goes near it.  Sport has its own path, which DOES ask C and
;;;  D, and which asks a different plan chain entirely: E2 F2 G F1 E1 M
;;;  L K, not H G F E.  So on a Sport the chart's H, F and E boxes are
;;;  greyed: they are not what POOL will ask for, and a number typed
;;;  into one would be read by nothing.  The other side of that trade
;;;  is in lzf:dead: E2 F2 F1 E1 have boxes on every sheet whose flow
;;;  can reach a Sport, and every bottom that is NOT a Sport greys
;;;  them.
(defun lzf:btskip (bt / sp out)
  (cond
    ((= bt "Sport") (list "h" "f" "e" "c2"))
    ((not pool:btmspec) nil)          ; no POOL: grey nothing, ask everything
    (t
     (setq sp (pool:btmspec bt))
     (if (not (car sp))    (setq out (cons "g" out)))
     (if (not (cadr sp))   (setq out (cons "e" out)))
     (if (not (caddr sp))  (setq out (append (list "c" "d") out)))
     (if (not (cadddr sp)) (setq out (cons "c2" out)))
     out)))

;; THE ONE AUTHORITY.  Every key on this page POOL will not ask about,
;; given the bottom type, the in-square toggle and the mode dropdowns
;; (which are read from their own store, the way the boxes are).  The
;; answer is restricted to keys the page really carries, so a rule may
;; name a key no chart has and the two callers can both trust the list
;; -- mode_tile on a tile that is not there would error.
(defun lzf:dead (c insq btype / out bt n i k have seen)
  ;; the L family: POOL asks no bottom type there at all, so the popup
  ;; is dead and the page is judged against the bottom those flows
  ;; really draw
  (setq bt (if (lzf:btlive c) btype "Normal")
        out (if (lzf:btlive c) nil (list "btype")))
  (setq out (append out (lzf:btskip bt)))
  ;; the Sport chain is asked by a Sport bottom and by nothing else
  (if (/= bt "Sport")
      (setq out (append out lzf:*sportchain*)))
  ;; in square there are no cross dims to measure, no mode to measure
  ;; them from, and no second overall
  (if insq
      (setq out (append out (list "bo" "ri")
                        (mapcar 'car (lzf:cross c))
                        (if (lzf:crossmode c) (list (lzf:crossmode c))))))
  ;; and out of square, only as many cross boxes as the mode maps: the
  ;; rest stand for tapes this mode does not run
  (setq n (lzf:crosslive c) i 0)
  (foreach k (lzf:cross c)
    (if (>= i n) (setq out (cons (car k) out)))
    (setq i (1+ i)))
  ;; keep what this page actually has, once each
  (setq have (lzf:pagekeys c))
  (foreach k out
    (if (and (member k have) (not (member k seen)))
        (setq seen (cons k seen))))
  (reverse seen))

;; Grey every dead key on the page, un-grey the rest.
(defun lzf:btgrey (c / dead k)
  (setq dead (lzf:dead c lzf:*insq* (nth lzf:*btype* lzf:*btypes*)))
  (foreach k (lzf:pagekeys c)
    (mode_tile k (if (member k dead) 1 0))))

(defun lzf:form (shape insq btype / out k v a dead d cp)
  (setq dead (lzf:dead lzf:*chart* insq btype))
  (setq out (list (cons 'shape shape)
                  (cons 'insq (if insq "Insquare" "Outofsquare"))))
  ;; a key this page never asks about does not travel: it would sit in
  ;; the store unread, and a form that quietly carries dead answers is
  ;; harder to reason about than one that does not
  (if (and btype (/= btype "") (not (member "btype" dead)))
      (setq out (cons (cons 'btype btype) out)))
  (foreach k (lzf:keys lzf:*chart*)
    (setq v (lzf:get k)
          a (lzf:answer v))
    (if (and (not (eq a 'SKIP)) (not (member k dead)))
        (setq out (cons (cons (read k) a) out))))
  ;; the mode dropdowns: a keyword answer in its own right, and one
  ;; left on "(ask)" sends nothing, exactly as an empty box does
  (foreach d (lzf:picks lzf:*chart*)
    (setq v (lzf:pickval lzf:*chart* (car d)))
    (if (and (/= v "") (not (member (car d) dead)))
        (setq out (cons (cons (read (car d)) v) out))))
  ;; the corners: a dropdown left on (ask) sends nothing, a sized
  ;; treatment carries its size when one parses, and each row goes to
  ;; whichever POOL questions it answers in this state
  (setq cp (lzf:cornerpairs insq))
  (foreach k cp
    (setq out (cons k out)))
  ;; the corner gate.  On the shapes that put a yes/no in front of the
  ;; corner questions, a row picked here answers that gate too -- the
  ;; treatments would be read by nothing if it were left on No
  (if (and cp (member (car lzf:*chart*) lzf:*crecharts*))
      (setq out (cons (cons 'crec "Yes") out)))
  ;; the gates last, so a chart cannot be talked out of the path its
  ;; own letters live on
  (foreach k (lzf:gates lzf:*chart*)
    (setq out (cons (cons (read (car k)) (cdr k)) out)))
  (reverse out))

;; The (key . value) pairs the corner rows contribute.  A row carries
;; one treatment and one size to every POOL stem it answers in this
;; state: one on a rectangle corner, four when a Grecian's collective
;; row fans out to the corners POOL asks individually.
(defun lzf:cornerpairs (insq / out d stem targets i ty sz u)
  (foreach d (lzf:corners lzf:*chart*)
    (setq stem (car d)
          targets (if insq (caddr d) (cadddr d)))
    (if (and targets (> (setq i (lzf:cget stem)) 0))
        (progn
          (setq ty (nth i lzf:*ctreat*)
                sz (if (lzf:csized i)
                       (lzf:answer (lzf:get (strcat stem "-sz")))))
          (foreach u targets
            (setq out (cons (cons (read (strcat u "-ty")) ty) out))
            (if (numberp sz)
                (setq out (cons (cons (read (strcat u "-sz")) sz) out)))))))
  (reverse out))

;;; -------------------- the run -----------------------------------------
;;  A helper rather than the command body, so its localized *error* is
;;  out of scope by the time POOL is started: POOL installs its own, and
;;  a POOL that fails must report as POOL.

(defun lzf:show (chartkey / *error* f dcl rc c d n go done out)
  (defun *error* (msg)
    (term_dialog)
    (if (and dcl (>= dcl 0)) (unload_dialog dcl))
    (setq dcl nil)
    (if f (vl-file-delete f))
    (setq f nil)
    (if (and msg (not (wcmatch (strcase msg)
                               "*BREAK*,*CANCEL*,*QUIT*,*EXIT*")))
      (princ (strcat "\nLAZFORM error: " msg)))
    (princ))
  (setq lzf:*vals* nil
        lzf:*cvals* nil                 ; corner dropdowns back to (ask)
        lzf:*pvals* nil                 ; and the mode dropdowns with them
        lzf:*insq* nil                  ; the toggle's own starting state
        lzf:*btype* 0                   ; Normal, first in the list
        lzf:*pos* nil                   ; where the user last had it
        go chartkey)
  (cond
    ((not (lzf:chart go))
     (princ (strcat "\nLAZFORM: no chart called " go ".")))
    ((not (setq f (lzf:write-dcl)))
     (princ "\nLAZFORM error: could not write the dialog file."))
    ((< (setq dcl (load_dialog f)) 0)
     (princ "\nLAZFORM error: could not load the dialog file."))
    (t
     ;; The page loop.  DCL has no tab tile, so a tab is a button that
     ;; closes this page and reopens the next -- and because
     ;; done_dialog hands back where the dialog was standing, it
     ;; reopens exactly there instead of wandering off to the middle of
     ;; the screen.  Everything typed lives in lzf:*vals*, keyed, so it
     ;; survives the switch and is still there if you tab back.
     (while (not done)
       (setq lzf:*chart* (lzf:chart go)
             c lzf:*chart*
             lzf:*focus* nil)
       (cond
         ((not (lzf:newdlg (lzf:dlgname go) dcl))
          (princ "\nLAZFORM error: could not open the form.")
          (setq done t))
         (t
          (start_list "btype")
          (foreach d lzf:*btypes* (add_list d))
          (end_list)
          (set_tile "btype" (itoa lzf:*btype*))
          ;; the corner dropdowns: filled, put back to their remembered
          ;; pick, size boxes greyed unless that pick takes a size --
          ;; and each harvests into its own store the moment it changes
          (foreach d (lzf:corners c)
            (start_list (car d))
            (foreach n lzf:*ctreat* (add_list n))
            (end_list)
            (set_tile (car d) (itoa (lzf:cget (car d))))
            (set_tile (strcat (car d) "-sz")
                      (lzf:get (strcat (car d) "-sz")))
            (mode_tile (strcat (car d) "-sz")
                       (if (lzf:csized (lzf:cget (car d))) 0 1))
            (action_tile (car d)
              (strcat "(lzf:cornerpick \"" (car d) "\" $value)"))
            (action_tile (strcat (car d) "-sz")
              (strcat "(lzf:put \"" (car d) "-sz\" $value)")))
          ;; the mode dropdowns -- the cross-dim reference and the L's
          ;; mirror -- filled and put back the same way, and each
          ;; re-decides what is live as it changes
          (foreach d (lzf:picks c)
            (start_list (car d))
            (foreach n (cadddr d) (add_list n))
            (end_list)
            (set_tile (car d) (itoa (lzf:pget (car d))))
            (action_tile (car d)
              (strcat "(lzf:pickpick \"" (car d) "\" $value)")))
          (if lzf:*insq* (set_tile "insq" "1"))
          ;; put back what was typed before this page was opened
          (foreach d (lzf:keys c) (set_tile d (lzf:get d)))
          (foreach d (lzf:keys c)
            (action_tile d
              (strcat "(lzf:put \"" d "\" $value) (setq lzf:*focus* \"" d "\")"
                      " (lzf:redraw)")))
          ;; clicking a dimension's letter: caret into its box, with
          ;; the box's contents selected so the first keystroke
          ;; replaces rather than appends, and the dimension ringed on
          ;; the chart
          ;; wedge dims have no pick button -- their box already sits
          ;; on the drawing where the letter was
          (foreach d (lzf:dims c)
            (if (not (member (cadr d) (lzf:wedge-keys c)))
                (action_tile (strcat "pick_" (cadr d))
                  (strcat "(setq lzf:*focus* \"" (cadr d) "\") (lzf:redraw)"
                          " (mode_tile \"" (cadr d) "\" 2)"
                          " (mode_tile \"" (cadr d) "\" 3)"))))
          ;; the tabs -- each closes this page and names the next
          (foreach d lzf:*charts*
            (action_tile (strcat "tab_" (car d))
              (strcat "(setq lzf:*go* \"" (car d)
                      "\" lzf:*pos* (done_dialog 4))")))
          ;; the chart takes no action -- it is a passive image tile.
          ;; These two capture their value as it changes: get_tile
          ;; answers about a LIVE dialog, and by the time the answers
          ;; are assembled this one is closed and unloaded.
          (action_tile "btype"
            (strcat "(setq lzf:*btype* (atoi $value)) (lzf:redraw)"
                    " (lzf:btgrey lzf:*chart*)"))
          ;; the toggle decides the cross dims and the second overalls,
          ;; so it re-greys the page as well as repainting the chart
          (action_tile "insq"
            (strcat "(setq lzf:*insq* (= $value \"1\")) (lzf:redraw)"
                    " (lzf:btgrey lzf:*chart*)"))
          (action_tile "accept" "(setq lzf:*pos* (done_dialog 1))")
          (action_tile "cancel" "(setq lzf:*pos* (done_dialog 0))")
          (lzf:redraw)
          (lzf:btgrey c)
          (setq rc (start_dialog))
          (cond
            ((= rc 4) (setq go lzf:*go*))     ; a tab: go round again
            (t (setq done t
                     out (if (= rc 1)
                             (lzf:form (cadr c) lzf:*insq*
                                       (nth lzf:*btype* lzf:*btypes*)))))))))))
  (if (and dcl (>= dcl 0)) (unload_dialog dcl))
  (setq dcl nil)
  (if f (vl-file-delete f))
  (setq f nil)
  out)

;; Open a page where the user last had the dialog.  done_dialog reports
;; the position it was closed at and new_dialog takes one back, but only
;; as a 4-argument call -- and a build that answered done_dialog with
;; something other than a point would poison every reopen, so the shape
;; is checked before it is trusted and the plain 2-argument call is the
;; fallback.
(defun lzf:newdlg (name dcl)
  (if (and lzf:*pos* (listp lzf:*pos*) (= (length lzf:*pos*) 2)
           (numberp (car lzf:*pos*)) (numberp (cadr lzf:*pos*)))
      (new_dialog name dcl "" lzf:*pos*)
      (new_dialog name dcl)))

;;; -------------------- commands ----------------------------------------

;; The form, then POOL with what it collected.  COVER closes POOL's
;; pool-bottom gate first: a cover sheet has no floor work on it, so
;; the depth chain behind that gate is neither asked for nor drawn.
;; The flag goes on at the last moment -- after the form comes back --
;; so a cancelled form leaves the session exactly as it found it, and
;; c:POOL clears it again on the way out either way.
(defun lzf:run (cover / form)
  (cond
    ;; the chart fills POOL's answers in, so POOL has to be here to
    ;; receive them -- say so plainly rather than opening a form whose
    ;; Insert button could only fail
    ((not pool:run-with-answers)
     (princ "\nLAZFORM: POOL is not loaded in this session -- APPLOAD")
     (princ "\n         lisp/pool/POOL.LSP, or LAZPASS.lsp which has both."))
    ((setq form (lzf:show (car (car lzf:*charts*))))
     (princ (strcat "\nLAZFORM: " (itoa (length form))
                    " answers to POOL; it will ask for whatever is left."))
     (if cover
       (progn
         (setq pool:*nobottom* t)
         (princ "\n         Cover sheet - no pool bottom will be asked for.")))
     (pool:run-with-answers form))
    (t (princ "\nLAZFORM: cancelled, nothing drawn.")))
  (princ))

(defun c:LAZFORM () (lzf:run nil))

(defun c:LAZFORMCOVER () (lzf:run t))

(defun c:LAZFORMVER ()
  (princ (strcat "\nLAZFORM " *lazform-version* " (LAZFORM.lsp) - "
                 (itoa (length lzf:*charts*)) " chart(s)."))
  (princ))

(princ (strcat "\nLAZFORM " *lazform-version*
               " loaded.  Type LAZFORM to fill a chart in and draw it."))
(princ)


;;; ======================================================================
;;; >>> LAZPANEL.lsp
;;; ======================================================================

;;; ======================================================================
;;; LAZPANEL.lsp  --  clickable button panel that launches the calofin tools
;;; ----------------------------------------------------------------------
;;; For AutoCAD 2018 and later (plain AutoLISP, no external libraries).
;;;
;;; Commands:  LAZPANEL       open the panel
;;;            LAZBUTTON      put the screen-button toolbars up
;;;            LAZICON        report where the button picture came from
;;;            LAZPIN         choose the pinned tools
;;;            LAZPANELVER    print the loaded version
;;;
;;; SHARED BUILD: requires CALOFIN-LIB.lsp (load via CALOFIN-LOADER.lsp).
;;; Generic helpers live there under cal: - see STANDARDS.md.
;;;
;;; Every headline calofin routine as a button, on tabbed pages of two
;;; kinds.  Four JOB pages -- Pool, Cover, Spa, Rest -- hold what you
;;; reach for while doing that job, in columns that follow the work:
;;; lay the shape out, tie the points, build the steps, dimension and
;;; check.  Four CATEGORY pages -- Layout, Points, Dimensions, Checking,
;;; the same four names the VB.NET palette in ui/calofin_net uses --
;;; hold the whole roster filed by what each tool IS.  A tool that
;;; serves two jobs is on both, so there are more buttons than commands.
;;; Clicking a button closes the panel and runs the command exactly as
;;; if its name had been typed -- the panel adds nothing in front of a
;;; tool and nothing behind it.  (The Cover page names the cover twins,
;;; POOLCOVER and friends, which is not the panel meddling: they are
;;; commands of their own and do the same thing typed.)
;;;
;;; ZERO INSTALL.  The dialog is plain DCL, and this file writes its own
;;; .dcl into the system temp folder each time the panel opens, so there
;;; is no second file to ship, no support-path entry to add and no DLL
;;; to NETLOAD.  APPLOAD this one file (or LAZPASS.lsp, which carries
;;; it), type LAZPANEL, click.
;;;
;;; THE SCREEN BUTTON.  Loading this file also puts a one-button
;;; toolbar named "LazPanel" on screen, so the panel can live as a
;;; clickable button you drag anywhere or dock, like any toolbar.  It
;;; is created through the ActiveX menu API when no toolbar of that
;;; name exists yet -- no CUI file to install -- and its icon (an
;;; orange hexagon, point to the north) is generated as two .bmp files under
;;; TEMPPREFIX and re-applied on every load, because SetBitmaps stores
;;; the path rather than the picture.  Clicking it runs LAZPANEL.  If
;;; the toolbar gets closed or lost, LAZBUTTON brings it back.  When
;;; any of this is unavailable (no COM, locked CUI, unwritable temp
;;; folder) the button is quietly skipped and the panel is untouched.
;;;
;;; The icon goes out through an ADODB.Stream in binary mode, not
;;; through write-char: AutoLISP writes text-mode files and has no NUL
;;; in its character model at all -- (chr 0) is the empty string --
;;; while a 24-bit BMP header is full of NULs before a single pixel is
;;; reached.  No arrangement of this format could be written with the
;;; language's own file output.  COM is no new dependency here: the
;;; toolbar the icon goes on is made through the same ActiveX API.
;;;
;;; A button whose command is not loaded in this session is greyed out
;;; rather than left to fail -- the same availability probe the VB
;;; palette uses (read the name, evaluate it: an unbound C: symbol is
;;; nil).  The status line across the top says how many tools the
;;; session has.
;;;
;;; DCL dialogs are modal, so the panel cannot stay open while a tool
;;; runs the way a docked palette can -- but it no longer has to be
;;; reopened by hand: click, the panel closes, the tool runs to its own
;;; end, and the panel COMES BACK on the page and at the screen position
;;; it was at.  Close is the way out, and is the default button.  A
;;; PINNED row on every page carries the handful of tools you actually
;;; run all day, remembered between sessions; Pin... or LAZPIN edits it.
;;;
;;; The *SCAN companions are on the panel;
;;; satellites reachable from their headline tool (TUTORIAL*
;;; walkthroughs, *VER reporters, *RESCUE undo companions, -CFG /
;;; -SETUP partners) stay off on purpose, and so does the DD*
;;; drone-height toolset -- eight specialist photo-EXIF commands that
;;; are not part of the drafting flow the panel serves.
;;; tests/test_lazpanel.py pins the roster to the commands actually
;;; defined under lisp/, so a new tool without a button fails the suite
;;; instead of being quietly missing.
;;; ======================================================================

(vl-load-com)

(setq *lazpanel-version* "v3.4")

;;; -------------------- the roster --------------------------------------
;;  Two tables: lzp:*captions* names every command once, and
;;  lzp:*groups* lays the pages out in columns of those names.  The
;;  rules for what belongs on the panel at all:
;;    - every headline drafting command under lisp/ gets a button;
;;    - satellites do not: TUTORIAL* walkthroughs, *VER reporters,
;;      *RESCUE undo companions, -CFG / -SETUP partners, DCE (alias of
;;      DIMCONTEND) and STOCKLIST (STOCKCOVER's listing companion);
;;    - the DD* drone-height toolset stays off as a whole: eight
;;      specialist photo-EXIF commands, not part of the drafting flow;
;;    - LISPLAB never appears: it is held back from the shared build as
;;      OMITTED (see cal:*held-back* in CALOFIN-LOADER.lsp);
;;    - the deprecated acady matcher (MATCHSTD, ACADY-*) never appears.
;;  tests/test_lazpanel.py enforces all five rules against the tree.

;;  TWO KINDS OF TAB, and a command may sit on several.
;;
;;  The first four pages are JOBS -- what the drafter is actually doing
;;  this hour: a pool, a cover, a spa, and everything those three do not
;;  reach.  They run in the order the work runs: lay the shape out, tie
;;  the points, build the steps, then dimension and check.  A command
;;  that serves two jobs appears on both; AUTODIM and DIMCHECK are on
;;  all three, because every job ends the same way.  The last four are
;;  the CATEGORIES the panel has always had -- the whole roster filed by
;;  what each tool is rather than when you reach for it -- so a tool you
;;  cannot place in a job is still one tab away.
;;
;;  Every command therefore appears at least twice: once on a job page
;;  and once on a category page.  Keys are only required to be unique
;;  within a page, and each page is its own dialog, so this is free --
;;  but lzp:commands has to fold the repeats or the status line would
;;  count the roster twice over.
;;
;;  The job pages are laid out in COLUMNS, which is the other half of
;;  the same idea: a job is not a flat list of two dozen tools, it is
;;  four short lists in the order you reach for them.
;;
;;  "Rest" is not a hand-kept list: it is every command the Pool, Cover
;;  and Spa pages do not name, and the test recomputes that complement
;;  from the tree, so a tool added to the panel lands there by default
;;  instead of falling off the job pages unnoticed.
;;
;;  THE AB CHECKS LIVE IN "Rest" AND NOWHERE ELSE among the jobs.
;;  ABCURCHECK and its scan read the A/B survey ties themselves -- the
;;  tape rather than the pool -- so they are bench work over the
;;  numbers, not a step in laying out a pool, a cover or a spa.  Any
;;  further AB* check joins them on Rest and stays off the other three
;;  job pages; test_lazpanel.py enforces that against the tree, so a
;;  new one dropped onto Pool out of habit fails the suite instead of
;;  quietly widening a job page.  The Checking CATEGORY page still
;;  carries them: that page answers "what is this tool", which is a
;;  different question from "what am I doing this hour".

;;  ONE CAPTION PER COMMAND, here and nowhere else.  A command appears
;;  on several pages, so a caption kept beside each button would be the
;;  same words written two or three times -- and would drift the first
;;  time one copy was edited.  This is the only place they live.
(setq lzp:*captions*
  '(
    ("ABCDEF"           "Rectangle plot")
    ("ABCURCHECK"       "Perimeter continuity")
    ("ABCURCHECKSCAN"   "Perimeter continuity, no marks")
    ("ABFIND"           "A/B stake ties")
    ("ABHD"             "Survey perimeter + bottom")
    ("ABHDCOVER"        "Survey perimeter, no bottom")
    ("ABMOVE"           "Move mis-taped point")
    ("ADAB"             "Organic shape points")
    ("ALTABCDEF"        "Clockwise rectangle plot")
    ("AUTOBEAD"         "Bead offsets")
    ("AUTODIM"          "Auto dimension")
    ("AUTODIMSIDEPOV"   "Side-view dims")
    ("BPCALLOUT"        "Bad point callout")
    ("CABHD"            "Perimeter-only fit")
    ("CCPRECHECK"       "Tech flow chart")
    ("CDCALLOUT"        "Point-to-point cross dims")
    ("CDCREATE"         "Lines to cross dims")
    ("CHECK"            "Drawing check")
    ("CONSTELLATION"    "Points from cross dims")
    ("CORNERSTP"        "Corner step")
    ("COVERCHECK"       "Cover review")
    ("COVERSCAN"        "Cover scan")
    ("CPERPPTS"         "Curved perp points")
    ("CUSTBLOCK"        "Block from L/W/H")
    ("DIMARCCHECK"      "Arc endpoint check")
    ("DIMCHECK"         "Dimension review")
    ("DIMCONTEND"       "Continue dim chains")
    ("DIMSCAN"          "Dimension scan")
    ("DRONE"            "Drone cleanup")
    ("FITABHD"          "Typed template fit")
    ("FITABHDCOVER"     "Typed template fit, no bottom")
    ("FLOORDIM"         "Floor dims")
    ("HEMISTEP"         "Hemi step")
    ("LAZFORM"          "Pool from a filled-in chart")
    ("LAZTXT"           "The same form, drawn in tiles")
    ("LAZFORMCOVER"     "Chart to pool, no bottom")
    ("LAZSPA"           "Spa from a filled-in chart")
    ("LAZSTEP"          "Steps from a filled-in drawing")
    ("LHD"              "Laser outline fit")
    ("LINCHECK"         "Line checklist")
    ("LINFINCHECK"      "Liner finish review")
    ("LINFINSCAN"       "Liner finish scan")
    ("LINTXTCHK"        "Liner checklist text")
    ("LITECOVERSCAN"    "Cover scan, no dims")
    ("LITELINFINSCAN"   "Liner scan, no dims")
    ("LITESPACHECKSCAN" "Spa scan, no dims")
    ("NORMIESTEP"       "Normie step")
    ("OASIS"            "Freeform pool")
    ("PADDLE"           "Paddle pads")
    ("PERPPTS"          "Perpendicular points")
    ("POOL"             "Pool layout")
    ("POOLCOVER"        "Pool layout, no bottom")
    ("POOLDEMO"         "Worked pool example")
    ("SMARTFILLET"      "Corner radius, previewed")
    ("SPA"              "Spa template")
    ("SPACHECK"         "Spa sheet review")
    ("SPACHECKSCAN"     "Spa sheet scan")
    ("STAIRDIM"         "Stair dims")
    ("STOCKCOVER"       "Stock cover placement")
    ("TYDRN"            "Text + point tidy-up")
    ("TYLERDRONESUITE"  "Drone suite: tidy, pad, dim")
    ("WCALST"           "Unroll curved band")
    ("XFTCONV"          "Leica import cleanup")
    ("XYPLOT"           "X/Y offset plot")
   ))

(defun lzp:caption (name / p)
  (if (setq p (assoc name lzp:*captions*)) (cadr p) ""))

;;  THE PAGES, AS COLUMNS.  Each page is (title (heading cmd ...) ...) --
;;  one entry per COLUMN, laid out side by side across the page.  The
;;  job pages break their tools into the columns the work falls into:
;;  lay the shape out, tie the points, build the steps, dimension and
;;  check.  That is the grouping the drafter already carries; the
;;  columns just stop it being a single list of twenty-four.
;;
;;  A column heading of "" means the page is one plain column -- what
;;  the four category pages are.
;;
;;  WHY A MULTI-COLUMN PAGE SHOWS THE NAME ALONE.  A button reading
;;  "CDCALLOUT  -  Point-to-point cross dims" is about 39 cells wide;
;;  four of those side by side is 147, and DCL will not scroll a dialog
;;  wider than the screen -- the dialog simply fails to open.  So the
;;  columns carry the meaning in their headings and the buttons carry
;;  the command name, which puts the widest page at about 64 cells.
;;  Single-column pages have the room, and keep the caption on the
;;  button: the category pages stay the place to go to find out what a
;;  tool is, and the job pages are the place to go when you know.
(setq lzp:*groups*
  '(("Pool"
     ("Shape"
      "POOL"
      "LAZFORM"
      "LAZTXT"
      "OASIS"
      "ABHD"
      "ADAB"
      "FITABHD"
      "XFTCONV"
      )
     ("Points"
      "ABFIND"
      "ABMOVE"
      "CDCREATE"
      "CDCALLOUT"
      "BPCALLOUT"
      )
     ("Steps"
      "LAZSTEP"
      "CORNERSTP"
      "HEMISTEP"
      "NORMIESTEP"
      "AUTOBEAD"
      "PERPPTS"
      "CPERPPTS"
      )
     ("Dims & check"
      "AUTODIM"
      "LINFINCHECK"
      "LINFINSCAN"
      "LITELINFINSCAN"
      "DIMCHECK"
      "DIMSCAN"
      )
    )
     ("Cover"
     ("Shape"
      "POOLCOVER"
      "LAZFORMCOVER"
      "OASIS"
      "ABHDCOVER"
      "FITABHDCOVER"
      "STOCKCOVER"
      "CUSTBLOCK"
      "XFTCONV"
      )
     ("Points"
      "ABFIND"
      "ABMOVE"
      "CDCREATE"
      "CDCALLOUT"
      "BPCALLOUT"
      )
     ("Pads, dims & check"
      "PADDLE"
      "AUTODIM"
      "COVERCHECK"
      "COVERSCAN"
      "LITECOVERSCAN"
      "DIMCHECK"
      "DIMSCAN"
      )
    )
     ("Spa"
     (""
      "SPA"
      "LAZSPA"
      "CUSTBLOCK"
      "AUTODIM"
      "SPACHECK"
      "SPACHECKSCAN"
      "LITESPACHECKSCAN"
      "DIMCHECK"
      "DIMSCAN"
      )
    )
     ("Rest"
     (""
      "POOLDEMO"
      "CABHD"
      "LHD"
      "SMARTFILLET"
      "WCALST"
      "ABCDEF"
      "ALTABCDEF"
      "XYPLOT"
      "CONSTELLATION"
      "DRONE"
      "TYDRN"
      "TYLERDRONESUITE"
      "AUTODIMSIDEPOV"
      "STAIRDIM"
      "FLOORDIM"
      "DIMCONTEND"
      "CHECK"
      "DIMARCCHECK"
      "ABCURCHECK"
      "ABCURCHECKSCAN"
      "LINCHECK"
      "LINTXTCHK"
      "CCPRECHECK"
      )
    )
     ("Layout"
     (""
      "LAZFORM"
      "LAZTXT"
      "LAZFORMCOVER"
      "LAZSPA"
      "SPA"
      "POOL"
      "POOLCOVER"
      "POOLDEMO"
      "OASIS"
      "FITABHD"
      "FITABHDCOVER"
      "ABHD"
      "ABHDCOVER"
      "ADAB"
      "CABHD"
      "LHD"
      "PADDLE"
      "AUTOBEAD"
      "LAZSTEP"
      "CORNERSTP"
      "HEMISTEP"
      "NORMIESTEP"
      "SMARTFILLET"
      "STOCKCOVER"
      "WCALST"
      "CUSTBLOCK"
      )
    )
     ("Points"
     (""
      "ABCDEF"
      "ALTABCDEF"
      "XYPLOT"
      "CONSTELLATION"
      "ABFIND"
      "ABMOVE"
      "PERPPTS"
      "CPERPPTS"
      "XFTCONV"
      "DRONE"
      "TYDRN"
      "TYLERDRONESUITE"
      )
    )
     ("Dimensions"
     (""
      "AUTODIM"
      "AUTODIMSIDEPOV"
      "STAIRDIM"
      "FLOORDIM"
      "DIMCONTEND"
      "CDCREATE"
      "CDCALLOUT"
      "BPCALLOUT"
      )
    )
     ("Checking"
     (""
      "CHECK"
      "DIMARCCHECK"
      "DIMCHECK"
      "DIMSCAN"
      "ABCURCHECK"
      "ABCURCHECKSCAN"
      "LINCHECK"
      "LINFINCHECK"
      "LINFINSCAN"
      "LITELINFINSCAN"
      "COVERCHECK"
      "COVERSCAN"
      "LITECOVERSCAN"
      "SPACHECK"
      "SPACHECKSCAN"
      "LITESPACHECKSCAN"
      "LINTXTCHK"
      "CCPRECHECK"
      )
    )))

;; How the tab strip is laid out: one DCL row per entry, in this order.
;; The jobs sit on one line and the categories on the next, which is
;; both what they mean and what keeps the strip narrow -- eight tabs on
;; a single row run about 94 character cells, and DCL will not scroll a
;; dialog that is wider than the screen.  This is presentation only; the
;; pages themselves are still lzp:*groups*.  The test asserts the two
;; tables name exactly the same groups, so neither can drift.
(setq lzp:*rows*
  '(("Job"            "Pool" "Cover" "Spa" "Rest")
    ("Or by category" "Layout" "Points" "Dimensions" "Checking")))

(setq lzp:*pick* nil)             ; the button clicked on the last run
(setq lzp:*tbname* "LazPanel")    ; the panel's screen-button toolbar
(setq lzp:*tbsuite* "TylerDroneSuite")  ; and the suite's own

;; Whether TYLERDRONESUITE gets a screen button of its own.
;;
;;   AUTO  (the default) yes when the drone lisp was loaded ON ITS OWN,
;;         no when it arrived inside LAZPASS
;;   T     always      nil  never
;;
;; Set these AFTER the file has loaded and run LAZBUTTON -- not before.
;; The load sets each of them itself, so a value put in place first is
;; overwritten before it is ever read.  (editions/TYLERDRONE.lsp sets
;; them in its footer, which is after, and states BOTH outright rather
;; than leaving one to AUTO: AUTO reads a flag another build may have
;; left standing, which is exactly how that edition once put up no
;; button at all.)
;;
;; The distinction is the point.  A drawer who was handed tydrn.lsp by
;; itself has no panel to reach the suite through, so the button IS the
;; surface.  Inside LAZPASS the panel is already on screen and carries
;; the suite like every other tool, so a second toolbar is one more
;; thing on the strip earning nothing -- the whole build should put up
;; ONE external button, and that button is the panel's.
(setq lzp:*suitebutton* 'AUTO)

;; And whether the PANEL gets one.  Almost always yes -- being on screen
;; is the panel's whole reason for being.  The exception is a build put
;; together around ONE tool, where the panel is along for the ride and
;; its button would be the odd one out: editions/TYLERDRONE.lsp sets
;; this nil so the only thing on the strip is the drone button.
;; LAZPANEL still types the same as ever; it is just not on the strip.
(setq lzp:*panelbutton* T)

;; Draw the button at 32 pixels rather than 16.  The small one is easy
;; to miss on a crowded screen, and both pictures are already written
;; -- AutoCAD simply picks the 16 unless it is told otherwise.
;;
;; Read this before changing it: AutoCAD's large-button setting is not
;; per toolbar.  Asking for it here turns it on for EVERY toolbar in
;; the session, which is the same switch as Options > Display > "Use
;; large buttons for Toolbars".  That is why it is a tunable and why
;; LAZBUTTON says what it did: setq it nil and run LAZBUTTON to put the
;; setting back and return every toolbar to small buttons.
(setq lzp:*bigbutton* T)
(setq lzp:*iconerr* nil)          ; why the last icon write failed
(setq lzp:*pos* nil)              ; where the panel was last standing
(setq lzp:*go* nil)               ; the group a tab click asked for
(setq lzp:*icontype* nil)         ; which byte-array spelling worked
(setq lzp:*iconstep* nil)         ; the COM call the icon write died on
(setq lzp:*msxmlwhy* nil)         ; what each MSXML ProgID said, newest first
(setq lzp:*iconroute* nil)        ; which route actually wrote the file
(setq lzp:*icondir* nil)          ; the folder the icons landed in
(setq lzp:*iconref* nil)          ; "name" on the support path, else "path"
(setq lzp:*page* nil)             ; the page the panel reopens on
(setq lzp:*pins* nil)             ; the pinned tools, in pin order
(setq lzp:*pinkey* "HKEY_CURRENT_USER\\Software\\Calofin\\LazPanel")

;;; -------------------- roster access -----------------------------------

;; One page's commands, flattened out of its columns, in display order:
;; down the first column, then down the second.
(defun lzp:group-commands (name / g col c out)
  (foreach g lzp:*groups*
    (if (= (car g) name)
        (foreach col (cdr g)
          (foreach c (cdr col) (setq out (cons c out))))))
  (reverse out))

;; A page's columns: (heading cmd ...) each.
(defun lzp:group-columns (name / g out)
  (foreach g lzp:*groups*
    (if (= (car g) name) (setq out (cdr g))))
  out)

;; Folded, because a command that serves two jobs is listed on both
;; pages and the status line counts tools, not buttons.  First
;; appearance wins, so the order still reads as the panel is laid out.
(defun lzp:commands ( / g col c out)
  (foreach g lzp:*groups*
    (foreach col (cdr g)
      (foreach c (cdr col)
        (if (not (member c out))
          (setq out (cons c out))))))
  (reverse out))

;; Is C:<name> defined in this session?  An unbound symbol evaluates to
;; nil in AutoLISP, so reading the name and evaluating it is enough --
;; and it stays correct for commands loaded after this file was.
(defun lzp:has (name)
  (if (eval (read (strcat "C:" name))) t nil))

;; The subset of the roster that is loaded right now.
(defun lzp:loaded ( / n out)
  (foreach n (lzp:commands)
    (if (lzp:has n)
      (setq out (cons n out))))
  (reverse out))

;;; -------------------- the dialog --------------------------------------
;;  The DCL is built here as a list of lines and written to a temp file
;;  when the panel opens, so the whole panel travels inside this one
;;  .lsp.  Keys are the command names themselves; boxed columns carry
;;  the group labels.

(defun lzp:dlgname (group) (strcat "lazpanel_" (strcase group t)))

;; The tab strip: one button per group, laid out in the rows of
;; lzp:*rows* -- jobs on the first line, categories on the second.  DCL
;; has no tab tile, so a tab is a button that closes this page and
;; reopens the next -- and since done_dialog reports where the dialog
;; was standing, it reopens there rather than jumping back to the middle
;; of the screen.
(defun lzp:tabstrip ( / out r g)
  (foreach r lzp:*rows*
    (setq out (cons "  : boxed_row {" out))
    (setq out (cons (strcat "    label = \"" (car r) "\";") out))
    (foreach g (cdr r)
      (setq out (cons (strcat "    : button { key = \"tab_" g
                              "\"; label = \"" g "\"; }")
                      out)))
    (setq out (cons "  }" out)))
  (reverse out))

;;; -------------------- the pinned row ----------------------------------
;;  Pins are the answer to "I run four of these fifty-six all day": the
;;  tools you tick sit on EVERY page, in the order you pinned them, so
;;  the ones you actually use stop being three tabs apart.
;;
;;  A pinned button carries a "pin_" key so it cannot collide with the
;;  same tool's own button further down the page, and it is greyed by
;;  the same availability probe.
;;
;;  WIDTH.  The pinned row is generated DCL like everything else, and a
;;  handful of long names abreast -- LITESPACHECKSCAN is sixteen
;;  characters -- would push the dialog past the width DCL refuses to
;;  scroll, which does not clip the page, it stops it opening at all.
;;  So pins are packed greedily into as many rows as they need, with
;;  the Pin... button packed last like any other item.  Pin thirty
;;  tools and you get a tall panel, never a broken one.
(setq lzp:*pinbudget* 84)

(defun lzp:pin-label (n) (strcat "    : button { label = \"" n
                                 "\"; key = \"pin_" n "\"; }"))

;; (name width) for every pinned tool, then the editor button last.
(defun lzp:pin-items ( / out n)
  (foreach n lzp:*pins* (setq out (cons n out)))
  (reverse (cons "*edit*" out)))

(defun lzp:pinrows ( / out row w n cw items)
  (setq items (lzp:pin-items) row nil w 0)
  (foreach n items
    (setq cw (+ (strlen (if (= n "*edit*") "Pin..." n)) 6))
    (if (and row (> (+ w cw) lzp:*pinbudget*))
      (setq out (cons (reverse row) out) row nil w 0))
    (setq row (cons n row) w (+ w cw)))
  (if row (setq out (cons (reverse row) out)))
  (reverse out))

(defun lzp:pinrow ( / out rows r n first)
  (setq rows (lzp:pinrows) first t)
  (foreach r rows
    (setq out (cons "  : boxed_row {" out))
    ;; only the first row is labelled: two boxes both saying "Pinned"
    ;; would read as two different things
    (setq out (cons (strcat "    label = \""
                            (if first "Pinned" "") "\";") out))
    (foreach n r
      (setq out
        (cons (if (= n "*edit*")
                "    : button { label = \"Pin...\"; key = \"pin_edit\"; }"
                (lzp:pin-label n))
              out)))
    (if (and first (not lzp:*pins*))
      (setq out (cons "    : text { label = \"nothing pinned yet\"; }" out)))
    (setq out (cons "  }" out))
    (setq first nil))
  (reverse out))

;; One page per group.  The whole roster is still one list -- the pages
;; are lzp:*groups* itself, so re-ordering or re-grouping the tools is
;; an edit to that table and nothing else.
(defun lzp:dcl-one (g / out c col)
  ;; consed newest-first and reversed at the end, so this seed list
  ;; reads BACKWARDS: the dialog line last here comes out first
  (setq out (list (strcat "  : text { key = \"status\"; width = 60; "
                          "alignment = centered; }")
                  (strcat "  label = \"LazPanel " *lazpanel-version*
                          "  -  " (car g) "\";")
                  (strcat (lzp:dlgname (car g)) " : dialog {")))
  (setq out (append (reverse (lzp:tabstrip)) out))
  (setq out (append (reverse (lzp:pinrow)) out))
  (cond
    ;; ONE COLUMN: the page has the width to spare, so every button
    ;; carries its caption -- this is what the category pages are for.
    ((= (length (cdr g)) 1)
     (setq out (cons "  : boxed_column {" out))
     (setq out (cons (strcat "    label = \"" (car g) "\";") out))
     (foreach c (cdr (car (cdr g)))
       (setq out (cons (strcat "    : button { label = \"" c "  -  "
                               (lzp:caption c) "\"; key = \"" c "\"; }")
                       out)))
     (setq out (cons "  }" out)))
    ;; SEVERAL COLUMNS, side by side: the heading says what the column
    ;; is for and the buttons carry the command name alone.  Four
    ;; captioned buttons abreast would be about 147 cells wide and the
    ;; dialog would not open at all.
    (t
     (setq out (cons "  : boxed_row {" out))
     (setq out (cons (strcat "    label = \"" (car g) "\";") out))
     (foreach col (cdr g)
       (setq out (cons "    : boxed_column {" out))
       (setq out (cons (strcat "      label = \"" (car col) "\";") out))
       (foreach c (cdr col)
         (setq out (cons (strcat "      : button { label = \"" c
                                 "\"; key = \"" c "\"; }")
                         out)))
       (setq out (cons "    }" out)))
     (setq out (cons "  }" out))))
  (setq out (cons "  spacer;" out))
  (setq out (cons (strcat "  : button { label = \"Close\"; key = \"cancel\"; "
                          "is_default = true; is_cancel = true; "
                          "fixed_width = true; alignment = centered; }")
                  out))
  (reverse (cons "}" out)))

;; The pin editor: every tool on the panel as a toggle, in three
;; columns so fifty-six of them fit on a screen rather than a scroll
;; DCL would not give.
(defun lzp:dcl-pins ( / out cmds n per i j c)
  (setq cmds (lzp:commands)
        n    (length cmds)
        per  (1+ (/ (1- n) 3))
        i    0)
  (setq out (list "lazpanel_pins : dialog {"
                  "  label = \"LazPanel  -  pinned tools\";"
                  (strcat "  : text { label = \"Ticked tools sit in the "
                          "Pinned row on every page.\"; }")
                  "  : row {"))
  (while (< i n)
    (setq out (append out (list "    : column {")) j 0)
    (while (and (< j per) (< i n))
      (setq c (nth i cmds))
      (setq out (append out
        (list (strcat "      : toggle { label = \"" c
                      "\"; key = \"tg_" c "\"; }"))))
      (setq i (1+ i) j (1+ j)))
    (setq out (append out (list "    }"))))
  (append out
    (list "  }" "  spacer;"
          (strcat "  : row { alignment = centered; "
                  ": button { label = \"OK\"; key = \"accept\"; "
                  "is_default = true; fixed_width = true; } "
                  ": button { label = \"Cancel\"; key = \"cancel\"; "
                  "is_cancel = true; fixed_width = true; } }")
          "}")))

;; Every page, then the pin editor, in one generated file.
(defun lzp:dcl-lines ( / out g)
  (foreach g lzp:*groups*
    (setq out (append out (lzp:dcl-one g) (list ""))))
  (append out (lzp:dcl-pins) (list "")))

;; The write loop, alone so it can run under vl-catch-all-apply: if a
;; write dies half way (disk full, quota) the handle still gets closed
;; and the partial file deleted instead of being handed to load_dialog.
(defun lzp:write-lines (fh / l)
  (foreach l (lzp:dcl-lines)
    (write-line l fh)))

;; Write the dialog into the system temp folder; the path comes back,
;; or nil when the folder cannot be written to.
(defun lzp:write-dcl ( / f fh err)
  (setq f (vl-filename-mktemp "lazpanel" nil ".dcl"))
  (if (and f (setq fh (open f "w")))
    (progn
      (setq err (vl-catch-all-apply 'lzp:write-lines (list fh)))
      (close fh)
      (cond
        ((vl-catch-all-error-p err)
         (vl-file-delete f)
         nil)
        (t f)))))

;; Run a roster command by name, exactly as if it had been typed.  The
;; probe guards the greyed-button race: a command that vanished between
;; opening the panel and clicking reports itself instead of erroring.
(defun lzp:split (s sep / i n c cur out)
  (setq i 1 n (strlen s) cur "")
  (while (<= i n)
    (setq c (substr s i 1))
    (if (= c sep)
      (progn (if (/= cur "") (setq out (cons cur out))) (setq cur ""))
      (setq cur (strcat cur c)))
    (setq i (1+ i)))
  (if (/= cur "") (setq out (cons cur out)))
  (reverse out))

;; Read the pins back, dropping any name no longer on the roster: a pin
;; left over from an older build must not put a dead button on screen,
;; and the roster is the only thing that says what is real.
(defun lzp:pins-read ( / s)
  (setq s (vl-catch-all-apply 'vl-registry-read (list lzp:*pinkey* "Pins")))
  (setq lzp:*pins*
    (if (and (not (vl-catch-all-error-p s)) (= (type s) 'STR) (/= s ""))
      (vl-remove-if-not '(lambda (n) (member n (lzp:commands)))
                        (lzp:split s ";"))))
  lzp:*pins*)

(defun lzp:pins-write ( / s n)
  (setq s "")
  (foreach n lzp:*pins*
    (setq s (strcat s (if (= s "") "" ";") n)))
  (vl-catch-all-apply 'vl-registry-write (list lzp:*pinkey* "Pins" s))
  lzp:*pins*)

;; Pin order is click order: a newly ticked tool goes on the END rather
;; than jumping into the middle of a row the hand has already learned.
(defun lzp:pin-toggle (name val)
  (if (= val "1")
    (if (not (member name lzp:*pins*))
      (setq lzp:*pins* (append lzp:*pins* (list name))))
    (setq lzp:*pins* (vl-remove name lzp:*pins*)))
  (princ))

;; The toggle dialog.  Cancel re-reads the registry rather than trying
;; to undo the ticks one by one -- the stored list is the truth, so
;; going back to it is exact where unwinding would be approximate.
(defun lzp:pin-edit (dcl / n rc)
  (cond
    ((not (new_dialog "lazpanel_pins" dcl)) nil)
    (t
     (foreach n (lzp:commands)
       (set_tile (strcat "tg_" n) (if (member n lzp:*pins*) "1" "0"))
       (action_tile (strcat "tg_" n)
                    (strcat "(lzp:pin-toggle \"" n "\" $value)")))
     (action_tile "accept" "(done_dialog 1)")
     (action_tile "cancel" "(done_dialog 0)")
     (setq rc (start_dialog))
     (if (= rc 1) (lzp:pins-write) (lzp:pins-read))
     t)))

(defun lzp:launch (name / fn)
  (setq fn (read (strcat "C:" name)))
  (cond
    ((eval fn)
     (princ (strcat "\nLAZPANEL: running " name
                    " -- LAZPANEL reopens the panel."))
     (eval (list fn)))
    (t
     (princ (strcat "\nLAZPANEL: " name
                    " is not loaded in this session.")))))

;;; -------------------- the screen button -------------------------------
;;  A one-button toolbar so the panel can sit on screen like any other
;;  toolbar button -- drag it anywhere, dock it, click it to open the
;;  panel.  Created through the ActiveX menu API, so there is no CUI
;;  file to install; the icon is an orange hexagon, point north.
;;
;;  Everything here is best effort by design.  A session without COM,
;;  with a locked CUI or an unwritable temp folder loses the button and
;;  keeps the panel -- which is why the load-time call sits inside
;;  vl-catch-all-apply and why nothing below reports its own failure.

;; The mark: a hexagon with a corner facing north.  Each size is
;; drawn at its own resolution rather than the small one doubled --
;; a hexagon doubled from 16 pixels keeps the 16-pixel staircase on
;; its diagonals, and those diagonals are the whole shape.
(setq lzp:*icon16*
  '(
    "................"
    "......XXXX......"
    ".....XXXXXX....."
    "...XXXXXXXXXX..."
    "..XXXXXXXXXXXX.."
    "..XXXXXXXXXXXX.."
    "..XXXXXXXXXXXX.."
    "..XXXXXXXXXXXX.."
    "..XXXXXXXXXXXX.."
    "..XXXXXXXXXXXX.."
    "..XXXXXXXXXXXX.."
    "..XXXXXXXXXXXX.."
    "...XXXXXXXXXX..."
    ".....XXXXXX....."
    "......XXXX......"
    "................"))

;; The second mark: a triangle, point north, for TYLERDRONESUITE's own
;; button.  A different SHAPE rather than a different colour, because
;; the two sit side by side on the same strip and both are orange --
;; lzp:bmp-bytes paints every "X" the one orange, which is what makes
;; the pair read as one toolkit rather than two.
(setq lzp:*tri16*
  '(
    "................"
    ".......XX......."
    ".......XX......."
    "......XXXX......"
    "......XXXX......"
    ".....XXXXXX....."
    ".....XXXXXX....."
    "....XXXXXXXX...."
    "....XXXXXXXX...."
    "...XXXXXXXXXX..."
    "...XXXXXXXXXX..."
    "..XXXXXXXXXXXX.."
    "..XXXXXXXXXXXX.."
    ".XXXXXXXXXXXXXX."
    "XXXXXXXXXXXXXXXX"
    "................"
))

(setq lzp:*tri32*
  '(
    "................................"
    "................................"
    "...............XX..............."
    "...............XX..............."
    "..............XXXX.............."
    "..............XXXX.............."
    ".............XXXXXX............."
    ".............XXXXXX............."
    "............XXXXXXXX............"
    "............XXXXXXXX............"
    "...........XXXXXXXXXX..........."
    "...........XXXXXXXXXX..........."
    "..........XXXXXXXXXXXX.........."
    "..........XXXXXXXXXXXX.........."
    ".........XXXXXXXXXXXXXX........."
    ".........XXXXXXXXXXXXXX........."
    "........XXXXXXXXXXXXXXXX........"
    ".......XXXXXXXXXXXXXXXXXX......."
    ".......XXXXXXXXXXXXXXXXXX......."
    "......XXXXXXXXXXXXXXXXXXXX......"
    "......XXXXXXXXXXXXXXXXXXXX......"
    ".....XXXXXXXXXXXXXXXXXXXXXX....."
    ".....XXXXXXXXXXXXXXXXXXXXXX....."
    "....XXXXXXXXXXXXXXXXXXXXXXXX...."
    "....XXXXXXXXXXXXXXXXXXXXXXXX...."
    "...XXXXXXXXXXXXXXXXXXXXXXXXXX..."
    "...XXXXXXXXXXXXXXXXXXXXXXXXXX..."
    "..XXXXXXXXXXXXXXXXXXXXXXXXXXXX.."
    "..XXXXXXXXXXXXXXXXXXXXXXXXXXXX.."
    ".XXXXXXXXXXXXXXXXXXXXXXXXXXXXXX."
    "................................"
    "................................"
))

(setq lzp:*icon32*
  '(
    "................................"
    "..............XXXX.............."
    ".............XXXXXX............."
    "...........XXXXXXXXXX..........."
    ".........XXXXXXXXXXXXXX........."
    ".......XXXXXXXXXXXXXXXXXX......."
    "......XXXXXXXXXXXXXXXXXXXX......"
    "....XXXXXXXXXXXXXXXXXXXXXXXX...."
    "...XXXXXXXXXXXXXXXXXXXXXXXXXX..."
    "...XXXXXXXXXXXXXXXXXXXXXXXXXX..."
    "...XXXXXXXXXXXXXXXXXXXXXXXXXX..."
    "...XXXXXXXXXXXXXXXXXXXXXXXXXX..."
    "...XXXXXXXXXXXXXXXXXXXXXXXXXX..."
    "...XXXXXXXXXXXXXXXXXXXXXXXXXX..."
    "...XXXXXXXXXXXXXXXXXXXXXXXXXX..."
    "...XXXXXXXXXXXXXXXXXXXXXXXXXX..."
    "...XXXXXXXXXXXXXXXXXXXXXXXXXX..."
    "...XXXXXXXXXXXXXXXXXXXXXXXXXX..."
    "...XXXXXXXXXXXXXXXXXXXXXXXXXX..."
    "...XXXXXXXXXXXXXXXXXXXXXXXXXX..."
    "...XXXXXXXXXXXXXXXXXXXXXXXXXX..."
    "...XXXXXXXXXXXXXXXXXXXXXXXXXX..."
    "...XXXXXXXXXXXXXXXXXXXXXXXXXX..."
    "...XXXXXXXXXXXXXXXXXXXXXXXXXX..."
    "....XXXXXXXXXXXXXXXXXXXXXXXX...."
    "......XXXXXXXXXXXXXXXXXXXX......"
    ".......XXXXXXXXXXXXXXXXXX......."
    ".........XXXXXXXXXXXXXX........."
    "...........XXXXXXXXXX..........."
    ".............XXXXXX............."
    "..............XXXX.............."
    "................................"))

(defun lzp:le2 (n)
  (list (rem n 256) (rem (/ n 256) 256)))

(defun lzp:le4 (n)
  (append (lzp:le2 (rem n 65536)) (lzp:le2 (/ n 65536))))

;; The complete .bmp as a byte list: 24bpp, bottom-up rows (a positive
;; height means the FIRST row in the file is the BOTTOM row of the
;; image, hence the reverse).  "X" pixels are orange -- stored B,G,R,
;; so 0 165 255 -- and the rest panel grey.  Both sizes give a row
;; width that is a multiple of 4 (48 and 96), so there is no row
;; padding to get wrong.
(defun lzp:bmp-bytes (size grid / fg bg rowbytes out row s i)
  (setq fg '(0 165 255)
        bg '(54 54 54)
        rowbytes (* 3 size))
  (setq out (append
              (list 66 77)                      ; "BM"
              (lzp:le4 (+ 54 (* rowbytes size)))
              '(0 0 0 0)
              (lzp:le4 54)                      ; pixel data offset
              (lzp:le4 40)                      ; BITMAPINFOHEADER
              (lzp:le4 size)
              (lzp:le4 size)
              (lzp:le2 1)                       ; planes
              (lzp:le2 24)                      ; bits per pixel
              (lzp:le4 0)                       ; no compression
              (lzp:le4 (* rowbytes size))
              (lzp:le4 0) (lzp:le4 0)
              (lzp:le4 0) (lzp:le4 0)))
  ;; built by consing and reversed once: appending inside the loop
  ;; would copy the whole list per pixel, which for the 32x32 is
  ;; millions of cons cells and a visible pause on every load
  (setq out (reverse out))
  (foreach row (reverse grid)
    (setq i 1)
    (while (<= i size)
      (setq s (substr row i 1))
      (setq out (cons (caddr (if (= s "X") fg bg))
                      (cons (cadr (if (= s "X") fg bg))
                            (cons (car (if (= s "X") fg bg)) out))))
      (setq i (1+ i))))
  (reverse out))

;;  WRITING IT.  Not with write-char: AutoLISP opens files in text mode
;;  and has no NUL in its character model at all -- (chr 0) is the
;;  empty string -- while a 24-bit BMP header is full of them.  The
;;  pixel-data offset (54 0 0 0), the header size (40 0 0 0) and the
;;  five zeroed DIB fields are 43 NULs before a single pixel, and the
;;  orange itself has a zero blue channel.  There is no arrangement of
;;  this format that write-char could emit, so the bytes go out through
;;  an ADODB.Stream in binary mode instead.
;;
;;  That is no new dependency: the toolbar this icon goes on is made
;;  through the ActiveX menu API a few lines below, so a session that
;;  cannot reach COM has no button to put an icon on.  If the stream
;;  is unavailable the write fails, the caller skips SetBitmaps, and
;;  the button keeps its default face.

;; A byte array is the one piece of this that AutoLISP may refuse:
;; vlax-make-safearray's documented type constants stop at
;; vlax-vbVariant, and VT_UI1 (17) is not among them, so whether it is
;; accepted is a property of the release rather than of the code.  Both
;; spellings are tried before giving up, and which one worked is
;; recorded for LAZICON to report.
;;  BASE64, AND WHY THE ICON GOES OUT THROUGH IT.
;;
;;  ADODB.Stream's Write wants a VT_UI1 (byte) array and nothing else.
;;  AutoLISP cannot reliably make one: vlax-make-safearray's documented
;;  type constants stop at vlax-vbVariant, VT_UI1 (17) is not among
;;  them, and whether a release accepts it anyway is a property of that
;;  release.  Where it is refused the old code fell back to a
;;  vbInteger (VT_I2) array, which Write then rejected with
;;
;;      Arguments are of the wrong type, are out of acceptable range,
;;      or are in conflict with one another
;;
;;  -- reported from the field, and the reason the button had no
;;  picture at all rather than a wrong one.
;;
;;  The way round it is to stop trying to build a byte array in
;;  AutoLISP.  Base64 is a pure-ASCII encoding of arbitrary bytes --
;;  no NUL, nothing AutoLISP's character model lacks -- so the bytes
;;  can be carried in an ordinary string, and MSXML turns that string
;;  into a real VT_UI1 array on the other side.  Both components ship
;;  with Windows, and the toolbar this icon goes on already needs COM.
(setq lzp:*b64*
  "ABCDEFGHIJKLMNOPQRSTUVWXYZabcdefghijklmnopqrstuvwxyz0123456789+/")

;; Join a list of strings without the quadratic cost of strcat-ing onto
;; one accumulator: a 32x32 icon is 4168 base64 characters, and growing
;; that a chunk at a time copies the whole string every time.  Pairwise
;; merging is O(n log n) and finishes instantly.
(defun lzp:joinstr (lst / out a)
  (while (cdr lst)
    (setq out nil)
    (while lst
      (setq a (car lst) lst (cdr lst))
      (if lst
        (setq out (cons (strcat a (car lst)) out) lst (cdr lst))
        (setq out (cons a out))))
    (setq lst (reverse out)))
  (if lst (car lst) ""))

;; Bytes to base64.  Plain integer arithmetic rather than lsh/logand:
;; the shifts are all by 2, 4 and 6 bits, which is division and
;; multiplication by 4, 16 and 64, and every AutoLISP has those.
(defun lzp:b64 (bytes / out n b1 b2 b3)
  (while bytes
    (setq b1 (car bytes) bytes (cdr bytes) n 1 b2 0 b3 0)
    (if bytes (setq b2 (car bytes) bytes (cdr bytes) n 2))
    (if bytes (setq b3 (car bytes) bytes (cdr bytes) n 3))
    (setq out
      (cons
        (strcat
          (substr lzp:*b64* (1+ (/ b1 4)) 1)
          (substr lzp:*b64* (1+ (+ (* (rem b1 4) 16) (/ b2 16))) 1)
          (if (>= n 2)
            (substr lzp:*b64* (1+ (+ (* (rem b2 16) 4) (/ b3 64))) 1)
            "=")
          (if (>= n 3) (substr lzp:*b64* (1+ (rem b3 64)) 1) "="))
        out)))
  (lzp:joinstr (reverse out)))

;; The base64 string as a real byte array, via MSXML's bin.base64
;; element.  nodeTypedValue on such an element IS a VT_UI1 array, which
;; is exactly what Write will take.
;; The whole chain on one document: an element typed bin.base64, the
;; base64 text put into it, and the byte array read back out.
(defun lzp:b64-chain (doc b64 / el out)
  ;; the documented long spellings, not the vlax-get / vlax-put /
  ;; vlax-invoke shorthands: the shorthands are what the rest of this
  ;; file uses and they clearly work here, but this chain is the part
  ;; that keeps coming back empty, so it does not get to be the place
  ;; a spelling is also in question
  (setq el (vlax-invoke-method doc 'createElement "b"))
  (vlax-put-property el 'dataType "bin.base64")
  (vlax-put-property el 'text b64)
  (setq out (vlax-get-property el 'nodeTypedValue))
  (vl-catch-all-apply 'vlax-release-object (list el))
  out)

;; One ProgID, tried all the way through.  nil if this version cannot
;; carry it.
(defun lzp:whynot (id msg)
  (setq lzp:*msxmlwhy*
        (cons (strcat id ": " msg) lzp:*msxmlwhy*))
  nil)

(defun lzp:b64-try (id b64 / doc r)
  (setq r (vl-catch-all-apply 'vlax-create-object (list id)))
  (cond
    ((vl-catch-all-error-p r)
     (lzp:whynot id (vl-catch-all-error-message r)))
    ((null r) (lzp:whynot id "came back nil"))
    (t
     (setq doc r)
     (setq r (vl-catch-all-apply 'lzp:b64-chain (list doc b64)))
     (vl-catch-all-apply 'vlax-release-object (list doc))
     (cond
       ((vl-catch-all-error-p r)
        (lzp:whynot id (vl-catch-all-error-message r)))
       ((null r) (lzp:whynot id "the chain ran but gave back nothing"))
       (t (setq lzp:*icontype* (strcat "bin.base64 via " id))
          r)))))

;;  EVERY ProgID IS TRIED ALL THE WAY THROUGH, not just far enough to
;;  create.  MSXML 6.0 creates perfectly happily and then refuses
;;  dataType -- XDR schema support, of which bin.base64 is part, was
;;  removed in 6.0 -- so a version test that stops at "did the object
;;  appear?" picks 6.0, fails on the next line, and reports nothing.
;;  That is exactly what happened in the field: the report said
;;  "array: VT_UI1 safearray", meaning this returned nil and the
;;  fallback ran.
;;
;;  So 3.0 and the version-independent Microsoft.XMLDOM come first --
;;  both carry XDR -- and 6.0 stays at the back where it costs one
;;  failed attempt and nothing else.
(defun lzp:bytes-msxml (bytes / b64 out id)
  (setq lzp:*msxmlwhy* nil)
  (setq b64 (lzp:b64 bytes))
  (foreach id '("MSXML2.DOMDocument.3.0" "Microsoft.XMLDOM"
                "MSXML2.DOMDocument" "MSXML2.DOMDocument.6.0")
    (if (not out) (setq out (lzp:b64-try id b64))))
  out)

;; A byte array by whichever route this AutoCAD allows.  MSXML first
;; because it is the one that does not depend on an undocumented
;; safearray type; the two safearray spellings stay as fallbacks so a
;; machine where they DO work is no worse off.  Which route won is
;; recorded for LAZICON to report.
(defun lzp:bytearray (bytes / sa)
  (cond
    ;; lzp:b64-try has already recorded WHICH MSXML version carried it,
    ;; which is the part worth knowing; do not flatten that back to a
    ;; generic label here
    ((setq sa (lzp:bytes-msxml bytes)) sa)
    (t
     (setq sa (vl-catch-all-apply
                'vlax-make-safearray
                (list 17 (cons 0 (1- (length bytes))))))
     (if (vl-catch-all-error-p sa)
         (setq sa (vl-catch-all-apply
                    'vlax-make-safearray
                    (list vlax-vbInteger (cons 0 (1- (length bytes)))))
               lzp:*icontype* "vbInteger (VT_I2 - Write may refuse this)")
         (setq lzp:*icontype* "VT_UI1 safearray"))
     (cond
       ((vl-catch-all-error-p sa) (setq lzp:*icontype* "none - no array could be made") nil)
       (t (vlax-safearray-fill sa bytes)
          sa)))))

(defun lzp:bmp-stream (st path bytes / sa)
  (setq lzp:*icontype* nil)
  ;; each step names itself before it runs, so a failure reports WHICH
  ;; call refused rather than one COM message with no address on it
  (setq lzp:*iconstep* "building the byte array")
  (if (not (setq sa (lzp:bytearray bytes)))
      (exit))                                 ; caught by the caller
  (setq lzp:*iconstep* "Type = 1 (adTypeBinary)")
  (vlax-put st 'Type 1)
  (setq lzp:*iconstep* "Open")
  (vlax-invoke st 'Open)
  ;; Two spellings.  Write takes a Variant, and whether a raw safearray
  ;; marshals into one is another thing that varies by release -- so if
  ;; the plain call is refused, the wrapped one is tried before giving
  ;; up.  The step name says which was in play.
  (setq lzp:*iconstep* "Write")
  (if (vl-catch-all-error-p
        (vl-catch-all-apply 'vlax-invoke (list st 'Write sa)))
    (progn
      (setq lzp:*iconstep* "Write (variant-wrapped)")
      (vlax-invoke st 'Write (vlax-make-variant sa))))
  (setq lzp:*iconstep* "SaveToFile")
  (vlax-invoke st 'SaveToFile path 2)         ; overwrite if present
  (setq lzp:*iconstep* "Close")
  (vlax-invoke st 'Close)
  (setq lzp:*iconstep* nil)
  t)

;;; -------------------- the route that needs no byte array ---------------
;;  Every failure so far has been about handing AutoLISP's idea of an
;;  array to COM.  VT_UI1 was accepted on the machine that reported it
;;  and Write refused the array anyway, wrapped in a variant or not;
;;  MSXML, which exists to sidestep that, came back empty.
;;
;;  So here is the route with no array in it at all.  certutil has
;;  shipped with Windows since Vista and decodes base64 to binary in
;;  one command.  AutoLISP writes the base64 as ORDINARY TEXT with
;;  write-line -- which is the one thing it has never had trouble with
;;  -- and Windows does the decoding.  Nothing crosses the COM boundary
;;  except a command line.
;;
;;  It is last because it costs a process and writes a second file;
;;  when the stream route works this never runs.
(defun lzp:b64-lines (b64 fh / i n)
  ;; certutil wants the base64 wrapped rather than one enormous line
  (setq i 1 n (strlen b64))
  (while (<= i n)
    (write-line (substr b64 i 76) fh)
    (setq i (+ i 76))))

(defun lzp:bmp-certutil (path bytes / tmp fh sh r out)
  (setq tmp (strcat path ".b64"))
  (cond
    ((not (setq fh (open tmp "w")))
     (setq lzp:*iconerr*
           (strcat lzp:*iconerr* "  certutil: could not write " tmp "."))
     nil)
    (t
     (setq r (vl-catch-all-apply 'lzp:b64-lines (list (lzp:b64 bytes) fh)))
     (close fh)
     (cond
       ((vl-catch-all-error-p r)
        (vl-file-delete tmp)
        (setq lzp:*iconerr*
              (strcat lzp:*iconerr* "  certutil: writing the base64 failed: "
                      (vl-catch-all-error-message r)))
        nil)
       (t
        (setq sh (vl-catch-all-apply 'vlax-create-object
                                     (list "WScript.Shell")))
        (cond
          ((vl-catch-all-error-p sh)
           (vl-file-delete tmp)
           (setq lzp:*iconerr*
                 (strcat lzp:*iconerr* "  certutil: WScript.Shell would not "
                         "start: " (vl-catch-all-error-message sh)))
           nil)
          (t
           ;; the third argument waits for it, so the file is there by
           ;; the time this returns rather than some moments later
           (setq r (vl-catch-all-apply
                     'vlax-invoke-method
                     (list sh 'Run
                           (strcat "cmd /c certutil -f -decode \"" tmp
                                   "\" \"" path "\"")
                           0 :vlax-true)))
           (vl-catch-all-apply 'vlax-release-object (list sh))
           (vl-file-delete tmp)
           (cond
             ((vl-catch-all-error-p r)
              (setq lzp:*iconerr*
                    (strcat lzp:*iconerr* "  certutil: " 
                            (vl-catch-all-error-message r)))
              nil)
             ((findfile path) (setq lzp:*icontype* "base64 text + certutil") t)
             (t (setq lzp:*iconerr*
                      (strcat lzp:*iconerr* "  certutil ran but wrote nothing."))
                nil)))))))))

(defun lzp:bmp-via-stream (path bytes / st ok)
  (setq st (vl-catch-all-apply 'vlax-create-object (list "ADODB.Stream")))
  (cond
    ((vl-catch-all-error-p st)
     (setq lzp:*iconerr*
           (strcat "ADODB.Stream would not start: "
                   (vl-catch-all-error-message st)))
     nil)
    ((null st)
     (setq lzp:*iconerr* "ADODB.Stream came back nil.")
     nil)
    (t
     (setq ok (vl-catch-all-apply 'lzp:bmp-stream (list st path bytes)))
     (vl-catch-all-apply 'vlax-release-object (list st))
     (cond
       ((vl-catch-all-error-p ok)
        (setq lzp:*iconerr*
              (strcat "writing " path " failed at "
                      (if lzp:*iconstep* lzp:*iconstep* "an unnamed step")
                      ": " (vl-catch-all-error-message ok)))
        nil)
       (t path)))))

;; The icon, by whichever route this machine allows.  The stream first
;; because it writes the file directly; certutil after it, because it
;; costs a process and a second file but asks nothing of AutoLISP but
;; text.  Which one won is recorded for LAZICON to report.
(defun lzp:bmp-write (path size grid / bytes)
  (setq lzp:*iconerr* ""
        lzp:*iconroute* nil
        bytes (lzp:bmp-bytes size grid))
  (cond
    ((lzp:bmp-via-stream path bytes)
     (setq lzp:*iconroute* "ADODB.Stream" lzp:*iconerr* nil)
     path)
    ((lzp:bmp-certutil path bytes)
     (setq lzp:*iconroute* "certutil")
     path)
    (t nil)))

;; A STABLE path, not a fresh temp name each time: SetBitmaps stores the
;; path rather than the image, and AutoCAD re-reads it whenever the
;; button is redrawn.  A toolbar that survives into another session
;; would otherwise be pointing at a swept temp file for ever.
(defun lzp:icon-file (dir stem name / d)
  (setq d dir)
  ;; a folder is not guaranteed to end in a separator -- glue the name
  ;; straight on and a folder called Temp becomes a file called
  ;; Templazpanel-16.bmp, which fails silently later
  (if (not (member (substr d (strlen d) 1) '("\\" "/")))
      (setq d (strcat d "\\")))
  (strcat d stem "-" name ".bmp"))

(defun lzp:icon-path (stem name / d)
  (setq d (getvar "TEMPPREFIX"))
  (if (and d (= (type d) 'STR) (/= d ""))
      (lzp:icon-file d stem name)
      (vl-filename-mktemp (strcat stem "-" name) nil ".bmp")))

;;  WHERE THE FILES GO, AND WHAT SETBITMAPS IS TOLD.  The CUI resolves a
;;  toolbar bitmap by NAME along the support file search path -- hand it
;;  a full path into the temp folder, which is not on that path, and on
;;  many builds the button draws the "?" missing-image placeholder even
;;  though the file is right where the path says.  So the icons go into
;;  the FIRST folder of the support path (the user's own Support folder,
;;  writable by design) and SetBitmaps is handed the bare names, which
;;  resolve exactly the way the CUI wants to resolve them.  Only when
;;  that folder cannot be written does this fall back to the temp folder
;;  and full paths -- better a chance of an icon than none.

(defun lzp:support-read ()
  (vla-get-supportpath
    (vla-get-files (vla-get-preferences (vlax-get-acad-object)))))

;; The first entry of the support path, or nil.
(defun lzp:support-dir ( / p out i n c)
  (setq p (vl-catch-all-apply 'lzp:support-read nil))
  (if (and (not (vl-catch-all-error-p p)) (= (type p) 'STR) (/= p ""))
      (progn
        (setq i 1 n (strlen p) out "")
        (while (and (<= i n) (/= (setq c (substr p i 1)) ";"))
          (setq out (strcat out c)
                i (1+ i)))
        (if (/= out "") out))))

;; Write both sizes into DIR; the paths, or nil when either write fails
;; (lzp:bmp-write records why in lzp:*iconerr*).
(defun lzp:try-icons (dir stem art16 art32 / s l)
  (if (and dir (= (type dir) 'STR) (/= dir ""))
      (progn
        (setq s (lzp:icon-file dir stem "16")
              l (lzp:icon-file dir stem "32"))
        (if (and (lzp:bmp-write s 16 art16)
                 (lzp:bmp-write l 32 art32))
            (progn (setq lzp:*icondir* dir)
                   (list s l))))))

;; What to hand SetBitmaps: bare names when the files sit on the support
;; path, full temp paths as the fallback.
(defun lzp:write-bmps (stem art16 art32 / d)
  (setq lzp:*icondir* nil
        lzp:*iconref* nil)
  (cond
    ((and (setq d (lzp:support-dir)) (lzp:try-icons d stem art16 art32))
     (setq lzp:*iconref* "name")
     (list (strcat stem "-16.bmp") (strcat stem "-32.bmp")))
    ((lzp:try-icons (getvar "TEMPPREFIX") stem art16 art32)
     (setq lzp:*iconref* "path")
     (list (lzp:icon-file (getvar "TEMPPREFIX") stem "16")
           (lzp:icon-file (getvar "TEMPPREFIX") stem "32")))))

;; The LazPanel toolbar, wherever it lives -- one this file made in an
;; earlier session may sit in any loaded menu group.
;;; -------------------- the two screen buttons --------------------------
;;  Each is one toolbar with one button, and a spec says everything that
;;  differs between them:
;;
;;      (toolbar-name  icon-stem  tooltip  command  art16  art32)
;;
;;  There are two because they are two different tools.  The panel is
;;  the whole roster; the suite is one job someone runs all day, and it
;;  earns a button of its own rather than two clicks through a dialog.
;;  A different SHAPE tells them apart -- hexagon and triangle -- since
;;  both are painted the same orange.
(defun lzp:tb-name (spec) (nth 0 spec))
(defun lzp:tb-stem (spec) (nth 1 spec))
(defun lzp:tb-tip  (spec) (nth 2 spec))
(defun lzp:tb-cmd  (spec) (nth 3 spec))
(defun lzp:tb-16   (spec) (nth 4 spec))
(defun lzp:tb-32   (spec) (nth 5 spec))

(defun lzp:panel-spec ()
  (list lzp:*tbname* "lazpanel"
        "Open the LazPanel tool panel" "LAZPANEL"
        lzp:*icon16* lzp:*icon32*))

(defun lzp:suite-spec ()
  (list lzp:*tbsuite* "tylerdronesuite"
        "TYLERDRONESUITE - TYDRN, then PADDLE, then AUTODIM"
        "TYLERDRONESUITE"
        lzp:*tri16* lzp:*tri32*))

;; Is this session the LAZPASS build?  Both LAZPASS.lsp and
;; CALOFIN-LOADER.lsp raise cal:*build-loading* before they load a
;; thing, and neither lowers it -- so it answers for the session, which
;; is what is being asked.  Standalone the symbol is simply unbound,
;; and an unbound symbol is nil.
(defun lzp:in-build-p () (if cal:*build-loading* T nil))

;; Does the suite want a button of its own here?
(defun lzp:suite-wanted-p ()
  (and (lzp:has "TYLERDRONESUITE")
       (cond ((eq lzp:*suitebutton* 'AUTO) (not (lzp:in-build-p)))
             (lzp:*suitebutton* T))))

;; The buttons to put up.  Two things have to be true for the suite's:
;; its command has to be loaded -- LAZPANEL.lsp APPLOADed on its own has
;; no tydrn.lsp beside it, and a button that answers a click with
;; "Unknown command" is worse than no button -- and this has to not be
;; the LAZPASS build, which puts up one external button and that one is
;; the panel's.
(defun lzp:tb-specs ( / out)
  (setq out nil)
  (if lzp:*panelbutton* (setq out (list (lzp:panel-spec))))
  (if (lzp:suite-wanted-p)
    (setq out (append out (list (lzp:suite-spec)))))
  out)

;; Every button this file knows how to draw, wanted here or not.  What
;; is NOT wanted still matters: AutoCAD keeps toolbars in the CUI
;; between sessions, so one put up by another build is still on screen
;; when this one loads.
(defun lzp:tb-all ()
  (list (lzp:panel-spec) (lzp:suite-spec)))

(defun lzp:wanted-name-p (name / spec found)
  (foreach spec (lzp:tb-specs)
    (if (= (lzp:tb-name spec) name) (setq found T)))
  found)

(defun lzp:toolbar-find (name / mgs n i tbs m j tb found)
  (setq mgs (vla-get-menugroups (vlax-get-acad-object)))
  (setq n (vla-get-count mgs)
        i 0)
  (while (and (< i n) (not found))
    (setq tbs (vla-get-toolbars (vla-item mgs i)))
    (setq m (vla-get-count tbs)
          j 0)
    (while (and (< j m) (not found))
      (setq tb (vla-item tbs j))
      (if (= (strcase (vla-get-name tb)) (strcase name))
        (setq found tb))
      (setq j (1+ j)))
    (setq i (1+ i)))
  found)

;; Make the toolbar with its one button.  The macro is what a menu
;; button really sends: two Cancels (ASCII 3 -- the COM API takes the
;; raw characters, not the "^C^C" spelling a menu FILE would use) and
;; the command.
;;
;; The button goes in at index 0.  The toolbar was created empty a line
;; earlier, so 1 is past its end -- and if that throws, an empty
;; toolbar called LazPanel is left behind, which lzp:toolbar-find would
;; then hand back for ever while LAZBUTTON reported success and put
;; nothing on screen.  So a toolbar that fails to get its button does
;; not survive the attempt.
(defun lzp:toolbar-make (spec / tbs tb btn)
  (setq tbs (vla-get-toolbars
              (vla-item (vla-get-menugroups (vlax-get-acad-object)) 0)))
  (setq tb (vla-add tbs (lzp:tb-name spec)))
  (setq btn (vl-catch-all-apply
              'vla-addtoolbarbutton
              (list tb 0 (lzp:tb-name spec)
                    (lzp:tb-tip spec)
                    (strcat (chr 3) (chr 3) "_" (lzp:tb-cmd spec) " "))))
  (cond
    ((vl-catch-all-error-p btn)
     (vl-catch-all-apply 'vla-delete (list tb))
     nil)
    (t (list tb btn))))

;; Put the button on screen: reuse the toolbar when one exists -- its
;; position and docking are the user's -- otherwise create it and float
;; it in view.  Either way the icons are rewritten and re-applied, and
;; the toolbar is made visible: a toolbar the user closed is still
;; found by name, and without this it would never come back.
;; Returns the toolbar, or nil when there is none to be had.
(defun lzp:button-init (spec / tb btn pair paths made)
  (cond
    ((setq tb (lzp:toolbar-find (lzp:tb-name spec)))
     (setq btn (vl-catch-all-apply 'vla-item (list tb 0)))
     (if (vl-catch-all-error-p btn) (setq btn nil)))
    ((setq pair (lzp:toolbar-make spec))
     (setq tb (car pair)
           btn (cadr pair)
           made t)))
  (if tb
    (progn
      (if (and btn (setq paths (lzp:write-bmps (lzp:tb-stem spec)
                                               (lzp:tb-16 spec)
                                               (lzp:tb-32 spec))))
        (vl-catch-all-apply 'vla-setbitmaps
                            (list btn (car paths) (cadr paths)))
        ;; one line, not a stack trace: the panel still works without a
        ;; picture, but a blank button should not be a mystery
        (princ "\n[lazpanel] button picture not applied - LAZICON says why."))
      ;; Big buttons before visible: the toolbar resizes to fit its
      ;; button, and doing it the other way round makes it visibly jump.
      ;; nil does not merely SKIP this -- it puts the setting back, or
      ;; "setq it nil and run LAZBUTTON" would be advice that does
      ;; nothing once a session has already been switched over.
      (vl-catch-all-apply 'vla-put-largebuttons
                          (list tb (if lzp:*bigbutton*
                                     :vlax-true :vlax-false)))
      (vl-catch-all-apply 'vla-put-visible (list tb :vlax-true))
      ;; a new one is floated where it can be seen; the second lands
      ;; below the first rather than on top of it
      (if made
        (vl-catch-all-apply
          'vla-float
          (list tb (+ 200 (* 40 (lzp:tb-index spec))) 300 1)))))
  tb)

;; Where SPEC sits in the roster, so two new toolbars do not float onto
;; the same pixel.
(defun lzp:tb-index (spec / i n found)
  (setq i 0 found 0)
  (foreach n (lzp:tb-all)
    (if (= (lzp:tb-name n) (lzp:tb-name spec)) (setq found i))
    (setq i (1+ i)))
  found)

;; Take a button off the strip without destroying it: the toolbar keeps
;; wherever the operator docked or dragged it, and turning the tunable
;; back on and running LAZBUTTON brings it back exactly there.
(defun lzp:button-hide (spec / tb)
  (if (setq tb (lzp:toolbar-find (lzp:tb-name spec)))
    (vl-catch-all-apply 'vla-put-visible (list tb :vlax-false))))

;; Put up the buttons this session should have -- AND take down the ones
;; it should not.
;;
;; The second half is not tidiness.  AutoCAD keeps toolbars in the CUI,
;; so one put up by another build is still on screen the next time
;; AutoCAD opens: load the drone edition on a machine that has ever seen
;; LAZPASS and, without this, the panel's button would still be sitting
;; there beside the drone's.  "One button" has to mean one button on the
;; machine it actually lands on.  It works both ways round -- load
;; LAZPASS after the edition and the drone button goes away again -- so
;; whichever build was loaded last is the one whose buttons are showing.
;;
;; Returns the toolbars it put up, newest last.
(defun lzp:buttons-init ( / out spec tb)
  (foreach spec (lzp:tb-all)
    (if (lzp:wanted-name-p (lzp:tb-name spec))
      (if (setq tb (lzp:button-init spec))
        (setq out (append out (list tb))))
      (lzp:button-hide spec)))
  out)

;;; -------------------- the dialog run ----------------------------------
;;  No sysvar save, no undo group: the panel changes no settings and
;;  draws nothing -- whatever it launches manages its own.  The error
;;  handler only has the dialog and the temp file to pick up.
;;
;;  This is a helper rather than the command body so that its localized
;;  *error* is OUT OF SCOPE by the time anything is launched: the tool
;;  the user clicked gets whatever error handling it sets up itself,
;;  and a tool that fails reports as itself, not as "LAZPANEL error".

(defun lzp:show ( / *error* f dcl rc pick have n g done out)
  (defun *error* (msg)
    ;; the dialog itself first: unload_dialog alone does not dismiss a
    ;; dialog that is still up, term_dialog does (and is a no-op when
    ;; none is)
    (term_dialog)
    (if (and dcl (>= dcl 0)) (unload_dialog dcl))
    (setq dcl nil)
    (if f (vl-file-delete f))
    (setq f nil lzp:*pick* nil)
    (if (and msg (not (wcmatch (strcase msg)
                               "*BREAK*,*CANCEL*,*QUIT*,*EXIT*")))
      (princ (strcat "\nLAZPANEL error: " msg)))
    (princ))
  ;; NOT reset here: the panel reopens after every tool it launches, and
  ;; coming back to page one in the middle of the screen each time would
  ;; undo the whole point of reopening.  lzp:*page* and lzp:*pos* are
  ;; where the user last had it.
  (setq lzp:*pick* nil)
  (if (not (and lzp:*page* (assoc lzp:*page* lzp:*groups*)))
    (setq lzp:*page* (car (car lzp:*groups*))))
  (setq g lzp:*page*)
  (cond
    ((not (setq f (lzp:write-dcl)))
     (princ "\nLAZPANEL error: could not write the dialog file."))
    ((< (setq dcl (load_dialog f)) 0)
     (princ "\nLAZPANEL error: could not load the dialog file."))
    (t
     ;; The page loop.  One page per group, so the eye lands on a dozen
     ;; buttons rather than all of them; the tab strip is the whole
     ;; roster and never changes width as you move along it.
     (while (not done)
       (cond
         ((not (lzp:newdlg (lzp:dlgname g) dcl))
          (princ "\nLAZPANEL error: could not open the panel.")
          (setq done t))
         (t
          (setq lzp:*page* g
                have (lzp:loaded))
          (set_tile "status"
                    (strcat (itoa (length have)) " of "
                            (itoa (length (lzp:commands)))
                            " tools loaded - greyed are not in this session"))
          (foreach n (lzp:group-commands g)
            (action_tile n
              "(setq lzp:*pick* $key lzp:*pos* (done_dialog 1))")
            (if (not (member n have))
              (mode_tile n 1)))
          ;; the pinned row: same launch, its own keys, greyed the same
          ;; way -- $key would read "pin_POOL", so the name is baked in
          (foreach n lzp:*pins*
            (action_tile (strcat "pin_" n)
              (strcat "(setq lzp:*pick* \"" n
                      "\" lzp:*pos* (done_dialog 1))"))
            (if (not (member n have))
              (mode_tile (strcat "pin_" n) 1)))
          (action_tile "pin_edit" "(setq lzp:*pos* (done_dialog 5))")
          (foreach n lzp:*groups*
            (action_tile (strcat "tab_" (car n))
              (strcat "(setq lzp:*go* \"" (car n)
                      "\" lzp:*pos* (done_dialog 4))")))
          (action_tile "cancel" "(setq lzp:*pos* (done_dialog 0))")
          (setq rc (start_dialog))
          (cond
            ((= rc 4) (setq g lzp:*go* lzp:*page* lzp:*go*))  ; a tab
            ;; the pin editor runs on the same loaded handle, then the
            ;; caller reopens: the Pinned row is generated DCL, so it
            ;; only changes when the file is written again
            ((= rc 5)
             (lzp:pin-edit dcl)
             (setq done t out "*pins*"))
            (t (setq done t
                     out (if (= rc 1) lzp:*pick*)))))))))
  ;; the dialog and its temp file go away BEFORE anything is launched,
  ;; so an interactive command never starts under an open modal dialog
  ;; and the temp file never outlives the panel
  (if (and dcl (>= dcl 0)) (unload_dialog dcl))
  (setq dcl nil)
  (if f (vl-file-delete f))
  (setq f nil lzp:*pick* nil)
  out)

;; Open a page where the user last had the panel.  done_dialog reports
;; the position it closed at and new_dialog takes one back, but only in
;; its four-argument form -- and a build answering done_dialog with
;; something other than a point would poison every reopen, so the shape
;; is checked before it is trusted.
(defun lzp:newdlg (name dcl)
  (if (and lzp:*pos* (listp lzp:*pos*) (= (length lzp:*pos*) 2)
           (numberp (car lzp:*pos*)) (numberp (cadr lzp:*pos*)))
      (new_dialog name dcl "" lzp:*pos*)
      (new_dialog name dcl)))

;;; -------------------- commands ----------------------------------------

;;  THE REOPEN.  A DCL dialog is modal, so the panel still has to close
;;  for a tool to run -- but it no longer has to be reopened by hand.
;;  The loop is the feature: click, the panel closes, the tool runs to
;;  its own end, the panel comes straight back on the page and at the
;;  screen position it was at, with the session re-probed so a tool
;;  loaded meanwhile is no longer greyed.  Close is the way out, and it
;;  is the default button.
;;
;;  A tool cancelled with Escape comes back here exactly as a finished
;;  one does: lzp:launch has already returned by then, so the reopen is
;;  not conditional on the tool having succeeded.  A tool that dies with
;;  a hard error DOES end the loop -- its own *error* runs, the panel
;;  simply does not come back, and LAZPANEL reopens it.  That is the
;;  right way round: the alternative is a panel that keeps bouncing back
;;  in front of someone trying to read the error it just printed.
(defun c:LAZPANEL ( / pick)
  (lzp:pins-read)
  (while (setq pick (lzp:show))
    (if (/= pick "*pins*")
      (lzp:launch pick)))
  (princ))

;; Open the pin editor on its own, without going through the panel.
(defun c:LAZPIN ( / f dcl)
  (lzp:pins-read)
  (cond
    ((not (setq f (lzp:write-dcl)))
     (princ "\nLAZPIN error: could not write the dialog file."))
    ((< (setq dcl (load_dialog f)) 0)
     (princ "\nLAZPIN error: could not load the dialog file."))
    (t
     (lzp:pin-edit dcl)
     (unload_dialog dcl)
     (vl-file-delete f)
     (princ (strcat "\nLAZPANEL: "
                    (itoa (length lzp:*pins*)) " tools pinned."))))
  (princ))

(defun c:LAZBUTTON ( / tbs spec tb any)
  (setq tbs (vl-catch-all-apply 'lzp:buttons-init nil))
  (cond
    ((vl-catch-all-error-p tbs)
     (princ (strcat "\nLAZBUTTON error: " (vl-catch-all-error-message tbs))))
    (tbs
     (foreach tb tbs
       (vl-catch-all-apply 'vla-put-visible (list tb :vlax-true)))
     (setq any nil)
     (foreach spec (lzp:tb-specs)
       (if (lzp:toolbar-find (lzp:tb-name spec))
         (progn
           (setq any T)
           (princ (strcat "\n" (lzp:tb-name spec) " button is on screen -"
                          " drag it anywhere, dock it,"
                          "\n  click it to run " (lzp:tb-cmd spec) ".")))))
     ;; said out loud because it is not a change to THESE toolbars: the
     ;; operator's other toolbars grew too, and they should hear it
     ;; from the command that did it rather than wonder
     (if (and any lzp:*bigbutton*)
       (princ (strcat "\n  Drawn at 32 pixels.  AutoCAD sizes every"
                      " toolbar together, so the rest grew"
                      "\n  with it; (setq lzp:*bigbutton* nil) then"
                      " LAZBUTTON puts them all back.")))
     (cond
       ((lzp:suite-wanted-p))
       ((not (lzp:has "TYLERDRONESUITE"))
        (princ (strcat "\n  TYLERDRONESUITE is not loaded, so it has no"
                       " button of its own -"
                       "\n  APPLOAD tydrn.lsp (or LAZPASS.lsp) and run"
                       " LAZBUTTON again.")))
       (t
        (princ (strcat "\n  TYLERDRONESUITE is on the panel rather than"
                       " on a button of its own:"
                       "\n  this is the whole build, and the build puts"
                       " up one external button."
                       "\n  (setq lzp:*suitebutton* T) then LAZBUTTON"
                       " gives it one anyway.")))))
    (t
     (princ "\nLAZBUTTON: the menu API is unavailable - type LAZPANEL instead.")))
  (princ))

(defun c:LAZICON ( / spec)
  ;; The icon path is best effort and fails silently on purpose: a
  ;; missing picture must never stop the panel working.  Silence is the
  ;; right default and a poor answer to "why is my button blank", so
  ;; this walks the same steps out loud -- once per button, because
  ;; they are written separately and either can fail on its own.
  (princ "\nLAZICON: where the button pictures come from.")
  (princ (strcat "\n  support    : "
                 (cond ((lzp:support-dir))
                       (t "(could not read the support path)"))))
  (princ (strcat "\n  TEMPPREFIX : "
                 (if (= (type (getvar "TEMPPREFIX")) 'STR)
                     (getvar "TEMPPREFIX") "(not a string)")))
  (foreach spec (lzp:tb-specs) (lzp:icon-report spec))
  (if (not (lzp:suite-wanted-p))
    (princ (strcat "\n\n  TYLERDRONESUITE has no button here, so no"
                   " picture is drawn for it."
                   "\n  LAZBUTTON says which of the two reasons it is.")))
  (princ))

;; One button's picture, start to finish.
(defun lzp:icon-report (spec / paths tb btn r w)
  (princ (strcat "\n\n  [" (lzp:tb-name spec) "] -> " (lzp:tb-cmd spec)))
  (setq paths (lzp:write-bmps (lzp:tb-stem spec)
                              (lzp:tb-16 spec) (lzp:tb-32 spec)))
  (cond
    (paths
     (princ (strcat "\n  written to : "
                    (if lzp:*icondir* lzp:*icondir* "?")))
     (princ (strcat "\n  route      : "
                    (if lzp:*iconroute* lzp:*iconroute* "?")
                    "  (" (if lzp:*icontype* lzp:*icontype* "?") ")"))
     (princ (strcat "\n  handed on  : " (car paths)
                    (if (= lzp:*iconref* "name")
                        "  (a name the support path resolves)"
                        "  (a full path - the fallback)")))
     ;; the CUI's own test, run here: a bitmap is resolved by findfile
     ;; along the support path, and a name findfile cannot resolve is
     ;; exactly the "?" placeholder on the button
     (princ (strcat "\n  findfile   : "
                    (cond ((findfile (car paths)))
                          (t "CANNOT RESOLVE - this is the ? placeholder"))))
     (cond
       ((not (setq tb (vl-catch-all-apply 'lzp:toolbar-find
                                          (list (lzp:tb-name spec)))))
        (princ "\n  toolbar    : not on screen - type LAZBUTTON first."))
       ((vl-catch-all-error-p tb)
        (princ (strcat "\n  toolbar    : " (vl-catch-all-error-message tb))))
       (t
        (setq btn (vl-catch-all-apply 'vla-item (list tb 0)))
        (cond
          ((vl-catch-all-error-p btn)
           (princ (strcat "\n  button     : "
                          (vl-catch-all-error-message btn))))
          (t
           (setq r (vl-catch-all-apply
                     'vla-setbitmaps
                     (list btn (car paths) (cadr paths))))
           (princ (strcat "\n  SetBitmaps : "
                          (if (vl-catch-all-error-p r)
                              (vl-catch-all-error-message r)
                              "accepted - the button should show it now"))))))))
    (t
     ;; the failure branch has to say as much as the success one, or
     ;; the next report leaves the same two questions open: which route
     ;; produced the array, and which COM call refused it
     (princ (strcat "\n  array      : "
                    (if lzp:*icontype* lzp:*icontype* "none was made")))
     (princ (strcat "\n  died at    : "
                    (if lzp:*iconstep* lzp:*iconstep* "an unnamed step")))
     ;; the MSXML route failing silently is what cost two rounds of
     ;; this; every ProgID now says what it said
     (if lzp:*msxmlwhy*
       (progn
         (princ "\n  MSXML      : every version refused it --")
         (foreach w (reverse lzp:*msxmlwhy*)
           (princ (strcat "\n               " w))))
       (princ "\n  MSXML      : carried it, so the array is not the story"))
     (princ (strcat "\n  written    : NO - "
                    (if lzp:*iconerr* lzp:*iconerr* "no reason recorded")))))
  (princ))

(defun c:LAZPANELVER ()
  (princ (strcat "\nLAZPANEL " *lazpanel-version* " (LAZPANEL.lsp) - "
                 (itoa (length (lzp:commands))) " tools on the panel across "
                 (itoa (length lzp:*groups*)) " pages, "
                 (itoa (length lzp:*pins*)) " pinned."))
  (princ))

;; Put the button up as the file loads, quietly: in a session where
;; the COM menu API is missing the panel still loads and LAZPANEL
;; still runs -- the button is a convenience, never a gate.
(vl-catch-all-apply 'lzp:buttons-init nil)
(vl-catch-all-apply 'lzp:pins-read nil)

(princ (strcat "\nLAZPANEL " *lazpanel-version*
               " loaded.  LAZPANEL opens the panel;"
               " LAZBUTTON puts its button on screen;"
               " LAZPIN edits the pinned row."))
(princ)


;;; ======================================================================
;;; -------------------- what actually arrived ---------------------------
(setq lazpass:*want* '(
  "CALVER" "POOL" "POOLCOVER" "POOLVER" "POOLDEMO" "TUTORIALPOOL"
  "SPA" "SPAVER" "TUTORIALSPA" "OASIS" "OASISVER" "ABCDEF"
  "ABCDEFVER" "ABFIND" "ABMOVE" "ABFINDVER" "ALTABCDEF" "ABHD"
  "ABHDCOVER" "ADAB" "TUTORIALABHD" "TUTORIALADAB" "ABCURCHECK" "ABCURCHECKSCAN"
  "ABCURCHECKRESCUE" "ABCURCHECKVER" "CABHDVER" "CABHD" "AUTOBEAD" "AUTOBEADVER"
  "TUTORIALAUTOBEAD" "AUTODIM" "STAIRDIM" "FLOORDIM" "AUTODIMSIDEPOV" "BPCALLOUT"
  "CCPRECHECK" "CDCALLOUT" "CDCREATE" "CDCREATEVER" "CHECK" "DIMARCCHECK"
  "CONSTELLATION" "CONSTELLATIONVER" "CORNERSTP" "TUTORIALCORNERSTP" "HEMISTEP" "TUTORIALHEMISTEP"
  "NORMIESTEP" "TUTORIALNORMIESTEP" "LAZSTEP" "LAZSTEPVER" "COVERCHECKRESCUE" "COVERCHECK"
  "COVERSCAN" "LITECOVERSCAN" "TUTORIALCOVERCHECK" "TUTORIALCOVERCHECKCLEAN" "COVERCHECKVER" "COVERCHECKVERSION"
  "CUSTBLOCK" "CUSTBLOCKVER" "DIMCHECKVER" "DIMCHECKRESCUE" "DIMCHECK" "DIMSCAN"
  "TUTORIALDIMCHECK" "TUTORIALDIMSCAN" "DIMCONTEND" "DCE" "DDFIX" "DDSET"
  "DDCAL" "DDINFO" "DDALT" "DDGPS" "DDELEV" "DDTEST"
  "FITABHDVER" "FITABHD" "FITABHDCOVER" "LHD" "LINCHECK" "LINFINCHECKVER"
  "LINFINCHECKRESCUE" "LINFINCHECK" "LINFINSCAN" "LITELINFINSCAN" "TUTORIALLINFINCHECK" "TUTORIALLINFINSCAN"
  "LINTXTCHK" "PADDLE" "TUTORIALPADDLE" "PERPPTS" "CPERPPTS" "TUTORIALPERPPTS"
  "TUTORIALCPERPPTS" "SMARTFILLET" "SMARTFILLETVER" "SPACHECKVER" "SPACHECKSCAN" "LITESPACHECKSCAN"
  "SPACHECK" "SPACHECKRESCUE" "TUTORIALSPACHECK" "STOCKLIST" "STOCKCOVER-CFG" "STOCKCOVER"
  "DRONE" "TYDRN" "TYLERDRONESUITE" "WCALST" "XFTCONV" "XFTCONV-SETUP"
  "XYPLOT" "XYPLOTVER" "LAZSPA" "LAZSPAVER" "LAZASCII" "LAZTXT"
  "LAZFORM" "LAZFORMCOVER" "LAZFORMVER" "LAZPANEL" "LAZPIN" "LAZBUTTON"
  "LAZICON" "LAZPANELVER"
))

(setq lazpass:*missing* nil)
(foreach n lazpass:*want*
  (if (not (eval (read (strcat "C:" n))))
    (setq lazpass:*missing* (cons n lazpass:*missing*))))

(if lazpass:*missing*
  (progn
    (princ (strcat "\nLAZPASS: only " (itoa (- (length lazpass:*want*)
                                             (length lazpass:*missing*)))
                   " of " (itoa (length lazpass:*want*))
                   " commands loaded -- this build is incomplete."))
    (princ "\nLAZPASS: missing:")
    (foreach n (reverse lazpass:*missing*)
      (princ (strcat " " n))))
  (princ (strcat "\nLAZPASS: calofin v3.0 loaded - "
                 (itoa (length lazpass:*want*))
                 " commands in one session.")))
(princ)

;;; ======================================================================
;;; >>> the edition's own footer
;;; ======================================================================

;; BOTH buttons, and both said outright rather than deduced.
;;
;; lzp:*suitebutton* AUTO would work the second one out by reading
;; cal:*build-loading*, which the bundle above has just raised and
;; nothing ever lowers -- so AUTO would conclude it is inside
;; LAZPASS and decline the very button this file exists for.  That
;; is not a bug in AUTO: AUTO is right for a plain build.  It is
;; the wrong question to ask here, because this edition already
;; knows the answer.
(setq lzp:*panelbutton* T)
(setq lzp:*suitebutton* T)
(vl-catch-all-apply 'lzp:buttons-init nil)

;; And say how it went.  A load that quietly leaves nothing on
;; screen is what made the last one of these take a bug report.
(if (and (vl-catch-all-apply 'lzp:toolbar-find (list lzp:*tbname*))
         (vl-catch-all-apply 'lzp:toolbar-find (list lzp:*tbsuite*)))
  (princ "\nTYLERDRONE: both buttons are on screen - the hexagon opens the panel,")
  (princ "\nTYLERDRONE: the buttons could not be put up - the AutoCAD menu API is")
)
(if (and (vl-catch-all-apply 'lzp:toolbar-find (list lzp:*tbname*))
         (vl-catch-all-apply 'lzp:toolbar-find (list lzp:*tbsuite*)))
  (princ "\nthe triangle runs TYLERDRONESUITE.")
  (princ "\nunavailable here.  Type TYLERDRONESUITE instead, or LAZBUTTON to retry.")
)
(princ)
