;;; ===================================================================
;;; ABHD.LSP  --  Fit a pool perimeter through surveyed points
;;; -------------------------------------------------------------------
;;; For AutoCAD 2018 and later (plain AutoLISP, no external libraries).
;;;
;;; Commands:  ABHD - fit the perimeter, then optionally the bottom
;;;            SIMPABHD - the same fit with NONE of ABHD's three
;;;                   numbers asked: five ready-made perimeters are
;;;                   drawn and you keep the one that looks like the
;;;                   pool (see the SIMPABHD section further down)
;;;            ADAB - the pool bottom on its own, over an existing
;;;                   perimeter (select the closed polyline or its
;;;                   exploded lines/arcs; the survey points sitting
;;;                   on it are found automatically)
;;;
;;; The user window-selects an area containing:
;;;   * On layer "POOL"   : (optional) a closed perimeter drawn as ONE
;;;                         closed polyline OR an exploded set of
;;;                         LINEs/ARCs.
;;;   * On layer "POINTS" : POINT entities surveyed on the real pool
;;;                         edge.
;;;
;;; TWO MODES, chosen automatically from the selection:
;;;   * GUIDED  - the selection contains POOL geometry: the drawn
;;;               shape is used as the guide and re-fitted through the
;;;               points (described below).
;;;   * POINTS-ONLY - the selection contains no POOL geometry: the
;;;               program orders the points into a closed loop by
;;;               itself (nearest-neighbour tour + 2-opt uncrossing)
;;;               and covers them with as FEW long, overarching ARCS
;;;               as possible - each arc is grown to take in as many
;;;               consecutive points as it can hold.  No straight
;;;               lines are drawn (organic shapes have none); the only
;;;               exception is a stretch between two sharp corners
;;;               with no points in between, where an arc would be
;;;               pure invention.
;;;
;;; ON THE POINTS FIRST: every arc endpoint sits ON a survey point,
;;; and each arc is chosen so its MIDDLE passes exactly through one of
;;; its interior points too (a true 3-point arc) whenever such an arc
;;; holds the span.  Arcs that float between the points are a last
;;; resort and must cover at least 2 more points to be chosen - they
;;; should be the rare exception (roughly 1 arc in 10), not the rule.
;;;
;;; NEAR-TANGENT SMOOTHNESS: at every joint the new arc must start
;;; within *PF-TANG-TOL* (8 degrees) of the previous arc's end
;;; tangent - close enough to look smooth, loose enough that the
;;; points stay in charge.  Sharp corners (over *PF-CORNER-ANG*) stay
;;; free kinks; the closing seam is held to the same window (the fit
;;; is re-run once with a seeded start tangent when the seam comes
;;; out worse).
;;;
;;; NICE RADII: arc radii are snapped to friendly increments before a
;;; free ("weird") number is accepted - whole feet first, then half
;;; feet, then whole inches (*PF-NICE-RADII*, drawing units = inches).
;;; The points outrank pretty radii: a snap may move covered points at
;;; most *PF-SNAP-EPS* beyond where they already sat and may never
;;; pull an arc off its anchor point; endpoints never move.
;;;
;;; THE MISS ALLOWANCE: the perimeter no longer has to thread every
;;; point exactly.  A share of the points - asked per run, standard
;;; *PF-MISS-PCT* (20%), rounded UP to the nearest whole point - may
;;; sit off the result by up to the max distance (default 1 unit = one
;;; inch, capped at *PF-TOL-MAX*); every other point stays on it
;;; (within *PF-ON-EPS*).  That slack is spent where it buys the most:
;;; longer arcs, fewer curves, nicer radii.  A fifth of the points an
;;; inch off is the recommendation because it is what an AB survey of
;;; a built shell looks like - the three questions at steps 1 to 3 now
;;; offer one coherent answer rather than three separate ones.
;;;
;;; MOVED POINTS ARE NOT SURVEY POINTS: a number carrying the letter
;;; *PF-MOVED-MARK* ("m") is out of the fit entirely.  ABFIND writes
;;; "17m" when it copies Pt.17 to a position it worked out from two
;;; tape readings off a pair of good points - the original was a bad
;;; shot, and the copy is where that point SHOULD be, not where
;;; anybody stood.  Holding a perimeter to a deduction dresses it up
;;; as evidence: the fit bends to meet a position no one measured,
;;; and the report then claims it held a point that was never there.
;;; So a moved point is dropped as the selection is read, before the
;;; point list exists - not ordered into the loop, not fitted, not
;;; held, not counted against the miss allowance, and never ringed or
;;; listed as one the line missed.  The original it came from is
;;; still in the survey and still fitted; only the deduced twin is
;;; out.  The command says how many it left out, so a survey that
;;; comes up short is explained rather than mysterious.  Matched
;;; case-insensitively anywhere in the number, so "17m", "17M" and
;;; "17m2" are all out.
;;;
;;; DECLARED STRAIGHT WALLS: the user may declare dead-straight walls
;;; up front by naming their two end points; each is marked with a
;;; dashed line on *PF-WALL-LAYER* and comes out of the points-built
;;; fit as a straight LINE between exactly those two survey points -
;;; arcs never swallow or cross a declared wall.
;;;
;;; LEAVING POINTS OUT: with the whole survey selected, step 8 asks
;;; which of those points the fit should not chase - the shot on the
;;; coping, the double-shot, the rod held crooked - and a Redo asks
;;; again.  Each one named gets a dashed ring and leaves the fit, the
;;; stats and the miss allowance alike; naming a ringed one again puts
;;; it back, its duplicate shots with it.  Nothing is thrown away: a
;;; point left out is still MEASURED against the line that is kept,
;;; ringed beside the points the fit missed and listed with how far
;;; off it landed, because that number is what says whether leaving it
;;; out was right.  Under the list goes one line naming every bad
;;; point - "- Pt.12, Pt.15 and Pt.20 are bad." - in BPCALLOUT's
;;; wording, so a sheet reads the same sentence whichever tool wrote
;;; it.
;;;
;;; NAMING A POINT: every question about a survey point - a wall end,
;;; a corner, a held point, a break end, a slope waypoint, a point to
;;; omit - is asked PERPMARK's way, because it is a question about a
;;; point the drawing already holds and not about a place: click the
;;; point, or type its number ("17", "Pt.17", "pt 17", "#17" and "017"
;;; all name the same one).  A click has to land within *PF-SNAP* of
;;; a point to pick it; a click on nothing, a number nothing carries
;;; and a number two points share are re-asked where they stand,
;;; never snapped to whatever was nearest.  A wall, corner or hold is
;;; declared before the points are selected, so it is matched to the
;;; selection afterwards by the point's own identity - and one
;;; declared on a point that was not selected is named and dropped,
;;; not snapped onto some other point.
;;;
;;; HELD POINTS: the user may also declare points that must be held
;;; ABSOLUTELY - control shots, tie-ins, anything surveyed as an
;;; exact position.  A held point is never buried inside a span, so
;;; every span ends ON it and the fitted line passes through it
;;; exactly, in every candidate; it costs nothing from the miss
;;; allowance and the tangency window still applies at its joint (it
;;; is not a corner).  In guided mode the drawn shape wins, as with
;;; declared walls - held points steer the points-built fit - and the
;;; report flags any held point the kept fit did not land on.
;;;
;;; THE CURVE CAP: the command also asks for a maximum number of
;;; curves ("None" = unlimited).  When a fit needs more, the whole
;;; loop is refitted with a progressively relaxed tolerance until the
;;; cap holds - merging arcs would break their tangency, so the chain
;;; is rebuilt instead and stays smooth.  The cap wins over the
;;; tolerance; whatever error it forces is shown in the hit report.
;;; The cap binds in EVERY mode: a guided run whose drawn perimeter
;;; needs more curves falls back to fitting from the points (the
;;; drawn shape still orders them), and an unreachably small cap
;;; returns the fewest-curves fit found - never the full-size one.
;;;
;;; THE THREE CANDIDATES: how much curve to spend on how much accuracy
;;; is a judgement, not a setting, so all three answers are drawn and
;;; the user points at one (*PF-COMPARE*).  Fit 1 is the accurate end:
;;; it fits to *PF-TIGHT-TOL*, writes off no point at all, and obeys
;;; neither the typed distance nor the curve cap - the most curves for
;;; the least error there is.  Fit 2 is the settings exactly as typed,
;;; cap included.  Fit 3 is the economical end: the same typed
;;; distance, but with the miss allowance and its per-span fair share
;;; lifted, so arcs run as long as that distance allows - the fewest
;;; curves that still hold it.  All three are then MEASURED against
;;; the typed distance, so the table compares like for like.
;;;
;;; The command rebuilds the perimeter as a single closed LWPOLYLINE
;;; (lines + arcs only, no splines); the candidates preview on layer
;;; "POOL-FIT" and the kept one moves onto the POOL layer:
;;;   * Every polyline vertex is snapped to the nearest surveyed point
;;;     within the tolerance (default 1 unit = 1 inch), so corners land
;;;     exactly on points whenever one is close enough.
;;;   * Every curved (arc/bulge) segment is re-fitted so that the arc
;;;     passes through the surveyed points lying along it.  A single
;;;     replacement arc is tried first (the best of the exact 3-point
;;;     arcs through the two snapped endpoints and the points, plus
;;;     their average), with its radius snapped to a nice increment
;;;     when possible; if it keeps every point within the tolerance
;;;     and the miss allowance can absorb the off ones, that ONE arc
;;;     is kept.  Only when that fails is the segment SUBDIVIDED into
;;;     a tangent-continuous chain of arcs through every point.
;;;   * Straight segments the user drew are trusted and kept straight
;;;     (only their endpoints snap to points); where the user found a
;;;     straight wall, the result has a straight wall.
;;;   * A point that turns more than *PF-CORNER-ANG* (45 deg) is a
;;;     sharp corner: it can start or end a span but is never buried
;;;     inside one, so polygonal shapes keep their corners as lines.
;;; Everything is fitted on the 2D plane - Z coordinates are ignored.
;;; Every segment shares its endpoints with its neighbours, so the
;;; result stays closed.
;;;
;;; A hit report is printed: how many points the new perimeter passes
;;; through exactly, how many are within tolerance, how many missed.
;;;
;;; THE POOL BOTTOM: once a perimeter is kept, the command offers to
;;; draw the floor too (Enter = No).  The user names the two ends of
;;; the SHALLOW BREAK and the DEEP BREAK; the hopper - the flat
;;; deep-end floor - lies beyond the deep break, away from the
;;; shallow.  Its back is found automatically (the survey point
;;; nearest a perpendicular ray cast from the middle of the deep
;;; break), and three offsets - asked by point number, one at each
;;; deep break point, one at the back - pull the hopper in from the
;;; perimeter, blending gradually where they differ.  Slope lines
;;; join the hopper's ends to the shallow break points - each side is
;;; asked whether its line runs STRAIGHT, GUIDED (following the
;;; perimeter's curve, the offset easing to nothing at the shallow
;;; break), or through POINTS the user names along that side, each
;;; with its own offset measured square off the wall - the line still
;;; runs guided between them.  Every prompt in the flow after the
;;; first offers Back ([Back] at the picks and choices, B typed at
;;; the offsets; Undo works too), re-opening the previous question -
;;; and in the POINTS loop, Back un-picks the last waypoint.  The
;;; hopper and the guided slopes are merged into as FEW long arcs as
;;; hold their shape (within *PF-BOTTOM-FIT*) - curves, not facets,
;;; and not many of them.
;;; Everything - the bottom's lines, the dimensions, and the kept
;;; perimeter itself - ends up on *PF-POOL-LAYER* (the deep break
;;; stubs dashed).
;;; ===================================================================

;;; -------------------- tunables ----------------------------------------
;;;  Every knob the tool has, in one place (STANDARDS.md section 5).
;;;  Nothing below the "end of tunables" rule is meant to be edited to
;;;  change how ABHD behaves: if a number in the body still reads like a
;;;  setting, it belongs up here.  Three groups, in the order a drafter
;;;  is likely to need them:
;;;
;;;    1. DRAWING SETUP  - what the tool reads and where it writes: the
;;;       layer names and colours, the point block and its tag, the
;;;       linetypes, the dimension styles, and how the candidate pick
;;;       and its on-screen labels look.
;;;    2. FITTER TUNING  - the distances, shares, angles and gains that
;;;       decide how the perimeter and the bottom come out.  Calibrated
;;;       against a real hand-drawn as-built trace; each entry says what
;;;       moving it does.  The same span fitter lives in LHD (*LH-*) and
;;;       CABHD (*CAB-*) word for word and the tests hold the three
;;;       equal, so a fitter knob changed here is changed there too.
;;;    3. GUARDS  - limits that keep the maths finite and the searches
;;;       bounded.  Named so each is defined once and can be read, not
;;;       because it wants changing.
;;;
;;;  Every one is a literal nothing re-assigns.  What a RUN writes -
;;;  the distance, the curve cap and the hopper offset it remembers, and
;;;  the cover-mode flag - is state, not a setting, and sits in its own
;;;  section under the rule below rather than in here advertising an
;;;  initial value as something to tune.
;;;
;;;  Drawing units are inches throughout.  The practice pool
;;;  TUTORIALABHD draws is fixed on purpose and has no knobs.
;;;
;;;  ONE DIVERGENCE from the section 5 spelling, deliberate: these are
;;;  named *PF-NAME* rather than pf:*name*.  The spelling predates the
;;;  rule, the README quotes it, ABCURCHECK reads two of them out of
;;;  this file by name, and LHD and CABHD carry the fitter half under
;;;  *LH-* and *CAB-* with their suites comparing it code for code - so
;;;  renaming is a coordinated pass over three tools and four suites,
;;;  which is also why abhd is not yet in tests/test_tunables.py's
;;;  FILES (its reader wants the namespaced spelling).
;;; ----------------------------------------------------------------------

;; ---- 1. DRAWING SETUP ----------------------------------------------
;; Layers.  Each is created if missing, in the colour beside it; one
;; that already exists keeps its own colour but is thawed, unlocked and
;; switched on so a run is never invisible.  Colours are AutoCAD colour
;; indices (1 red, 2 yellow, 3 green, 4 cyan, 7 white, 8 grey).
(setq *PF-POOL-LAYER*   "POOL")     ; layer holding the drawn perimeter
                                    ; guide, and where the kept fit,
                                    ; the bottom and its dims end up
(setq *PF-POOL-COLOUR*  4)          ; ...its colour when ABHD creates it
(setq *PF-POINT-LAYER*  "POINTS")   ; layer holding the survey points
                                    ; as plain POINT entities (ab_pt
                                    ; blocks count on ANY layer)
(setq *PF-POINT-COLOUR* 7)          ; ...its colour; only the tutorial
                                    ; ever creates it, for the practice
                                    ; survey
(setq *PF-POINT-BLOCK*  "ab_pt")    ; block name whose INSERTs mark survey
                                    ; points; the block's insertion point
                                    ; is taken as the point location
(setq *PF-PT-TAG*       "number")   ; attribute tag on the point block
                                    ; holding the surveyed point number,
                                    ; used to label it as "Pt.17"; a
                                    ; block without it is numbered in
                                    ; selection order
(setq *PF-MOVED-MARK*   "M")        ; a point number carrying this letter
                                    ; is a MOVED point - ABFIND writes
                                    ; "17m" when it copies Pt.17 to a
                                    ; position worked out from two tape
                                    ; readings (abf:*moved-suffix*).
                                    ; That position is a deduction, not
                                    ; a shot: nobody stood there.  So a
                                    ; number with this letter in it is
                                    ; left out of the fit ENTIRELY - not
                                    ; ordered into the loop, not fitted,
                                    ; not held, not counted against the
                                    ; miss allowance and never reported
                                    ; as a point the line failed to
                                    ; hold.  Matched case-insensitively
                                    ; anywhere in the number
(setq *PF-OUT-LAYER*    "POOL-FIT") ; layer the three candidate fits
                                    ; preview on, with their labels
(setq *PF-OUT-COLOUR*   3)          ; ...its colour when ABHD creates it
                                    ; (each candidate carries its own,
                                    ; see *PF-COMPARE* below)
(setq *PF-MISS-LAYER*   "FGStep")   ; layer the "could not hold this
                                    ; point" circles and their list go
                                    ; on.  This may well be a layer you
                                    ; already use, so ABHD stamps the
                                    ; objects it makes and only ever
                                    ; erases its own (see pf:tag-mine)
(setq *PF-MISS-COLOUR*  1)          ; ...its colour when ABHD creates it
(setq *PF-MISS-RADIUS*  4.0)        ; radius of those circles (4 inches);
                                    ; also the ring on a declared corner
                                    ; and on a point omitted at a Redo
(setq *PF-HOLD-RADIUS*  (* 0.5 *PF-MISS-RADIUS*)) ; the ring on a HELD
                                    ; point - half size, so it reads
                                    ; apart from a corner ring.  Worked
                                    ; out from the line above as the
                                    ; file loads
(setq *PF-BAD-PREFIX*   "- ")       ; the one line under the list that
                                    ; NAMES the bad points leads with
                                    ; this, the way ABFIND leads every
                                    ; note it writes, so a sheet's notes
                                    ; read as one column
(setq *PF-BAD-ONE*      " is bad.") ; ...its tail when ONE point is bad:
                                    ; "- Pt.12 is bad."
(setq *PF-BAD-MANY*     " are bad.") ; ...and when two or more are:
                                    ; "- Pt.12, Pt.15 and Pt.20 are
                                    ; bad."  BPCALLOUT's wording, so the
                                    ; sentence reads the same whichever
                                    ; tool wrote it
(setq *PF-OMIT-TAIL*    "   (left out)") ; what marks a LEFT-OUT point's
                                    ; row apart from a point the fit
                                    ; tried to hold and missed.  Both
                                    ; are bad and both are ringed; only
                                    ; one of them was the fitter's doing
(setq *PF-WALL-LAYER*   "POOL-WALLS"); layer the dashed markers for
                                    ; declared straight walls, corners
                                    ; and held points go on (scaffolding:
                                    ; swept when the command ends)
(setq *PF-WALL-COLOUR*  8)          ; ...its colour when ABHD creates it
(setq *PF-BOTTOM-LAYER* "POOL-BOTTOM") ; legacy: where earlier versions
                                    ; of this command put the bottom
                                    ; geometry and dims.  Everything
                                    ; goes on *PF-POOL-LAYER* now, but
                                    ; ADAB still skips this layer when
                                    ; reading a selection
(setq *PF-MARK-LTYPE*   "DASHED")   ; linetype of the wall markers and
                                    ; the corner / held / omitted rings.
                                    ; A linetype the drawing already has
                                    ; is used as it is; a name it lacks
                                    ; is created with a plain dashed
                                    ; pattern (pf:ensure-dashed, dashes
                                    ; sized for an inch drawing)
(setq *PF-STUB-LTYPE*   "DASHED2")  ; linetype of the two deep-break
                                    ; stubs (wall to hopper corner);
                                    ; created the same way, with
                                    ; half-size dashes
(setq *PF-DIM-FTIN* "SIDE DIMENSION") ; dimension style stamped on the
                                    ; offset dims NOT anchored to a
                                    ; break point (hopper back, slope
                                    ; waypoints) when the offset was
                                    ; typed as feet-and-inches (3'6)
(setq *PF-DIM-IN* "STANDARD INCHES") ; same dims when the offset was
                                    ; typed in plain inches (42).
                                    ; Either style missing from the
                                    ; drawing falls back to the
                                    ; current style, with a note
(setq *PF-DIM-OFF* 12.0)            ; the deep-end dimension string
                                    ; (wall-to-hopper, hopper width,
                                    ; hopper-to-wall) sits this far off
                                    ; the deep break line (a foot), on
                                    ; the shallow-end side
(setq *PF-LABEL-FRAC*   20.0)       ; the on-screen candidate labels
                                    ; ("1", "2", "3" with their figures)
                                    ; and the list of unheld points are
                                    ; sized to the survey: text height =
                                    ; the shape's larger extent divided
                                    ; by this.  Smaller = bigger text
(setq *PF-DEFAULT-FIT*  "2")        ; the candidate Enter keeps at the
                                    ; choose prompt - "1" (tight), "2"
                                    ; (as asked) or "3" (few).  The
                                    ; standard is "2" (STANDARDS
                                    ; section 3, multi-fit pick).
                                    ; Anything else would leave Enter
                                    ; keeping no fit at all, silently,
                                    ; so a slip here is corrected on
                                    ; the next line rather than found
                                    ; in the drawing
(if (not (member *PF-DEFAULT-FIT* '("1" "2" "3")))
  (setq *PF-DEFAULT-FIT* "2"))
(setq *PF-SLOW-NOTE*    150)        ; above this many distinct points
                                    ; the command says the ordering and
                                    ; fitting will take a little while
(setq *PF-COMPARE*                  ; the three candidate fits offered:
  '(("tight" 1 "red"    "most curves - least error")
    ("asked" 2 "yellow" "as asked")
    ("few"   4 "cyan"   "fewest curves - still within the distance")))
                                    ; (mode, AutoCAD colour, colour name,
                                    ; description).  The three ask three
                                    ; different questions of the same
                                    ; points, so what is being chosen is
                                    ; an aim, not a tolerance:
                                    ;   "tight" - accuracy above all: it
                                    ;     fits to *PF-TIGHT-TOL*, lets no
                                    ;     point miss and ignores both the
                                    ;     distance typed at step 1 and
                                    ;     the curve cap, so it draws the
                                    ;     most curves and the least error
                                    ;   "asked" - the settings exactly as
                                    ;     typed, curve cap and all
                                    ;   "few" - the fewest curves that
                                    ;     still hold every point within
                                    ;     the distance typed: the same
                                    ;     distance, but with the miss
                                    ;     allowance lifted so arcs run as
                                    ;     long as that distance permits
                                    ; Colours and wording are yours to
                                    ; edit; the three mode names are not
(setq *PF-SIMP-TOL*     1.0)        ; the distance SIMPABHD fits and
                                    ; measures to.  SIMPABHD asks no
                                    ; numbers at all, so this is the one
                                    ; it uses in place of step 1 - and
                                    ; the one the table's columns are
                                    ; read against, exactly as the typed
                                    ; distance is in ABHD's
(setq *PF-SIMP-COMPARE*             ; the five candidates SIMPABHD draws
  '(("tight" 1 "red"     "most curves - least error"                nil nil  nil)
    ("pct"   2 "yellow"  "10% off by 1in, a third as many curves"   0.10 1.0  3.0)
    ("hold"  3 "green"   "all but the 3 worst held, half as many"   3    1.0  2.0)
    ("pct"   4 "cyan"    "20% off by 1/2in, a third as many curves" 0.20 0.5  3.0)
    ("few"   6 "magenta" "fewest curves - still within the distance" nil nil  nil)))
                                    ; (kind, AutoCAD colour, colour name,
                                    ; description, share, distance,
                                    ; points-per-curve).  ABHD asks three
                                    ; numbers and draws the two ends of
                                    ; the trade around them; SIMPABHD
                                    ; asks none and draws the same two
                                    ; ends around three ready-made
                                    ; answers, so what is chosen is a
                                    ; picture rather than a guess at
                                    ; three settings.  Rows 1 and 5 are
                                    ; ABHD's own "tight" and "few" - the
                                    ; least error there is and the fewest
                                    ; curves that still hold the distance
                                    ; - and take no share, distance or
                                    ; cap of their own: capping either
                                    ; would be asking for the most curves,
                                    ; or the fewest, and then overruling
                                    ; the answer.  The three between them
                                    ; are read as:
                                    ;   "pct"  - this share of the points
                                    ;     may sit off the line, by up to
                                    ;     this distance, with the curve
                                    ;     cap set to the point count over
                                    ;     the last number, rounded to the
                                    ;     nearest whole curve
                                    ;   "hold" - every point is held but
                                    ;     this many: the share column is a
                                    ;     COUNT, not a fraction, and the
                                    ;     ones given up are the worst the
                                    ;     fitter meets
                                    ; Colours and wording are yours to
                                    ; edit; the four kind names are not
(setq *PF-SIMP-DEFAULT-FIT* "2")    ; the candidate Enter keeps at
                                    ; SIMPABHD's choose prompt.  "2" is
                                    ; the middle of the road - a tenth of
                                    ; the points an inch off, a third as
                                    ; many curves as points - and the
                                    ; nearest of the five to what ABHD
                                    ; itself recommends
(if (not (member *PF-SIMP-DEFAULT-FIT* '("1" "2" "3" "4" "5")))
  (setq *PF-SIMP-DEFAULT-FIT* "2"))

;; ---- 2. FITTER TUNING ----------------------------------------------
(setq *PF-TOL-MAX*      2.0)        ; hard ceiling on the max-distance
                                    ; prompt (2 inches): further than
                                    ; that and the line is no longer a
                                    ; trace of the points
(setq *PF-MISS-PCT*     0.20)       ; share of the points, as a FRACTION
                                    ; from 0 to 1 (0.20 is 20%; anything
                                    ; else is offered as 0.20), rounded
                                    ; UP to a whole point, that may sit
                                    ; off the result by up to the
                                    ; tolerance (an inch by default) -
                                    ; this slack is what buys longer
                                    ; spans and fewer curves.  Step 2
                                    ; offers it; the answer is per run,
                                    ; on purpose.  A fifth of an AB
                                    ; survey off by an inch is what the
                                    ; built shell actually does: at 15%
                                    ; the fitter ran out of allowance
                                    ; early in the loop and paid for the
                                    ; rest of it in short arcs
(setq *PF-ARC-DIV*      3.0)        ; the RECOMMENDED curve cap: one
                                    ; curve per this many survey points,
                                    ; rounded to the NEAREST whole curve
                                    ; and never below 1 (pf:rec-arcs).
                                    ; A third of the points is what a
                                    ; pool edge reads as - long
                                    ; overarching arcs with three or so
                                    ; points under each, rather than one
                                    ; curve per shot.  It is only what
                                    ; Enter offers at step 3: a number
                                    ; typed there wins, and None still
                                    ; lifts the cap entirely
(setq *PF-ON-EPS*       0.25)       ; a point within this of the result
                                    ; counts as ON it; only points off by
                                    ; more than this eat into the miss
                                    ; allowance above.  Calibrated from a
                                    ; hand-drawn reference trace: ~87% of
                                    ; its points sat within a quarter inch
(setq *PF-ON-FRAC*      0.25)       ; ...and that threshold scales with
                                    ; the distance typed: this fraction
                                    ; of it, whichever of the two is the
                                    ; larger.  If 4 inches of error is
                                    ; accepted, a point an inch off is
                                    ; plainly still ON the shape;
                                    ; counting it as a miss would burn
                                    ; the whole allowance on the first
                                    ; span and starve the rest of the
                                    ; loop into single-point stubs
(setq *PF-TIGHT-TOL*    0.01)       ; the "tight" candidate's accuracy
                                    ; target (units) - what it fits to
                                    ; instead of the distance typed at
                                    ; step 1, or that distance when it
                                    ; happens to be tighter still
(setq *PF-FIT-EPS*      0.01)       ; if a single arc misses any of its
                                    ; points by more than this, split it
                                    ; into several arcs that hit exactly
                                    ; (guided mode)
(setq *PF-ANCHOR-EPS*   (* 2.0 *PF-FIT-EPS*)) ; an arc "passes through"
                                    ; an interior survey point when the
                                    ; point sits within this of it -
                                    ; twice the fit epsilon, so a
                                    ; nice-radius snap of a hair still
                                    ; counts as anchored.  Worked out
                                    ; from *PF-FIT-EPS* as the file
                                    ; loads, so edit that one and this
                                    ; follows; set it here to break the
                                    ; tie
(setq *PF-CORNER-ANG*   (/ pi 4.0)) ; a point that turns more than this
                                    ; (45 deg) is a sharp corner: it may
                                    ; start or end a span but never gets
                                    ; buried inside one, so polygonal
                                    ; shapes keep their corners.  Sample
                                    ; real tight curves with at least ~3
                                    ; points per quarter turn to stay
                                    ; under it.
(setq *PF-NICE-RADII* '(12.0 6.0 1.0)) ; preferred arc-radius increments,
                                    ; tried in order: whole feet, half
                                    ; feet, whole inches (drawing units
                                    ; are inches).  A radius is snapped
                                    ; to the first increment whose arc
                                    ; still holds the points; only when
                                    ; none does is the free-fit ("weird")
                                    ; radius kept.
(setq *PF-SNAP-EPS*     0.02)       ; a nice-radius snap may move the
                                    ; covered points at most this far
                                    ; beyond where they already sat, and
                                    ; it may never pull an arc off its
                                    ; anchor point entirely - the points
                                    ; outrank pretty radii
(setq *PF-TANG-TOL* (/ pi 22.5))    ; wiggle room from perfect
                                    ; tangency at each joint between two
                                    ; arcs (8 degrees).  Being ON the
                                    ; points matters more than perfect
                                    ; tangency; this slack is what lets
                                    ; every arc endpoint sit on a survey
                                    ; point and radii stay nice.
                                    ; Calibrated from a hand-drawn
                                    ; reference trace whose joints ran up
                                    ; to 7.9 deg (median 3 deg); tighter
                                    ; values shatter the fit into many
                                    ; short arcs (5 deg is workable,
                                    ; 6 deg and below is not).
(setq *PF-TANG-STEPS* '(1.0 1.25 1.5)) ; when nothing fits inside the
                                    ; tangent window, stretch it by
                                    ; these multiples in turn rather
                                    ; than abandon it; if even the
                                    ; widest finds nothing, a one-point
                                    ; stub takes over, and that
                                    ; continues the previous tangent
                                    ; exactly.  Smoothness is worth
                                    ; more than one extra arc, so keep
                                    ; the last step small: dropping the
                                    ; window outright allowed joints to
                                    ; kink three times the limit.
(setq *PF-ARC-SLACK* (/ pi 3.0))    ; how much further than its own
                                    ; points actually turn one arc may
                                    ; sweep (60 degrees).  An arc is
                                    ; allowed to curve about as much as
                                    ; the run of points it covers
                                    ; curves, and no more - which is
                                    ; what stops a shaky survey coming
                                    ; back as a chain of loops.  A span
                                    ; between two neighbouring points
                                    ; covers no turn at all, so it gets
                                    ; the slack alone: room for a
                                    ; quarter turn sampled only two
                                    ; points to the corner, nowhere
                                    ; near the semicircles this fitter
                                    ; used to draw when a tangent got
                                    ; away from it.
(setq *PF-FLOAT-GAIN*   2)          ; an arc that floats between the
                                    ; points (its middle on no survey
                                    ; point) has to earn its keep: it is
                                    ; taken only when it covers at least
                                    ; this many more points than the
                                    ; longest arc that passes exactly
                                    ; through one.  Whole points; 2
                                    ; keeps floaters about 1 arc in 10
(setq *PF-DROP-PCT*     0.10)       ; share of the points (rounded UP)
                                    ; the fit may give up on entirely:
                                    ; left further off than the max
                                    ; distance, counted as "not held"
                                    ; and ringed in the drawing.  It is
                                    ; spent only where the walk would
                                    ; otherwise shatter into one-point
                                    ; stubs, and only when each point
                                    ; given up buys enough span (see
                                    ; *PF-DROP-GAIN*) - a stray shot is
                                    ; worth less than the shape, but
                                    ; the points at large outrank both.
                                    ; Declared corners, wall points and
                                    ; held points are never given up.
                                    ; The "tight" candidate is granted
                                    ; none of this at all.
(setq *PF-DROP-MULT*    2.0)        ; how far past the max distance a
                                    ; point has to be before the fit
                                    ; may give up on it at all.  This
                                    ; is what separates a bad shot from
                                    ; a feature: a point that misses by
                                    ; a little is still fought for - it
                                    ; stops the span exactly as it
                                    ; always did - and only one plainly
                                    ; off can be written off.  Without
                                    ; it the fit would give up the tip
                                    ; of a sparsely shot pool to save
                                    ; one segment.
(setq *PF-DROP-GAIN*    2)          ; and every point given up must buy
                                    ; at least this many more points of
                                    ; span, or it is held after all.
                                    ; Whole points
(setq *PF-CAP-RELAX*    1.4)        ; when a fit needs more curves than
                                    ; the cap allows, the whole loop is
                                    ; refitted with the distance
                                    ; multiplied by this, again and
                                    ; again, until the cap holds.
                                    ; Nearer 1 = finer steps, more
                                    ; refits, a result closer to the
                                    ; cap; larger = coarser and quicker
(setq *PF-CAP-TRIES*    40)         ; ...and at most this many refits;
                                    ; the fewest-curves result seen is
                                    ; kept when the cap is still not
                                    ; met.  40 steps of 1.4 let the
                                    ; distance grow about 700,000-fold,
                                    ; so a cap unmet by then is
                                    ; genuinely unreachable
(setq *PF-SNAP*         12.0)       ; a CLICK within this of a survey
                                    ; point names that point - at a
                                    ; wall end, a corner, a held point,
                                    ; a break end, a slope waypoint, a
                                    ; point to omit.  A typed number
                                    ; never uses it: a name is exact.
                                    ; 12.0 is what BPCALLOUT, ABFIND
                                    ; and PERPMARK snap at, so a
                                    ; drafter's aim carries between
                                    ; the tools
(setq *PF-PICKUP-EPS*   3.0)        ; a survey point within this of the
                                    ; selected perimeter counts as one
                                    ; of ITS points when ADAB gathers
                                    ; or trims them (3 in - genuine
                                    ; edge points sit within the fit
                                    ; tolerance, depth shots and deck
                                    ; points are feet away)
(setq *PF-BOTTOM-STEP*  6.0)        ; sampling step for the hopper
                                    ; offset curve (6 inches keeps it
                                    ; smooth without a heavy polyline);
                                    ; also how far a slope waypoint may
                                    ; sit from its side of the pool
(setq *PF-BOTTOM-FIT*   0.25)       ; merging those samples into long
                                    ; arcs may leave no sample further
                                    ; than this off the drawn curve (a
                                    ; quarter inch - invisible at pool
                                    ; scale, a big cut in arc count)
(setq *PF-SPIKE-TOL*    2.0)        ; how far a slope waypoint's offset
                                    ; has to sit against BOTH its
                                    ; neighbours along that side before
                                    ; the run names it: two inches.  40,
                                    ; 10 and 30 in a row is a digit that
                                    ; went in wrong, and the wall
                                    ; between a 40 and a 30 is about 35.
                                    ; Raising it hides typos, lowering
                                    ; it starts naming real steps

;; ---- 3. GUARDS ------------------------------------------------------
(setq *PF-EXACT-EPS*    0.001)      ; "exactly on" threshold (units):
                                    ; two points closer than this are
                                    ; the same point - duplicates
                                    ; collapse, picks match, held and
                                    ; declared points are found by it
(setq *PF-CHAIN-FUZZ*   1.0e-4)     ; endpoint-matching fuzz for
                                    ; chaining exploded segments into
                                    ; one closed loop
(setq *PF-THIN-EPS*     0.01)       ; consecutive samples of an offset
                                    ; curve closer than this (a
                                    ; hundredth) collapse to one - a
                                    ; tight offset can fold neighbouring
                                    ; samples onto each other
(setq *PF-BULGE-CLAMP*  1.373)      ; the half-angle a tangent-window
                                    ; edge, or a span's own permitted
                                    ; turn, may reach (radians): its
                                    ; tangent is a bulge of about 5, an
                                    ; arc sweeping some 314 degrees.
                                    ; Keeps U-turn geometry finite;
                                    ; anything real sits far below it
(setq *PF-STRAIGHT-R*   1.0e6)      ; an arc whose radius reaches this
                                    ; is a straight line for every
                                    ; practical purpose: it is not
                                    ; snapped to a nice radius and is
                                    ; not reported as sitting on one
(setq *PF-2OPT-PASSES*  40)         ; the automatic point ordering
                                    ; uncrosses its loop with 2-opt
                                    ; passes until one improves nothing,
                                    ; or this many have run - a bound
                                    ; on the search, not a target

;; The LENGTH RULER beside the three hopper offsets.  They are asked
;; one after another, each defaulting to the one before, and they are
;; not taped off anything -- a hopper is offset in from the walls by
;; whatever the sheet says, out of a short list the shop builds to.  So
;; each stands beside DIMSTAMP's ruler, drawn down a strip near the
;; right edge of the view, and a click on a row IS the offset.  Scratch
;; on its own layer, taken down before any prompt that does not take it
;; and on every way out.  Every size is a fraction of the current view,
;; so the ruler reads the same at any zoom.
(setq *PF-RULER-LAYER* "ABHD-RULER") ; scratch layer the rows are drawn
                                    ; on, made if missing and left
                                    ; behind empty
(setq *PF-RULER-COLOR* 3)           ; ACI colour of the rows you can
                                    ; PICK, carried on the entities
                                    ; themselves
(setq *PF-RULER-CUR-COLOR* 7)       ; ...and of the ringed CURRENT row,
                                    ; so it reads apart from the
                                    ; options; 7 is AutoCAD's
                                    ; black/white swap
(setq *PF-RULER-SCREEN-X* 0.88)     ; where the spine sits across the
                                    ; view, as a fraction of its width
                                    ; in from the left; past 0.5 the
                                    ; rows reach left, short of it they
                                    ; reach right, so the ruler is
                                    ; always inside the view
(setq *PF-RULER-ROW-FRAC* 0.042)    ; one row's share of the view's
                                    ; height -- the ruler's size knob
(setq *PF-RULER-TXT-FRAC* 0.5)      ; the biggest row label's height, as
                                    ; a fraction of the row spacing
(setq *PF-RULER-TICK-FRAC* 0.6)     ; the longest tick, same measure
(setq *PF-RULER-RING-FRAC* 0.26)    ; the ring round the current row,
                                    ; same measure
(setq *PF-RULER-REACH* 6.0)         ; how far inboard of the spine, in
                                    ; row spacings, a click still counts
                                    ; as picking a row rather than as
                                    ; the first point of a measured
                                    ; length
(setq *PF-HOP-OFF-LADDER* '(24.0 72.0 6.0))
                                    ; the rungs those three prompts
                                    ; offer, as (LOW HIGH STEP) in
                                    ; inches -- 2' to 6' by 6", the
                                    ; offsets a hopper is laid out to.
                                    ; POOL and FITABHD offer the same
                                    ; range at the same question: a
                                    ; hopper offset is one number
                                    ; whichever tool is asking for it.
                                    ; nil leaves them the plain typed
                                    ; questions they were
;; ---- end of tunables -----------------------------------------------

;; ---- session memory and run state ----------------------------------
;; None of this is a setting: each is written as the tool runs, so an
;; initial value here is a starting point rather than something to
;; tune.  The two remembered answers are seeded only when unset, so
;; re-loading the file mid-session does not forget what the last run
;; was asked.
(setq pf:*version*      "092326 REV26") ; announced on load.  The
                                    ; versioned twin of this file is
                                    ; named abhd_<MMDDYY>_REV<##>.lsp
                                    ; so anyone can see which iteration
                                    ; is in a colleague's stack; bump
                                    ; this with every revision and
                                    ; regenerate releases/ (the tests
                                    ; check the name, the match, and
                                    ; this)
(if (null *PF-TOL*) (setq *PF-TOL* 1.0)) ; the max distance a point may
                                    ; sit from the fitted line: asked at
                                    ; step 1, Enter keeps the last
                                    ; answer, 1 inch in a fresh session
(if (null *PF-HOP-OFF*) (setq *PF-HOP-OFF* 18.0)) ; the hopper offset
                                    ; the bottom flow offers first; the
                                    ; first offset typed in a run
                                    ; becomes the next run's default
;; *PF-MAX-ARCS* : the curve cap the last run was given, in one of
;; three states:
;;     'AUTO    - the recommendation, worked out from the survey once
;;                the points are in hand: one curve per *PF-ARC-DIV*
;;                of them (pf:rec-arcs).  The cap is asked at step 3,
;;                four steps before the points are selected, so the
;;                recommendation cannot be a number there - it is a
;;                RULE that becomes a number at step 7.  This is what
;;                a fresh session starts on
;;     a number - that many curves, typed at step 3
;;     nil      - no cap at all, "None" typed at step 3
;; Asked at step 3 (Enter keeps whichever it is on) and remembered
;; like the two above.  Seeded only when unset, like them, which does
;; mean a mid-session re-load of this file reads a "None" back as
;; 'AUTO - nil is the one state that cannot be told from never-asked.
;; Re-typing None at the next step 3 puts it back.
(if (null *PF-MAX-ARCS*) (setq *PF-MAX-ARCS* 'AUTO))
;;
;; Cover mode: the pool-bottom question in pf:bottom answers No without
;; being asked, so a cover sheet is fitted to its perimeter and stops
;; there.  Set by ABHDCOVER, cleared on both exits from c:ABHD; nil for
;; a typed ABHD, always.
(setq abhd:*nobottom* nil)
;; ---- end of state ---------------------------------------------------

;; ---- small 2D vector helpers ---------------------------------------
(defun pf:2d (p) (list (car p) (cadr p)))
(defun pf:dist (a b) (distance (pf:2d a) (pf:2d b)))
(defun pf:sub (a b) (mapcar '- (pf:2d a) (pf:2d b)))
(defun pf:add (a b) (mapcar '+ (pf:2d a) (pf:2d b)))
(defun pf:scl (v s) (list (* (car v) s) (* (cadr v) s)))
(defun pf:dot (a b) (+ (* (car a) (car b)) (* (cadr a) (cadr b))))
(defun pf:mid (a b) (pf:scl (pf:add a b) 0.5))
(defun pf:perp (v) (list (- (cadr v)) (car v))) ; rotate 90 deg CCW

;; Tangent with the angle clamped just short of +/-90 degrees.  Every
;; bulge in this file is a tangent of a quarter-sweep, so a half-turn
;; quarter-sweep (a degenerate, full-circle segment) would otherwise
;; divide by zero and abort the command.  Clamping yields a huge but
;; finite bulge instead; the callers that can legitimately reach the
;; limit (full-circle ARCs and CIRCLEs) split themselves in half
;; before they get here, so this is purely a safety net.
(defun pf:tan (x)
  (cond ((> x  1.5697) (setq x  1.5697))    ; 89.94 deg
        ((< x -1.5697) (setq x -1.5697)))
  (/ (sin x) (cos x)))

;; smallest integer >= X (X non-negative)
(defun pf:ceil (x / f)
  (setq f (fix x))
  (if (> x f) (1+ f) f))

;; the list from index K on / COUNT elements of LST starting at index K
(defun pf:nthcdr (k lst)
  (while (> k 0) (setq lst (cdr lst) k (1- k)))
  lst)
(defun pf:sublist (lst k count / out)
  (setq lst (pf:nthcdr k lst))
  (while (> count 0)
    (setq out   (cons (car lst) out)
          lst   (cdr lst)
          count (1- count)))
  (reverse out))

;; normalize an angle into [0, 2pi)
(defun pf:norm-ang (a)
  (while (< a 0.0) (setq a (+ a (* 2.0 pi))))
  (while (>= a (* 2.0 pi)) (setq a (- a (* 2.0 pi))))
  a)

;; smallest signed angular difference (to - from), in (-pi, pi]
(defun pf:signed-dang (from to / d)
  (setq d (pf:norm-ang (- to from)))
  (if (> d pi) (- d (* 2.0 pi)) d))

;; ---- circle / arc geometry -----------------------------------------

;; Circumcenter of three points, nil when (nearly) collinear.
(defun pf:circumcenter (pa pb pc / x1 y1 x2 y2 x3 y3 d s1 s2 s3)
  (setq x1 (car pa) y1 (cadr pa)
        x2 (car pb) y2 (cadr pb)
        x3 (car pc) y3 (cadr pc)
        d  (* 2.0 (+ (* x1 (- y2 y3)) (* x2 (- y3 y1)) (* x3 (- y1 y2)))))
  (if (< (abs d) 1.0e-10)
    nil
    (progn
      (setq s1 (+ (* x1 x1) (* y1 y1))
            s2 (+ (* x2 x2) (* y2 y2))
            s3 (+ (* x3 x3) (* y3 y3)))
      (list (/ (+ (* s1 (- y2 y3)) (* s2 (- y3 y1)) (* s3 (- y1 y2))) d)
            (/ (+ (* s1 (- x3 x2)) (* s2 (- x1 x3)) (* s3 (- x2 x1))) d)))))

;; Bulge of the unique circular arc that starts at P1, ends at P2 and
;; passes through Q.  0.0 when the three points are collinear, and
;; also when the arc would be a (near) full circle - P1 and P2 lying
;; at the same angle from the center makes the sweep 0 or 2*pi, which
;; no single bulge can express.  Nearly-collinear noisy survey points
;; can produce exactly that, so both ends of the range are guarded.
(defun pf:bulge-3pt (p1 q p2 / c a1 a2 aq dccw dq)
  (setq p1 (pf:2d p1) q (pf:2d q) p2 (pf:2d p2)
        c  (pf:circumcenter p1 q p2))
  (if (null c)
    0.0
    (progn
      (setq a1   (angle c p1)
            a2   (angle c p2)
            aq   (angle c q)
            dccw (pf:norm-ang (- a2 a1))
            dq   (pf:norm-ang (- aq a1)))
      (cond
        ((< dccw 1.0e-9) 0.0)                       ; degenerate sweep
        ((> dccw (- (* 2.0 pi) 1.0e-9)) 0.0)        ; degenerate sweep
        ((<= dq dccw) (pf:tan (/ dccw 4.0)))        ; CCW arc through Q
        (T (- (pf:tan (/ (- (* 2.0 pi) dccw) 4.0)))))))) ; CW through Q

;; Arc geometry of a bulged segment: (center radius angStart angEnd)
;; where the arc runs CCW from angStart to angEnd when bulge > 0 and
;; CW when bulge < 0.  nil for a straight segment.
(defun pf:arc-geom (p1 p2 b / ch dir apex c)
  (if (< (abs b) 1.0e-9)
    nil
    (progn
      (setq p1   (pf:2d p1)
            p2   (pf:2d p2)
            ch   (pf:dist p1 p2)
            dir  (pf:scl (pf:sub p2 p1) (/ 1.0 ch))
            ;; sagitta = (chord/2)*bulge; a positive (CCW) bulge apex
            ;; lies to the RIGHT of the p1->p2 chord direction
            apex (pf:add (pf:mid p1 p2)
                         (pf:scl (pf:perp dir) (* -0.5 ch b)))
            c    (pf:circumcenter p1 apex p2))
      (if (null c)
        nil
        (list c (pf:dist c p1) (angle c p1) (angle c p2))))))

;; Distance from point P to segment (p1 p2 bulge).
(defun pf:seg-dist (p seg / p1 p2 b v w len2 t2 g c r a1 a2 ap sweep rel)
  (setq p  (pf:2d p)
        p1 (pf:2d (car seg))
        p2 (pf:2d (cadr seg))
        b  (caddr seg))
  (if (< (abs b) 1.0e-9)
    ;; straight: project onto the segment, clamp to its ends
    (progn
      (setq v    (pf:sub p2 p1)
            w    (pf:sub p p1)
            len2 (pf:dot v v))
      (if (< len2 1.0e-20)
        (pf:dist p p1)
        (progn
          (setq t2 (/ (pf:dot w v) len2))
          (if (< t2 0.0) (setq t2 0.0))
          (if (> t2 1.0) (setq t2 1.0))
          (pf:dist p (pf:add p1 (pf:scl v t2))))))
    ;; arc: radial distance when P falls inside the sweep, else the
    ;; nearer endpoint
    (progn
      (setq g (pf:arc-geom p1 p2 b))
      (if (null g)
        (min (pf:dist p p1) (pf:dist p p2))
        (progn
          (setq c  (car g)  r (cadr g)
                a1 (caddr g) a2 (cadddr g)
                ap (angle c p))
          (if (> b 0.0)
            (setq sweep (pf:norm-ang (- a2 a1)) rel (pf:norm-ang (- ap a1)))
            (setq sweep (pf:norm-ang (- a1 a2)) rel (pf:norm-ang (- ap a2))))
          (if (<= rel sweep)
            (abs (- (pf:dist p c) r))
            (min (pf:dist p p1) (pf:dist p p2))))))))

;; Bulge of the arc that starts at A with tangent direction TANG
;; (radians) and ends at B.  The angle between a chord and the tangent
;; at its end is half the included angle, so delta = 2*phi.
(defun pf:tangent-bulge (a tang b / phi)
  (setq phi (pf:signed-dang tang (angle (pf:2d a) (pf:2d b))))
  (pf:tan (/ phi 2.0)))

;; Tangent direction (radians) at the END of the arc from A to B with
;; the given bulge: chord direction + delta/2, delta = 4*atan(bulge).
(defun pf:end-tangent (a b bulge)
  (+ (angle (pf:2d a) (pf:2d b)) (* 2.0 (atan bulge))))

;; Position of P along segment (p1 p2 bulge) as a 0..1 parameter,
;; used only to ORDER candidate points along the segment.
(defun pf:seg-param (p seg / p1 p2 b v w len2 g c a1 a2 ap sweep rel)
  (setq p  (pf:2d p)
        p1 (pf:2d (car seg))
        p2 (pf:2d (cadr seg))
        b  (caddr seg))
  (if (< (abs b) 1.0e-9)
    (progn
      (setq v (pf:sub p2 p1) w (pf:sub p p1) len2 (pf:dot v v))
      (if (< len2 1.0e-20) 0.0 (/ (pf:dot w v) len2)))
    (progn
      (setq g (pf:arc-geom p1 p2 b))
      (if (null g)
        0.0
        (progn
          (setq c (car g) a1 (caddr g) a2 (cadddr g) ap (angle c p))
          (if (> b 0.0)
            (setq sweep (pf:norm-ang (- a2 a1))
                  rel   (pf:norm-ang (- ap a1)))
            (setq sweep (pf:norm-ang (- a1 a2))
                  rel   (- (pf:norm-ang (- a1 a2))
                           (pf:norm-ang (- ap a2)))))
          (if (< sweep 1.0e-10) 0.0 (/ rel sweep)))))))

;; ---- entity -> segment extraction ----------------------------------
;; A segment is (startPt endPt bulge), 2D points.

;; ---- the entity's own plane ----------------------------------------
;; An ARC, CIRCLE or polyline keeps its numbers in its OWN plane -- the
;; OCS its 210 names -- not the world's.  Flat work carries no 210, or
;; (0 0 1), and passes through untouched.  One on the underside of the
;; plane, (0 0 -1), is what exploding a mirrored block or some survey
;; exporters leave: every X is the other way round, so read raw the
;; outline lands mirrored through the Y axis, and the "not drawn in the
;; world plane" warning never fires because the plane IS the world's.
;; So the plane is read once per entity (nil when flat), each end is
;; taken to world through it, and each bulge turns the other way when
;; the plane is seen from below.  A genuinely tilted plane is still only
;; flattened here -- that one is warned about where it is read.
(defun pf:ocs-n (ed / nz)
  (setq nz (cdr (assoc 210 ed)))
  (if (and nz (not (equal nz '(0.0 0.0 1.0) 1.0e-10))) nz))

;; SEGS as read in EN's plane NZ at elevation Z, taken to the world's.
(defun pf:segs-w (segs en nz z)
  (if nz
    (mapcar '(lambda (s)
               (list (pf:2d (trans (list (car (car s)) (cadr (car s)) z)
                                   en 0))
                     (pf:2d (trans (list (car (cadr s)) (cadr (cadr s)) z)
                                   en 0))
                     (if (< (caddr nz) 0.0) (- (caddr s)) (caddr s))))
            segs)
    segs))

;; Where a survey point sits, in the world's numbers.  A block's (or a
;; TEXT's) insertion point is kept in its own plane just as an ARC's
;; centre is, so an ab_pt inserted from below, (0 0 -1), read raw lands
;; mirrored through the Y axis - off the outline it was shot on, with
;; nothing said.  A POINT's 10 is in world numbers already and is left
;; alone, as is anything flat.
(defun pf:ins-w (ed)
  (if (and (/= (cdr (assoc 0 ed)) "POINT") (pf:ocs-n ed))
    (trans (cdr (assoc 10 ed)) (cdr (assoc -1 ed)) 0)
    (cdr (assoc 10 ed))))

(defun pf:lw-segs (ed / pts bls item segs n closed)
  ;; collect (10) vertices and their (42) bulges, in order
  (setq pts nil bls nil)
  (foreach item ed
    (cond
      ((= (car item) 10)
       (setq pts (cons (pf:2d (cdr item)) pts)
             bls (cons 0.0 bls)))
      ((and (= (car item) 42) bls)
       (setq bls (cons (cdr item) (cdr bls))))))
  (setq pts (reverse pts) bls (reverse bls)
        closed (= 1 (logand 1 (cdr (assoc 70 ed))))
        segs nil n 0)
  (while (< n (1- (length pts)))
    (setq segs (cons (list (nth n pts) (nth (1+ n) pts) (nth n bls)) segs)
          n    (1+ n)))
  (if (and (> (length pts) 2)
           (or closed
               (< (pf:dist (last pts) (car pts)) *PF-CHAIN-FUZZ*)))
    (if (>= (pf:dist (last pts) (car pts)) *PF-CHAIN-FUZZ*)
      (setq segs (cons (list (last pts) (car pts) (last bls)) segs))))
  (pf:segs-w (reverse segs) (cdr (assoc -1 ed)) (pf:ocs-n ed)
             (cond ((cdr (assoc 38 ed))) (0.0))))

(defun pf:pl-segs (en / ed sub pts bls segs n closed nz z)
  ;; heavy (old-style) 2D POLYLINE: walk its VERTEX sub-entities
  (setq ed (entget en)
        closed (= 1 (logand 1 (cdr (assoc 70 ed))))
        ;; a 3D polyline or mesh (bits 8, 16) keeps world numbers
        nz     (if (= 0 (logand 24 (cdr (assoc 70 ed)))) (pf:ocs-n ed))
        z      (cond ((caddr (cdr (assoc 10 ed)))) (0.0))
        pts nil bls nil
        sub (entnext en))
  (while (and sub (= "VERTEX" (cdr (assoc 0 (setq ed (entget sub))))))
    ;; skip the spline FRAME points (flag 16) only: they are the
    ;; control net, off the curve.  A curve-fit extra vertex (flag 1)
    ;; is ON the curve -- PEDIT Fit joins an arc pair there -- and
    ;; dropping it while keeping its neighbours' bulges read arcs that
    ;; do not follow the outline
    (if (= 0 (logand 16 (cond ((cdr (assoc 70 ed))) (0))))
      (setq pts (cons (pf:2d (cdr (assoc 10 ed))) pts)
            bls (cons (cond ((cdr (assoc 42 ed))) (0.0)) bls)))
    (setq sub (entnext sub)))
  (setq pts (reverse pts) bls (reverse bls) segs nil n 0)
  (while (< n (1- (length pts)))
    (setq segs (cons (list (nth n pts) (nth (1+ n) pts) (nth n bls)) segs)
          n    (1+ n)))
  (if (and closed (> (length pts) 2))
    (setq segs (cons (list (last pts) (car pts) (last bls)) segs)))
  (pf:segs-w (reverse segs) en nz z))

(defun pf:ent-segs (en / ed typ c r a1 a2 delta nz z)
  (setq ed  (entget en)
        typ (cdr (assoc 0 ed))
        nz  (pf:ocs-n ed)
        z   (cond ((caddr (cdr (assoc 10 ed)))) (0.0)))
  (cond
    ((= typ "LINE")
     (list (list (pf:2d (cdr (assoc 10 ed)))
                 (pf:2d (cdr (assoc 11 ed)))
                 0.0)))
    ((= typ "ARC")
     (setq c  (pf:2d (cdr (assoc 10 ed)))
           r  (cdr (assoc 40 ed))
           a1 (cdr (assoc 50 ed))
           a2 (cdr (assoc 51 ed))
           delta (pf:norm-ang (- a2 a1)))
     (if (< delta 1.0e-10) (setq delta (* 2.0 pi)))
     ;; a full-circle arc cannot be one bulged segment (its bulge is
     ;; infinite): hand back two semicircles instead
     (pf:segs-w
       (if (> delta (- (* 2.0 pi) 1.0e-9))
         (list (list (polar c a1 r) (polar c (+ a1 pi) r) 1.0)
               (list (polar c (+ a1 pi) r) (polar c a1 r) 1.0))
         (list (list (polar c a1 r) (polar c a2 r) (pf:tan (/ delta 4.0)))))
       en nz z))
    ;; a CIRCLE is a legitimate pool perimeter (round spa): two
    ;; semicircles, so the chaining and fitting code sees a normal
    ;; closed loop instead of reporting a gap
    ((= typ "CIRCLE")
     (setq c (pf:2d (cdr (assoc 10 ed)))
           r (cdr (assoc 40 ed)))
     (pf:segs-w
       (list (list (polar c 0.0 r) (polar c pi r) 1.0)
             (list (polar c pi r) (polar c 0.0 r) 1.0))
       en nz z))
    ((= typ "LWPOLYLINE") (pf:lw-segs ed))
    ((= typ "POLYLINE") (pf:pl-segs en))
    (T nil)))

;; ---- chain loose segments into one closed loop ----------------------
;; Returns the ordered segment list, or nil (with a message) on failure.
(defun pf:chain (segs / loop start end found s rest)
  (if (null segs)
    nil
    (progn
      (setq loop  (list (car segs))
            start (car (car segs))
            end   (cadr (car segs))
            segs  (cdr segs))
      (while (and segs
                  (>= (pf:dist end start) *PF-CHAIN-FUZZ*))
        (setq found nil rest nil)
        (foreach s segs
          (cond
            (found (setq rest (cons s rest)))
            ((< (pf:dist end (car s)) *PF-CHAIN-FUZZ*)
             (setq found s))
            ((< (pf:dist end (cadr s)) *PF-CHAIN-FUZZ*)
             ;; reverse the segment: swap ends, negate the bulge
             (setq found (list (cadr s) (car s) (- (caddr s)))))
            (T (setq rest (cons s rest)))))
        (if found
          (setq loop (cons found loop)
                end  (cadr found)
                segs (reverse rest))
          (setq segs nil end nil)))  ; gap -> bail out
      (cond
        ((null end)
         (princ "\nABHD: gap in the POOL perimeter - could not close the loop.")
         nil)
        ((>= (pf:dist end start) *PF-CHAIN-FUZZ*)
         (princ "\nABHD: the POOL perimeter does not close.")
         nil)
        (T
         (if segs
           (princ (strcat "\nABHD: warning - "
                          (itoa (length segs))
                          " POOL segment(s) not part of the closed loop were ignored.")))
         (reverse loop))))))

;; ---- span fitting helpers --------------------------------------------
;; A "span" is one candidate segment from A to B judged against QS, the
;; survey points it is supposed to represent.

;; Worst distance from any of QS to the segment (A B bulge).
(defun pf:span-dev (a b bul qs / seg mx d q)
  (setq seg (list a b bul) mx 0.0)
  (foreach q qs
    (setq d (pf:seg-dist q seg))
    (if (> d mx) (setq mx d)))
  mx)

;; *PF-MISS-PCT* as it may be used: a fraction from 0 to 1, or the
;; shipped 0.20.  The step's initget and its clamp over 100 hold
;; only what is TYPED; Enter and every other reader take the knob
;; as it stands, so a LAZTUNE override of 15 (meant as 15%) was
;; offered as <1500> and let every point off the line, and one of
;; -0.1 as <-9>.
(defun pf:miss-knob ( / v)
  (setq v *PF-MISS-PCT*)
  (if (and (numberp v) (>= v 0) (<= v 1.0)) v 0.20))

;; The miss percentage in force for the current run: the command binds
;; pf-miss-pct from the user's answer; Enter keeps the standard value.
(defun pf:misspct ()
  (if pf-miss-pct pf-miss-pct (pf:miss-knob)))

;; A curve cap of N points over D of them, rounded to the NEAREST
;; whole curve and never below 1.  A cap of nothing is not a cap, and
;; a survey small enough to round to zero is one the fitter will not
;; reach a cap on anyway.
(defun pf:div-arcs (n d / c)
  (setq c (fix (+ 0.5 (/ (float n) d))))
  (if (< c 1) 1 c))

;; The RECOMMENDED curve cap for N points: one curve per *PF-ARC-DIV*
;; of them.  SIMPABHD's rows carry their own divisor and go straight
;; to pf:div-arcs.
(defun pf:rec-arcs (n) (pf:div-arcs n *PF-ARC-DIV*))

;; The curve cap actually in force over N points, resolving the three
;; states of *PF-MAX-ARCS*: 'AUTO is the recommendation worked out
;; from the count, a number is itself, nil is no cap.  Every reader of
;; the cap goes through here, so the recommendation becomes a number
;; in exactly one place.
(defun pf:cap-for (n)
  (if (eq 'AUTO *PF-MAX-ARCS*) (pf:rec-arcs n) *PF-MAX-ARCS*))

;; The "on the shape" threshold in force for the current run.  It
;; scales with the tolerance (a quarter of it, never below
;; *PF-ON-EPS*): if the user accepts 4 inches of error, a point 1 inch
;; off is plainly still ON the shape, and counting it as a miss would
;; burn the whole allowance on the first span and starve the rest of
;; the loop into single-point stubs.  pf-on-eps is bound per run by
;; the command and per pass by pf:fit-pass.
(defun pf:oneps ()
  (if pf-on-eps pf-on-eps *PF-ON-EPS*))

;; How many of QS sit farther than the on-the-shape threshold from the
;; segment - the points that would eat into the miss allowance.
(defun pf:span-misses (a b bul qs / seg c q lim)
  (setq seg (list a b bul) c 0 lim (pf:oneps))
  (foreach q qs
    (if (> (pf:seg-dist q seg) lim) (setq c (1+ c))))
  c)

;; Best single arc from A to B over the points QS: candidate bulges are
;; the exact 3-point fits through a few of the points plus the average
;; of them all; the one with the smallest worst-case deviation wins.
;; Returns (bulge . maxdev).
(defun pf:span-arc (a b qs / bls sum bl m cands best bd d)
  (setq bls (mapcar '(lambda (q) (pf:bulge-3pt a q b)) qs)
        sum 0.0
        m   (length qs))
  (foreach bl bls (setq sum (+ sum bl)))
  (setq cands (list (/ sum m) (nth (/ m 2) bls)))
  (if (>= m 4)
    (setq cands (append cands (list (nth (/ m 4) bls)
                                    (nth (/ (* 3 m) 4) bls)))))
  (setq best nil bd nil)
  (foreach bl cands
    (setq d (pf:span-dev a b bl qs))
    (if (or (null bd) (< d bd)) (setq best bl bd d)))
  (cons best bd))

;; Radius of the arc (A B bulge); nil for a straight segment.
(defun pf:bulge-radius (a b bl / h)
  (if (< (abs bl) 1.0e-9)
    nil
    (progn
      (setq h (/ (pf:dist a b) 2.0))
      (/ (* h (1+ (* bl bl))) (* 2.0 (abs bl))))))

;; Bulge of the arc from A to B with radius R, on the same side and
;; with the same minor/major-arc character as reference bulge BREF.
;; nil when R is too small to span the chord.
(defun pf:radius-bulge (a b r bref / h s bl)
  (setq h (/ (pf:dist a b) 2.0))
  (if (or (< r h) (< h 1.0e-9))
    nil
    (progn
      (setq s  (sqrt (- (* r r) (* h h)))
            bl (if (> (abs bref) 1.0)
                 (/ (+ r s) h)              ; major arc
                 (/ (- r s) h)))            ; minor arc
      (if (< bref 0.0) (- bl) bl))))

;; Try to snap the arc A->B (free-fit bulge BL over points QS) to a
;; "nice" radius - whole feet first, then half feet, then whole inches
;; (*PF-NICE-RADII*) - keeping every point within TOL and at most LEFT
;; of them off by more than *PF-ON-EPS*.  When WIN (a bulge interval)
;; is given the snapped bulge must stay inside it, so snapping never
;; breaks the tangency window.  The nearer multiple on each tier is
;; tried first; the arc's endpoints never move.  Returns
;; (bulge . misses) of the snapped arc, or nil.
(defun pf:snap-arc (a b bl qs tol left win / r0 h best tier lo hi
                                              cands r bl2 mis)
  (setq r0   (pf:bulge-radius a b bl)
        h    (/ (pf:dist a b) 2.0)
        best nil)
  (if (and r0 (< r0 *PF-STRAIGHT-R*))       ; a huge radius is basically straight
    (foreach tier *PF-NICE-RADII*
      (if (null best)
        (progn
          (setq lo    (* tier (fix (/ r0 tier)))
                hi    (+ lo tier)
                cands (if (< (- r0 lo) (- hi r0))
                        (list lo hi)
                        (list hi lo)))
          (foreach r cands
            (if (and (null best) (>= r h) (> r 0.0))
              (progn
                (setq bl2 (pf:radius-bulge a b r bl))
                (if (and bl2
                         (or (null win)
                             (and (>= bl2 (car win)) (<= bl2 (cdr win))))
                         (<= (pf:span-dev a b bl2 qs) tol)
                         (<= (setq mis (pf:span-misses a b bl2 qs))
                             left))
                  (setq best (cons bl2 mis))))))))))
  best)

;; ---- arc segment re-fitting ------------------------------------------
;; Re-fit one curved segment from P1 to P2 (original bulge B) through
;; CANDS, its nearby survey points sorted along the segment.  Returns a
;; list of one or more segments (p1 p2 bulge):
;;   * no candidates          -> the original arc, endpoints updated
;;   * a nice-radius (foot / half-foot / inch) arc holds every point
;;     within TOL and the miss allowance (pf-miss-left, set by the
;;     command) can absorb the off points
;;                            -> that single snapped arc, preferred
;;                               even over an exact free fit
;;   * one arc holds them all -> that single arc
;;   * one free arc keeps every point within TOL and the allowance
;;     covers it              -> that single arc; fewer curves beats
;;                               exactness, by design
;;   * otherwise              -> a chain of arcs passing exactly
;;                               through every point, each carrying
;;                               the last one's tangent on as far as
;;                               it can without looping (pf:tame-bulge)
;; The bulge that carries tangent TANG on from PREV to Q, tamed: the
;; drawn arc's own bulge B is the shape being trusted here, so a
;; sub-arc may curve that far, or as far as two neighbouring points
;; justify, whichever is more - but no further.  Carrying a tangent on
;; unchecked is what let this subdivision spiral into loops of its own.
(defun pf:tame-bulge (prev tang q b)
  (pf:cap-b (pf:tangent-bulge prev tang q)
            (max (abs b) (pf:max-bulge prev q nil))))

(defun pf:fit-arc-seg (p1 p2 b cands tol / ar bavg maxres mis nb q segs
                                            prev tang sn)
  (if (null cands)
    (list (list p1 p2 b))
    (progn
      (setq ar     (pf:span-arc p1 p2 cands)
            bavg   (car ar)
            maxres (cdr ar)
            sn     (pf:snap-arc p1 p2 bavg cands tol pf-miss-left nil))
      (cond
        ;; a nice-radius arc holds every point: take it first
        (sn
         (setq pf-miss-left (- pf-miss-left (cdr sn)))
         (list (list p1 p2 (car sn))))
        ;; a single free arc genuinely holds every point
        ((<= maxres *PF-FIT-EPS*)
         (list (list p1 p2 bavg)))
        ;; a single arc is close enough and the allowance covers it
        ((and (<= maxres tol)
              (<= (setq mis (pf:span-misses p1 p2 bavg cands))
                  pf-miss-left))
         (setq pf-miss-left (- pf-miss-left mis))
         (list (list p1 p2 bavg)))
        ;; subdivide.  First arc runs from P1 through the 1st point to
        ;; the 2nd; every further arc starts tangent to the previous one
        ;; and lands exactly on the next point; the last lands on P2.
        ;; All points are hit exactly and every internal joint is
        ;; tangent-continuous (smooth).
        (T
         (setq nb   (pf:bulge-3pt p1 (car cands) (cadr cands))
               segs (list (list p1 (cadr cands) nb))
               tang (pf:end-tangent p1 (cadr cands) nb)
               prev (cadr cands))
         (foreach q (cddr cands)
           (setq nb   (pf:tame-bulge prev tang q b)
                 segs (cons (list prev q nb) segs)
                 tang (pf:end-tangent prev q nb)
                 prev q))
         (setq nb (pf:tame-bulge prev tang p2 b))
         (reverse (cons (list prev p2 nb) segs)))))))

;; ---- points-only / ordering-sketch mode -------------------------------

;; Pure-AutoLISP list helpers (no Visual LISP / vl-* dependency, so the
;; command works even when (vl-load-com) has not been run).

;; Remove every element equal (within fuzz) to VAL from LST.
(defun pf:remove (val lst / out x)
  (foreach x lst
    (if (not (equal x val 1.0e-9)) (setq out (cons x out))))
  (reverse out))

;; Insert (key . val) pair X into the already-sorted list LST, keeping
;; ascending order by the pair's car (key).
(defun pf:ins-car (x lst)
  (cond ((null lst) (list x))
        ((< (car x) (car (car lst))) (cons x lst))
        (T (cons (car lst) (pf:ins-car x (cdr lst))))))

;; Insertion-sort a list of (key . val) pairs ascending by key.
(defun pf:sort-car (lst / out x)
  (foreach x lst (setq out (pf:ins-car x out)))
  out)

(defun pf:dedupe (pts / out q p dup)
  (foreach q pts
    (setq dup nil)
    (foreach p out
      (if (< (pf:dist p q) *PF-EXACT-EPS*) (setq dup T)))
    (if (not dup) (setq out (cons q out))))
  (reverse out))

;; T when the chained loop contains at least one curved segment
(defun pf:has-arcs (loop / r)
  (foreach s loop (if (>= (abs (caddr s)) 1.0e-9) (setq r T)))
  r)

;; Order points into a closed tour: nearest-neighbour walk from the
;; leftmost point, then 2-opt passes to remove crossings.
(defun pf:order-points (pts / start cur tour rest best bd q d n i j k
                              pass improved ti ti1 tj tj1 delta head midl
                              taill)
  (setq start (car pts))
  (foreach q (cdr pts)
    (if (or (< (car q) (car start))
            (and (= (car q) (car start)) (< (cadr q) (cadr start))))
      (setq start q)))
  (setq cur  start
        rest (pf:remove start pts)
        tour (list start))
  (while rest
    (setq best nil bd nil)
    (foreach q rest
      (setq d (pf:dist cur q))
      (if (or (null bd) (< d bd)) (setq best q bd d)))
    (setq tour (cons best tour)
          cur  best
          rest (pf:remove best rest)))
  (setq tour (reverse tour)
        n    (length tour)
        pass 0
        improved T)
  (while (and improved (< pass *PF-2OPT-PASSES*))
    (setq improved nil pass (1+ pass) i 0)
    (while (< i (1- n))
      (setq j (1+ i))
      (while (< j n)
        (if (not (and (= i 0) (= j (1- n))))
          (progn
            (setq ti    (nth i tour)
                  ti1   (nth (1+ i) tour)
                  tj    (nth j tour)
                  tj1   (nth (rem (1+ j) n) tour)
                  delta (- (+ (pf:dist ti tj) (pf:dist ti1 tj1))
                           (+ (pf:dist ti ti1) (pf:dist tj tj1))))
            (if (< delta -1.0e-9)
              (progn                    ; reverse tour[i+1 .. j]
                (setq head nil midl nil taill nil k 0)
                (foreach q tour
                  (cond ((<= k i) (setq head (cons q head)))
                        ((<= k j) (setq midl (cons q midl)))
                        (T        (setq taill (cons q taill))))
                  (setq k (1+ k)))
                (setq tour     (append (reverse head) midl (reverse taill))
                      improved T)))))
        (setq j (1+ j)))
      (setq i (1+ i))))
  tour)

;; Order points by their position along a user-drawn ordering sketch
;; (the chained loop): each point keys on segment-index + parameter.
(defun pf:loop-order (loop pts / keyed q best bd d i s tp)
  (foreach q pts
    (setq best 0 bd nil i 0)
    (foreach s loop
      (setq d (pf:seg-dist q s))
      (if (or (null bd) (< d bd)) (setq bd d best i))
      (setq i (1+ i)))
    (setq tp (pf:seg-param q (nth best loop)))
    (if (< tp 0.0) (setq tp 0.0))
    (if (> tp 1.0) (setq tp 1.0))
    (setq keyed (cons (cons (+ best tp) q) keyed)))
  (mapcar 'cdr (pf:sort-car keyed)))

;; The surveyed number carried by a point block, read from its
;; *PF-PT-TAG* attribute ("number" on ab_pt).  nil when the block has
;; no such attribute.
;;
;; DELIBERATELY strict: no first-numeric-attribute fallback, unlike
;; ABFIND/BPCALLOUT/LHD/FITABHD and cal:block-number.  The fitter
;; consumes every point it is handed, so a stray numbered block (a
;; detail bubble, a keynote) silently joining the survey would warp the
;; whole fit - a dropped untagged point is the visible, recoverable
;; failure.  Reviewed 2026-08-27 and kept on purpose; CABHD's copy
;; holds the same line for the same reason.
(defun pf:block-number (en / sub ed val)
  (setq sub (entnext en) val nil)
  (while (and sub
              (setq ed (entget sub))
              (= "ATTRIB" (cdr (assoc 0 ed))))
    (if (and (null val)
             (cdr (assoc 2 ed))
             (= (strcase (cdr (assoc 2 ed))) (strcase *PF-PT-TAG*)))
      (setq val (cdr (assoc 1 ed))))
    (setq sub (entnext sub)))
  val)

;; Is NM the number of a MOVED point - one ABFIND deduced from two tape
;; readings and numbered "17m" rather than one somebody shot?  The
;; letter is *PF-MOVED-MARK*, matched anywhere in the number and in
;; either case, so "17m", "17M" and "17m2" all answer yes.  A point
;; with no number at all (a bare POINT entity) answers no: there is no
;; number to carry the letter.
(defun pf:moved-p (nm)
  (and nm
       (eq 'STR (type nm))
       (wcmatch (strcase nm) (strcat "*" (strcase *PF-MOVED-MARK*) "*"))))

;; Remember a point and what to call it, so a miss can be reported as
;; "Pt.17" using the number in the drawing rather than a private
;; index.  Points with no number of their own get the next count.
;;
;; A moved point never gets remembered.  It is the one point in the
;; survey nobody stood on - ABFIND worked out where Pt.17 should have
;; been and wrote "17m" beside it - so holding the fit to it would be
;; holding it to a deduction.  Dropping it HERE, before pts exists,
;; is what makes that true of everything downstream at once: the
;; ordering walk, the fit, the miss allowance, the unheld rings and
;; the report all read pts, and none of them can see what was never
;; put in it.  The count goes to pf-nmoved so the command can say how
;; many it left out.
(defun pf:add-point (p nm)
  (if (pf:moved-p nm)
    (setq pf-nmoved (1+ (if pf-nmoved pf-nmoved 0)))
    (setq npt        (1+ npt)
          pts        (cons p pts)
          pf-ptnames (cons (cons p (if (and nm (/= nm "")) nm (itoa npt)))
                           pf-ptnames))))

;; What to call the surveyed point at Q.
(defun pf:pt-name (q / nm p)
  (setq nm nil)
  (foreach p pf-ptnames
    (if (and (null nm) (< (pf:dist (car p) q) *PF-EXACT-EPS*))
      (setq nm (cdr p))))
  (if nm nm "?"))

;; The member of LST nearest to P.
(defun pf:nearest (p lst / best bd q d)
  (setq best nil bd nil)
  (foreach q lst
    (setq d (pf:dist p q))
    (if (or (null bd) (< d bd)) (setq best q bd d)))
  best)

;; ---- naming a survey point -------------------------------------------
;; A declaration is ABOUT a survey point - the wall runs from Pt.17 to
;; Pt.22, Pt.9 is a corner, Pt.30 is held, Pt.41 is left out - so every
;; question below NAMES one rather than placing it.  This is PERPMARK's
;; infrastructure, carried here under this file's own prefix so the
;; standalone file loads alone (STANDARDS section 4; the grouped build
;; takes it from CALOFIN-LIB): one prompt takes a click OR a typed
;; number - "17", "Pt.17", "pt 17", "#17" and "017" all name the same
;; point - a click has to land within *PF-SNAP* of a point to pick it,
;; and every miss - a click on nothing, a number nothing carries, a
;; number two points share - is re-asked where it stands.  What used to
;; happen: a click ANYWHERE was snapped to the nearest survey point
;; after the selection, however far off it landed, and a wall end that
;; took the wrong point was a bad fit with no visible cause.
;;
;; A candidate is (position name): where the point is, and what the
;; prompts and the report call it.  The position is its IDENTITY - it
;; is what the fitter holds, and what a declaration made before the
;; selection is matched to once the selection is in hand.

;; The NUMBER a typed point name carries: the spelling with the spaces,
;; the hashes and the "Pt." prefix taken off, and nothing else touched.
;; Only the dot right after PT is a prefix dot - a point genuinely named
;; "40.5" keeps its decimal.
(defun pf:as-number (s / out i ch)
  (setq out "" i 1)
  (while (<= i (strlen s))
    (setq ch (substr s i 1))
    (if (not (member ch '(" " "#")))
      (setq out (strcat out ch)))
    (setq i (1+ i)))
  (if (and (>= (strlen out) 2) (= (strcase (substr out 1 2)) "PT"))
    (progn
      (setq out (substr out 3))
      (if (= (substr out 1 1) ".") (setq out (substr out 2)))))
  out)

;; One comparable form for a point number, so "35", "Pt.35", "pt 35",
;; "#35" and "035" all meet in the middle.
(defun pf:canon (s)
  (setq s (pf:as-number (strcase s)))
  (if (distof s 2)
    (rtos (distof s 2) 2 8)
    s))

;; Every candidate whose name is the number typed.  More than one is a
;; sheet that numbers two points the same, and is asked about rather
;; than guessed at.
(defun pf:cand-matches (s cands / want out c)
  (setq want (pf:canon s) out nil)
  (foreach c cands
    (if (= (pf:canon (cadr c)) want) (setq out (cons c out))))
  (reverse out))

;; The candidate nearest PK, when one sits within SNAP of it.  A typed
;; number never comes here - a name is exact.
(defun pf:cand-nearest (pk cands snap / best bd c d)
  (setq best nil bd nil)
  (foreach c cands
    (setq d (distance (pf:2d pk) (pf:2d (car c))))
    (if (and (<= d snap) (or (null bd) (< d bd)))
      (setq best c bd d)))
  best)

;; A survey point, clicked or typed.  One prompt takes both: (initget
;; 128) is arbitrary input, which hands typed text back from getpoint as
;; the string it is where a click comes back as the point it is.  The
;; misses are re-asked HERE rather than unwinding the caller's chain --
;; a number nothing carries and a click on nothing are typos, not
;; answers, and the question they belong to is this one.  TAIL is the
;; prose inside the angle brackets on a prompt whose Enter means
;; something - "Enter = done", the point Enter takes - and nil when a
;; point is required.  CANDS are the (position name) candidates and
;; SNAP how close a click has to land.  Returns the candidate, nil for
;; Enter, or PF-BACK.
(defun pf:askpoint (msg tail back cands snap / v out done dupes)
  (setq done nil out nil)
  (while (not done)
    (if back
      (initget (if tail 128 129) "Back Undo")
      (initget (if tail 128 129)))
    (setq v (getpoint (strcat "\n" msg
                              (if back " [Back]" "")
                              (if tail (strcat " <" tail ">") "")
                              ": ")))
    (if lzd:ask (lzd:ask msg v) v)
    (cond
      ((null v)
       (if tail
         (setq out nil done T)
         (princ "\nA survey point is required - click one, or type its number.")))
      ((and (= (type v) 'STR) (member v '("Back" "Undo")))
       (setq out 'PF-BACK done T))
      ((= (type v) 'STR)
       (setq dupes (pf:cand-matches v cands))
       (cond
         ((null dupes)
          (princ (strcat "\nNo survey point is numbered \""
                         (pf:as-number v)
                         "\" - try again, or click the point itself.")))
         ((> (length dupes) 1)
          (princ (strcat "\n" (itoa (length dupes)) " points are numbered \""
                         (pf:as-number v)
                         "\" - click the one you mean.")))
         (t (setq out (car dupes) done T))))
      (t
       (setq out (pf:cand-nearest v cands snap))
       (if out
         (setq done T)
         (princ (strcat "\nNo survey point there - click one, or type"
                        " its number."))))))
  out)

;; Every survey point in the DRAWING as a candidate, for the questions
;; asked before the selection exists (steps 4 to 6).  The classifier is
;; the selection's own: an ab_pt INSERT wherever it sits, any other
;; INSERT on the POINTS layer, a plain POINT on that layer - and a
;; moved point is left out here as it is there, since a declaration on
;; a point that is not in the fit declares nothing.  A point with no
;; readable number is called "?": it can be clicked, not typed.
(defun pf:collect-points ( / ss i en ed typ nm out)
  (setq out nil
        ss  (ssget "_X" '((0 . "INSERT,POINT"))))
  (if ss
    (progn
      (setq i 0)
      (repeat (sslength ss)
        (setq en  (ssname ss i)
              ed  (entget en)
              typ (cdr (assoc 0 ed))
              nm  nil)
        (cond
          ((= typ "INSERT")
           (if (or (= (strcase (cdr (assoc 2 ed)))
                      (strcase *PF-POINT-BLOCK*))
                   (= (strcase (cdr (assoc 8 ed)))
                      (strcase *PF-POINT-LAYER*)))
             (progn
               (setq nm (pf:block-number en))
               (if (not (pf:moved-p nm))
                 (setq out (cons (list (pf:2d (pf:ins-w ed))
                                       (if (and nm (/= nm "")) nm "?"))
                                 out))))))
          ((= typ "POINT")
           (if (= (strcase (cdr (assoc 8 ed)))
                  (strcase *PF-POINT-LAYER*))
             (setq out (cons (list (pf:2d (cdr (assoc 10 ed))) "?")
                             out)))))
        (setq i (1+ i)))))
  (reverse out))

;; The candidates for points already in hand - the selection's, or the
;; omit list's - named the way the report names them.
(defun pf:cands-of (qs)
  (mapcar '(lambda (q) (list q (pf:pt-name q))) qs))

;; T when the named point is one of DPTS.  When it is not, the WHAT
;; declared on it is named and dropped: it is a declaration about a
;; point the fit does not hold - never selected, or left out at step 8
;; - and never a near miss to be snapped onto some other point.  Which
;; of the two it was is worth saying: a wall dropped because the
;; drafter themselves left its end out reads very differently from one
;; dropped because the selection missed it.
(defun pf:declared-in (cand dpts what)
  (if (pf:memb (car cand) dpts)
    T
    (progn
      (princ (strcat "\n  (Pt." (cadr cand)
                     (if (pf:memb (car cand) (mapcar 'car pf-omitted))
                       " was left out of the fit"
                       " is not among the selected points")
                     " - the " what " declared on it is dropped)"))
      nil)))

;; The second end of a wall from C1: required, and a different point
;; from C1 - the same one again is refused and re-asked where it
;; stands.  Returns the candidate or PF-BACK.
(defun pf:ask-wall-end (c1 cands / c2)
  (setq c2 (pf:askpoint (strcat "  Second end, from Pt." (cadr c1)
                                " - pick it or type its number")
                        nil T cands *PF-SNAP*))
  (while (and (not (eq c2 'PF-BACK))
              (< (pf:dist (car c1) (car c2)) *PF-EXACT-EPS*))
    (princ (strcat "\n  That is Pt." (cadr c1)
                   " again - a wall needs two different points."))
    (setq c2 (pf:askpoint (strcat "  Second end, from Pt." (cadr c1)
                                  " - pick it or type its number")
                          nil T cands *PF-SNAP*)))
  c2)

;; Index of point P in TOUR (exact-point fuzz), or nil.
(defun pf:tour-index (p tour / i k q)
  (setq i nil k 0)
  (foreach q tour
    (if (and (null i) (< (pf:dist p q) *PF-EXACT-EPS*)) (setq i k))
    (setq k (1+ k)))
  i)

;; Rotate the closed TOUR so it starts at point P (used so a declared
;; straight wall never straddles the walk's origin).
(defun pf:rotate-to-point (tour p / i)
  (setq i (pf:tour-index p tour))
  (if (and i (> i 0))
    (append (pf:nthcdr i tour) (pf:sublist tour 0 i))
    tour))

;; Rotate the closed TOUR so it starts at its sharpest turn: the fitter
;; walks the loop from there, so the most corner-like point is always a
;; span endpoint and never gets buried inside a span.
(defun pf:rotate-to-corner (tour / n i prev cur next turn best bi)
  (setq n (length tour) i 0 best -1.0 bi 0)
  (repeat n
    (setq prev (nth (rem (+ i n -1) n) tour)
          cur  (nth i tour)
          next (nth (rem (1+ i) n) tour)
          turn (abs (pf:signed-dang (angle prev cur) (angle cur next))))
    (if (> turn best) (setq best turn bi i))
    (setq i (1+ i)))
  (append (pf:nthcdr bi tour) (pf:sublist tour 0 bi)))

;; Number of curved segments in a span list.
(defun pf:arc-count (spans / c sp)
  (setq c 0)
  (foreach sp spans (if (>= (abs (caddr sp)) 1.0e-9) (setq c (1+ c))))
  c)

;; ---- near-tangent span fitting ---------------------------------------
;; Arcs sit ON the survey points: every span runs from tour point to
;; tour point and its interior is fitted through the points with exact
;; 3-point arcs.  Tangency is a WINDOW, not a chain: at each joint the
;; new arc's start tangent may differ from the previous arc's end
;; tangent by at most *PF-TANG-TOL* (8 degrees), so the perimeter
;; stays visually smooth while the points stay in charge.  A bulge
;; window is a cons (lo . hi); nil means unconstrained.

;; Allowed bulge interval for the span A->B whose START tangent must
;; lie within *PF-TANG-TOL* of the incoming tangent TE.  WF stretches
;; that limit (see *PF-TANG-STEPS*).  The window edges are clamped so
;; extreme (U-turn) geometry stays finite.
(defun pf:tang-window (te a b wf / tt phi alo ahi lo hi)
  (setq tt  (* *PF-TANG-TOL* wf)
        phi (pf:signed-dang te (angle a b))
        alo (max (min (/ (- phi tt) 2.0) *PF-BULGE-CLAMP*) (- *PF-BULGE-CLAMP*))
        ahi (max (min (/ (+ phi tt) 2.0) *PF-BULGE-CLAMP*) (- *PF-BULGE-CLAMP*))
        lo  (pf:tan alo)
        hi  (pf:tan ahi))
  (if (<= lo hi) (cons lo hi) (cons hi lo)))

;; Allowed bulge interval for the CLOSING span A->B whose END tangent
;; must lie within *PF-TANG-TOL* (times WF) of the loop's start
;; tangent TS0.
(defun pf:end-window (ts0 a b wf / tt psi alo ahi lo hi)
  (setq tt  (* *PF-TANG-TOL* wf)
        psi (pf:signed-dang (angle a b) ts0)
        alo (max (min (/ (- psi tt) 2.0) *PF-BULGE-CLAMP*) (- *PF-BULGE-CLAMP*))
        ahi (max (min (/ (+ psi tt) 2.0) *PF-BULGE-CLAMP*) (- *PF-BULGE-CLAMP*))
        lo  (pf:tan alo)
        hi  (pf:tan ahi))
  (if (<= lo hi) (cons lo hi) (cons hi lo)))

;; Intersect two bulge windows.  When they don't overlap no bulge can
;; satisfy both joints, so the bulge halfway between them is used and
;; the leftover kink is split evenly across the two joints.
(defun pf:merge-windows (win win2 / lo hi)
  (cond
    ((null win) win2)
    ((null win2) win)
    (T
     (setq lo (max (car win) (car win2))
           hi (min (cdr win) (cdr win2)))
     (if (<= lo hi)
       (cons lo hi)
       (progn
         (setq lo (if (< (cdr win) (car win2))
                    (/ (+ (cdr win) (car win2)) 2.0)
                    (/ (+ (cdr win2) (car win)) 2.0)))
         (cons lo lo))))))

;; Clamp bulge B into window WIN (nil = unconstrained).
(defun pf:clamp-b (b win)
  (cond ((null win) b)
        ((< b (car win)) (car win))
        ((> b (cdr win)) (cdr win))
        (T b)))

;; Closest any of QS comes to the segment (A B bulge) - used to test
;; whether an arc still passes through one of its interior points.
(defun pf:span-min (a b bul qs / seg mn d q)
  (setq seg (list a b bul) mn nil)
  (foreach q qs
    (setq d (pf:seg-dist q seg))
    (if (or (null mn) (< d mn)) (setq mn d)))
  mn)

;; ---- how far an arc is allowed to curve ------------------------------
;; The fitter used to accept any bulge the tangent window let through,
;; and the window opens all the way to a near-full circle once the
;; incoming tangent has swung round.  On a survey with real scatter
;; that let one bad joint spiral: every arc came back a semicircle,
;; each one flinging the tangent further round, until the perimeter
;; read as a string of loops.  So an arc now has to justify its
;; curvature with the points it covers.

;; Total turning of the polyline A -> QS... -> B, in radians - how far
;; round the run of points this span sits on actually swings.
(defun pf:span-turn (a b qs / chain tot)
  (setq chain (cons a (append qs (list b)))
        tot   0.0)
  (while (cddr chain)
    (setq tot   (+ tot (abs (pf:signed-dang
                              (angle (car chain) (cadr chain))
                              (angle (cadr chain) (caddr chain)))))
          chain (cdr chain)))
  tot)

;; The steepest bulge this span's own points justify: it may sweep as
;; far as they turn, plus *PF-ARC-SLACK*.  A span between two
;; neighbours covers no turn, so it gets the slack alone.
(defun pf:max-bulge (a b qs)
  (pf:tan (min (/ (+ (pf:span-turn a b qs) *PF-ARC-SLACK*) 4.0) *PF-BULGE-CLAMP*)))

;; Clamp bulge B to +/- MX.
(defun pf:cap-b (b mx)
  (cond ((> b mx) mx) ((< b (- mx)) (- mx)) (T b)))

;; How the arc (A B BUL) treats the points QS, in one pass:
;;   (written-off  worst deviation of the rest  misses among the rest)
;; Only a point PLAINLY off - further than *PF-DROP-MULT* times TOL -
;; may be written off; that is what separates a bad shot from a
;; feature, and writing one off is what keeps a bad shot from
;; shattering the span into stubs.  A point that misses by merely a
;; little still counts against the fit, so the span stops at it as it
;; always did.  The caller rations how many may go.
(defun pf:span-score (a b bul qs tol / seg drop dev mis lim d q)
  (setq seg (list a b bul) drop 0 dev 0.0 mis 0 lim (pf:oneps))
  (foreach q qs
    (setq d (pf:seg-dist q seg))
    (if (> d (* *PF-DROP-MULT* tol))
      (setq drop (1+ drop))
      (progn
        (if (> d dev) (setq dev d))
        (if (> d lim) (setq mis (1+ mis))))))
  (list drop dev mis))

;; The points of QS this arc actually holds (within TOL) - the ones it
;; wrote off must not go on to steer the nice-radius snap.
(defun pf:span-kept (a b bul qs tol / seg out q)
  (setq seg (list a b bul))
  (foreach q qs
    (if (<= (pf:seg-dist q seg) tol) (setq out (cons q out))))
  (reverse out))

;; T when score SC beats KEY: fewer points written off, or as few and
;; a closer fit.
(defun pf:better (sc key)
  (or (< (car sc) (car key))
      (and (= (car sc) (car key)) (< (cadr sc) (cadr key)))))

;; Best bulge for the span A->B over interior points QS, restricted to
;; the tangent window WIN (nil = free) and to what the span's own
;; points justify (pf:max-bulge - no arc may come back as a loop).
;; EXACT 3-POINT ARCS COME FIRST: an unclamped 3-point bulge through
;; one of the actual interior points - so the arc's middle lands ON a
;; survey point - is preferred whenever one holds the span within TOL
;; and LEFT misses.  Compromise bulges (average / window-clamped /
;; window edges), which float between the points, are used only when
;; no exact arc works.  DLIM points may be written off - left plainly
;; off, see pf:span-score - instead of holding the span back; the
;; fewer written off the better, and a tie goes to the closer fit.
;; Returns (bulge dev misses exactflag written-off).
(defun pf:span-fit (a b qs win tol left dlim / bls m sum bl cands best
                                               bkey mx sc)
  (setq bls  (mapcar '(lambda (q) (pf:bulge-3pt a q b)) qs)
        m    (length qs)
        mx   (pf:max-bulge a b qs)
        best nil
        bkey nil)
  ;; exact candidates: through an interior point, inside the window,
  ;; and no steeper than the points themselves justify
  (foreach bl bls
    (if (and (<= (abs bl) mx)
             (or (null win)
                 (and (>= bl (car win)) (<= bl (cdr win)))))
      (progn
        (setq sc (pf:span-score a b bl qs tol))
        ;; an exact arc still has to HOLD the span - the points it did
        ;; not write off must all be inside TOL - or the compromise
        ;; bulges below never get their turn
        (if (and (<= (cadr sc) tol)
                 (<= (car sc) dlim)
                 (<= (caddr sc) left)
                 (or (null bkey) (pf:better sc bkey)))
          (setq best (list bl (cadr sc) (caddr sc) T (car sc))
                bkey sc)))))
  ;; compromise candidates, only when no exact arc holds the span
  (if (null best)
    (progn
      (setq sum 0.0)
      (foreach bl bls (setq sum (+ sum bl)))
      (setq cands (list (/ sum m) (nth (/ m 2) bls)))
      (if (>= m 4)
        (setq cands (append cands (list (nth (/ m 4) bls)
                                        (nth (/ (* 3 m) 4) bls)))))
      (if win
        (setq cands (append (mapcar '(lambda (bl) (pf:clamp-b bl win))
                                    cands)
                            (list (car win) (cdr win)
                                  (/ (+ (car win) (cdr win)) 2.0)))))
      (setq cands (mapcar '(lambda (bl) (pf:cap-b bl mx)) cands))
      (foreach bl cands
        (setq sc (pf:span-score a b bl qs tol))
        (if (or (null bkey) (pf:better sc bkey))
          (setq best (list bl (cadr sc) (caddr sc) nil (car sc))
                bkey sc)))))
  best)

;; The longest feasible span from POS, allowing DLIM of the points it
;; covers to be written off (0 = it must hold every one of them).  The
;; tangent window is stretched by degrees rather than abandoned; only
;; when even the widest step finds nothing does this return nil and
;; the stub in pf:span-loop take over.  Returns
;; (length bulge misses window written-off) or nil.
(defun pf:grow-span (tour pos te ts0 sharp nogrow lim tol left dlim pro
                     / n a best bstx steps wf len go bnd win qs lm dm
                       fr)
  (setq n     (length tour)
        a     (nth pos tour)
        best  nil
        bstx  nil
        steps *PF-TANG-STEPS*)
  (while (and (null best) steps)
    (setq wf    (car steps)
          steps (cdr steps)
          len   2
          go    T)
    (while (and go (<= len lim))
      (if (nth (rem (+ pos len -1) n) nogrow)
        (setq go nil)             ; never bury a corner or a wall point
        (progn
          (setq bnd (nth (rem (+ pos len) n) tour)
                win (if te (pf:tang-window te a bnd wf)))
          ;; the span that closes the loop must also end within the
          ;; tangent window of the loop's start
          (if (and (= (+ pos len) n) (not (car sharp)) ts0)
            (setq win (pf:merge-windows win
                                        (pf:end-window ts0 a bnd wf))))
          (setq qs (pf:sublist tour (1+ pos) (1- len))
                lm (if pro
                     (min left (pf:ceil (* (pf:misspct) len)))
                     left)
                dm (if (> dlim 0)
                     (min dlim (pf:ceil (* *PF-DROP-PCT* len)))
                     0)
                fr (pf:span-fit a bnd qs win tol lm dm))
          (if (and (<= (cadr fr) tol) (<= (caddr fr) lm)
                   (<= (nth 4 fr) dm))
            (progn
              (setq best (list len (car fr) (caddr fr) win (nth 4 fr)))
              (if (cadddr fr) (setq bstx best))
              (setq len (1+ len)))
            (setq go nil))))))
  ;; an arc that floats between the points has to earn its keep:
  ;; only take it when it covers at least 2 more points than the
  ;; longest arc that passes exactly through a point
  (if (and bstx best (< (car best) (+ (car bstx) *PF-FLOAT-GAIN*)))
    (setq best bstx))
  best)

;; Cover the rotated closed TOUR with arcs whose endpoints sit ON the
;; tour points, every joint within *PF-TANG-TOL* of tangent.  Sharp
;; corners stay free kinks.  TE0 (may be nil) seeds the first span's
;; tangent window - used to close the seam.  LEFT is the miss
;; allowance for this pass; when PRO is true each span may spend only
;; its own fair share of it, so one greedy span cannot exhaust the
;; budget and starve the rest of the loop (the curve cap turns PRO off
;; because there the whole point is to trade accuracy for few curves).
;; Straight walls the user declared (pf-walls, bound by the command as
;; snapped point pairs) are emitted verbatim as LINE spans; ordinary
;; spans may neither swallow nor cross them.  Returns the segment list.
(defun pf:span-loop (tour tol left drop te0 pro / n sharp i prev cur
                                                  next turn strtshp
                                                  segs pos te ts0 lim a
                                                  best alt len bnd win
                                                  qs bl mis sn dev0
                                                  anch phi stub walls w
                                                  i1 i2 fwd nogrow f
                                                  wrec)
  (setq n (length tour))
  ;; flag the sharp corners (intentional kinks, window resets): turns
  ;; sharper than *PF-CORNER-ANG*, plus every point the user declared
  ;; a corner - there the tangency rule is waived on purpose
  (setq sharp nil i 0)
  (repeat n
    (setq prev (nth (rem (+ i n -1) n) tour)
          cur  (nth i tour)
          next (nth (rem (1+ i) n) tour)
          turn (abs (pf:signed-dang (angle prev cur) (angle cur next))))
    (setq sharp (cons (or (> turn *PF-CORNER-ANG*)
                          (pf:memb cur pf-corners))
                      sharp)
          i     (1+ i)))
  (setq sharp (reverse sharp))
  ;; map the declared straight walls onto tour indices, walking the
  ;; short way around; the tour was rotated so none straddles index 0
  (setq walls nil)
  (foreach w pf-walls
    (setq i1 (pf:tour-index (car w) tour)
          i2 (pf:tour-index (cadr w) tour))
    (if (and i1 i2 (/= i1 i2))
      (progn
        (setq fwd (rem (+ (- i2 i1) n) n))
        (if (> (* 2 fwd) n)
          (setq i1 i2 fwd (- n fwd)))
        (if (<= (+ i1 fwd) n)
          (setq walls (cons (list i1 (+ i1 fwd)) walls))))))
  ;; indices ordinary spans may not swallow: sharp corners, every
  ;; index a declared wall covers, and every HELD point - a span may
  ;; end on a held point (landing on it exactly) but never bury it
  (setq nogrow nil i 0)
  (repeat n
    (setq f (nth i sharp))
    (foreach w walls
      (if (and (>= i (car w)) (<= i (cadr w))) (setq f T))
      (if (and (= (cadr w) n) (= i 0)) (setq f T)))
    (if (pf:memb (nth i tour) pf-holds) (setq f T))
    (setq nogrow (cons f nogrow)
          i      (1+ i)))
  (setq nogrow  (reverse nogrow)
        strtshp (car sharp)
        segs    nil
        pos     0
        te      (if strtshp nil te0)
        ts0     nil
        stub    nil)                ; was the span just emitted a stub?
  (while (< pos n)
    (setq a    (nth pos tour)
          wrec (assoc pos walls))
    (if wrec
      ;; ---- a declared straight wall starts here: emit it verbatim --
      (progn
        (setq len  (- (cadr wrec) pos)
              bnd  (nth (rem (cadr wrec) n) tour)
              qs   (pf:sublist tour (1+ pos) (1- len))
              mis  (pf:span-misses a bnd 0.0 qs)
              segs (cons (list a bnd 0.0) segs)
              left (max 0 (- left mis)))
        (if (and (null ts0) (not strtshp))
          (setq ts0 (angle a bnd)))
        (setq pos (cadr wrec)
              te  (if (and (< pos n) (nth (rem pos n) sharp))
                    nil
                    (angle a bnd))))
      ;; ---- an ordinary span --------------------------------------
      (progn
    ;; one span may never swallow the whole loop: the first span stops
    ;; one point short so the result always has at least two real
    ;; segments instead of a single zero-length one
    (setq lim  (if (= pos 0) (1- (- n pos)) (- n pos))
          best (pf:grow-span tour pos te ts0 sharp nogrow lim tol
                             left 0 pro))
    ;; Writing a point off is a last resort: it is offered only where
    ;; the span stopped growing - something is in the way - and kept
    ;; only when every point given up bought at least two more points
    ;; of span.  What may be given up at all is the narrow thing: a
    ;; point plainly off (pf:span-score), never one that merely costs
    ;; a segment.  A span that found nothing is worth one point (the
    ;; stub below), so the comparison always has a floor to beat - and
    ;; a span can never give up every point it covers.
    (if (and (> drop 0) (or (null best) (< (car best) lim)))
      (progn
        (setq alt (pf:grow-span tour pos te ts0 sharp nogrow lim tol
                                left drop pro))
        (if (and alt
                 (> (nth 4 alt) 0)
                 (>= (car alt) (+ (if best (car best) 1)
                                  (* *PF-DROP-GAIN* (nth 4 alt)))))
          (setq best alt))))
    (if (null best)
      ;; Stub to the very next point.  One stub carries the incoming
      ;; tangent on exactly, as it always has - but a stub turns its
      ;; arc twice as far as the chord ran, so a SECOND stub straight
      ;; after it doubles the mismatch, a third doubles it again, and
      ;; the bulges saturate as semicircles: that runaway is what
      ;; turned a shaky survey into spaghetti.  So once the walk is
      ;; stubbing along, a stub keeps only what the tangent window
      ;; allows and gives the rest up as a kink at the joint - and the
      ;; mismatch decays instead of running away.
      (progn
        (setq bnd (nth (rem (1+ pos) n) tour))
        (if te
          (progn
            (setq phi (pf:signed-dang te (angle a bnd)))
            (if stub
              (setq phi (max (- *PF-TANG-TOL*)
                             (min *PF-TANG-TOL* phi))))
            (setq bl (pf:tan (/ phi 2.0)))
            (if (and (= (1+ pos) n) (not strtshp) ts0)
              ;; closing stub: split the kink between both joints
              (setq bl (/ (+ bl (pf:tan (/ (pf:signed-dang (angle a bnd)
                                                           ts0)
                                           2.0)))
                          2.0)))
            (setq bl (pf:cap-b bl (pf:max-bulge a bnd nil))))
          (setq bl 0.0))
        (setq best (list 1 bl 0 nil 0)
              stub T))
      ;; nice-radius snap inside the same tangent window, over the
      ;; points the arc actually holds - the ones it wrote off must
      ;; not drag the snap around.  A snap may never pull the arc off
      ;; its points: covered points may only move a hair
      ;; (*PF-SNAP-EPS*) beyond where they already sat, an arc that
      ;; passed through an interior point must still pass through one
      ;; after snapping, and it may not curve past what the points
      ;; justify.
      (progn
        (setq len  (car best)
              bl   (cadr best)
              win  (cadddr best)
              bnd  (nth (rem (+ pos len) n) tour)
              qs   (pf:span-kept a bnd bl
                                 (pf:sublist tour (1+ pos) (1- len))
                                 tol)
              dev0 (pf:span-dev a bnd bl qs)
              anch (and qs
                        (<= (pf:span-min a bnd bl qs)
                            *PF-ANCHOR-EPS*))
              sn   (pf:snap-arc a bnd bl qs
                                (max dev0 *PF-SNAP-EPS*) left win))
        (if (and sn
                 (<= (abs (car sn)) (pf:max-bulge a bnd qs))
                 (or (not anch)
                     (<= (pf:span-min a bnd (car sn) qs)
                         *PF-ANCHOR-EPS*)))
          (setq best (list len (car sn) (cdr sn) win (nth 4 best))))
        (setq stub nil)))
    (setq len  (car best)
          bl   (cadr best)
          mis  (caddr best)
          bnd  (nth (rem (+ pos len) n) tour)
          segs (cons (list a bnd bl) segs)
          left (- left mis)
          drop (- drop (nth 4 best)))
    (if (and (null ts0) (not strtshp))
      (setq ts0 (- (angle a bnd) (* 2.0 (atan bl)))))
    (setq pos (+ pos len)
          te  (if (nth (rem pos n) sharp)
                nil
                (+ (angle a bnd) (* 2.0 (atan bl))))))))
  (reverse segs))

;; Tangent mismatch at the loop's closing joint (radians).
(defun pf:seam-kink (segs / sl sf te ts)
  (setq sl (last segs)
        sf (car segs)
        te (+ (angle (car sl) (cadr sl)) (* 2.0 (atan (caddr sl))))
        ts (- (angle (car sf) (cadr sf)) (* 2.0 (atan (caddr sf)))))
  (abs (pf:signed-dang te ts)))

;; One full fit; if the seam closes with more than *PF-TANG-TOL* of
;; kink, refit once seeding the first span's window with the arrival
;; tangent, and keep whichever seam is straighter.  The on-the-shape
;; threshold is bound here so it tracks this pass's tolerance.
(defun pf:fit-pass (tour tol left drop pro / segs k1 sl te0 segs2
                                             pf-on-eps)
  (setq pf-on-eps (max *PF-ON-EPS* (* *PF-ON-FRAC* tol))
        segs      (pf:span-loop tour tol left drop nil pro)
        k1        (pf:seam-kink segs))
  (if (> k1 (+ *PF-TANG-TOL* 0.001))
    (progn
      (setq sl    (last segs)
            te0   (+ (angle (car sl) (cadr sl))
                     (* 2.0 (atan (caddr sl))))
            segs2 (pf:span-loop tour tol left drop te0 pro))
      (if (< (pf:seam-kink segs2) k1) (setq segs segs2))))
  segs)

;; Points-only / ordering-sketch fit: arcs on the points, joints
;; within *PF-TANG-TOL* of tangent, nice radii.  LEFT is the miss
;; allowance the walk may spend and PRO whether each span is held to
;; its own fair share of it - lifting both is what buys long arcs at
;; an unchanged tolerance, which is how the "few" candidate trades
;; curves for nothing but slack the user already granted.  MAXARCS,
;; when set, is enforced by refitting the whole loop with a
;; progressively relaxed tolerance, which keeps the tangent windows
;; intact.  The fewest-curves result seen is kept, so an unreachably
;; small cap still returns the smallest fit possible - never the
;; biggest.
(defun pf:coarse-loop (tour tol maxarcs left drop pro / segs segs2 tol2
                                                        tries)
  ;; start the walk at a declared wall or corner when there is one, so
  ;; neither straddles the walk's origin; otherwise at the sharpest turn
  (setq tour (cond
               (pf-walls   (pf:rotate-to-point tour (car (car pf-walls))))
               (pf-corners (pf:rotate-to-point tour (car pf-corners)))
               (T          (pf:rotate-to-corner tour)))
        segs (pf:fit-pass tour tol left drop pro))
  ;; the cap deliberately buys few curves with accuracy, so the refits
  ;; drop both the miss allowance and the per-span fair share
  (if maxarcs
    (progn
      (setq tol2 tol tries 0)
      (while (and (> (pf:arc-count segs) maxarcs) (< tries *PF-CAP-TRIES*))
        (setq tol2  (* tol2 *PF-CAP-RELAX*)
              tries (1+ tries)
              segs2 (pf:fit-pass tour tol2 1000000 drop nil))
        (if (< (pf:arc-count segs2) (pf:arc-count segs))
          (setq segs segs2)))))
  segs)

;; ---- self-intersection check -----------------------------------------
;; A loop that crosses itself almost always means the automatic point
;; ordering went around a narrow waist the wrong way.  We cannot fix
;; that from the points alone, but we can spot it and say so.

;; Cross product of (P-O) x (Q-O); its sign says which side Q is on.
(defun pf:cross3 (o p q)
  (- (* (- (car p) (car o)) (- (cadr q) (cadr o)))
     (* (- (cadr p) (cadr o)) (- (car q) (car o)))))

;; T when segments A-B and C-D properly cross.  Touching or shared
;; endpoints give a zero product and do not count.
(defun pf:segs-cross (a b c d / d1 d2 d3 d4)
  (setq d1 (pf:cross3 a b c) d2 (pf:cross3 a b d)
        d3 (pf:cross3 c d a) d4 (pf:cross3 c d b))
  (and (< (* d1 d2) 0.0) (< (* d3 d4) 0.0)))

;; Sample the fitted loop into a point list; arcs get intermediate
;; points so a bulging arc's real path is tested, not just its chord.
(defun pf:loop-pts (segs / out s g c r a1 a2 sweep k j aa)
  (setq out nil)
  (foreach s segs
    (setq out (cons (pf:2d (car s)) out))
    (if (>= (abs (caddr s)) 1.0e-9)
      (progn
        (setq g (pf:arc-geom (car s) (cadr s) (caddr s)))
        (if g
          (progn
            (setq c  (car g)   r  (cadr g)
                  a1 (caddr g) a2 (cadddr g))
            (if (> (caddr s) 0.0)
              (setq sweep (pf:norm-ang (- a2 a1)))
              (setq sweep (- (pf:norm-ang (- a1 a2)))))
            (setq k 4 j 1)
            (while (< j k)
              (setq aa  (+ a1 (* sweep (/ (float j) (float k))))
                    out (cons (list (+ (car c) (* r (cos aa)))
                                    (+ (cadr c) (* r (sin aa))))
                              out)
                    j   (1+ j))))))))
  (reverse out))

;; T when the fitted loop crosses itself.
(defun pf:self-crosses (segs / p n found ti tj i j a b c d)
  (setq p (pf:loop-pts segs))
  (if (< (length p) 4)
    nil
    (progn
      (setq p     (append p (list (car p)))  ; close the point ring
            n     (1- (length p))            ; number of chords
            found nil
            ti    p
            i     0)
      (while (and (not found) (< i (- n 2)))
        (setq a  (car ti)
              b  (cadr ti)
              tj (cddr ti)
              j  (+ i 2))
        (while (and (not found) (< j n))
          (setq c (car tj) d (cadr tj))
          ;; the first and last chords legitimately share a vertex
          (if (not (and (= i 0) (= j (1- n))))
            (if (pf:segs-cross a b c d) (setq found T)))
          (setq tj (cdr tj) j (1+ j)))
        (setq ti (cdr ti) i (1+ i)))
      found)))

;; ---- output helpers --------------------------------------------------
;; Create the output layer, or - when it already exists - make sure it
;; is on, thawed and unlocked.  Without this a successful run onto a
;; frozen or switched-off layer looks like the command did nothing.
(defun pf:ensure-layer (name colour / rec ed flags col fixed)
  (if (not (tblsearch "LAYER" name))
    (entmakex (list '(0 . "LAYER") '(100 . "AcDbSymbolTableRecord")
                    '(100 . "AcDbLayerTableRecord")
                    (cons 2 name) '(70 . 0) (cons 62 colour)
                    '(6 . "Continuous")))
    (progn
      (setq rec   (tblobjname "LAYER" name)
            ed    (entget rec)
            flags (cdr (assoc 70 ed))
            col   (cdr (assoc 62 ed))
            fixed nil)
      (if (/= 0 (logand 5 flags))          ; frozen (1) or locked (4)
        (setq ed    (subst (cons 70 (- flags (logand 5 flags)))
                           (assoc 70 ed) ed)
              fixed T))
      (if (< col 0)                        ; layer switched off
        (setq ed    (subst (cons 62 (abs col)) (assoc 62 ed) ed)
              fixed T))
      (if fixed
        (progn
          (entmod ed)
          (princ (strcat "\nABHD: layer " name
                         " was off, frozen or locked - restored so the"
                         " result is visible.")))))))

;; How many fitted polylines are already on the output layer (counted
;; before the new one is drawn).
(defun pf:prior-fits (/ ss)
  (setq ss (ssget "_X" (list (cons 8 *PF-OUT-LAYER*)
                             '(0 . "LWPOLYLINE"))))
  (if ss (sslength ss) 0))

;; T when R is a whole multiple of one of the *PF-NICE-RADII* tiers.
(defun pf:nice-radius-p (r / found tier q)
  (setq found nil)
  (if (and r (< r *PF-STRAIGHT-R*))
    (foreach tier *PF-NICE-RADII*
      (setq q (/ r tier))
      (if (< (abs (- q (fix (+ q 0.5)))) 1.0e-6) (setq found T))))
  found)

;; verts: list of (pt bulge) in order, closed.  COL is an AutoCAD
;; colour index, or nil for BYLAYER.
(defun pf:make-pline (verts layer col / dxf v)
  (setq dxf (list '(0 . "LWPOLYLINE") '(100 . "AcDbEntity")
                  (cons 8 layer)))
  (if col (setq dxf (append dxf (list (cons 62 col)))))
  (setq dxf (append dxf (list '(100 . "AcDbPolyline")
                              (cons 90 (length verts)) '(70 . 1))))
  (foreach v verts
    (setq dxf (append dxf (list (cons 10 (car v)) (cons 42 (cadr v))))))
  (entmakex dxf))

;; The kept fit joins the POOL layer in ByLayer colour: the preview
;; colour and the preview layer both belonged to the comparison - the
;; result belongs with the pool.
(defun pf:set-bylayer (en / ed)
  (pf:ensure-layer *PF-POOL-LAYER* *PF-POOL-COLOUR*)
  (setq ed (entget en)
        ed (subst (cons 8 *PF-POOL-LAYER*) (assoc 8 ed) ed))
  (if (assoc 62 ed) (setq ed (subst '(62 . 256) (assoc 62 ed) ed)))
  (entmod ed))

;; Pad S with spaces to width W, for the comparison table.
(defun pf:pad (s w)
  (while (< (strlen s) w) (setq s (strcat s " ")))
  s)

;; The points SEGS fails to hold within TOL.
(defun pf:unheld (segs pts tol / out q s d dmin)
  (setq out nil)
  (foreach q pts
    (setq dmin nil)
    (foreach s segs
      (setq d (pf:seg-dist q s))
      (if (or (null dmin) (< d dmin)) (setq dmin d)))
    (if (> dmin tol) (setq out (cons q out))))
  (reverse out))

;; List membership by position, within the exact-point fuzz.
(defun pf:memb (q lst / found p)
  (setq found nil)
  (foreach p lst
    (if (< (pf:dist p q) *PF-EXACT-EPS*) (setq found T)))
  found)

(defun pf:isect (a b / out q)
  (setq out nil)
  (foreach q a
    (if (pf:memb q b) (setq out (cons q out))))
  (reverse out))

;; ---- temporary preview geometry --------------------------------------
;; Everything ABHD draws to help you decide - the dashed straight-wall
;; markers, the three candidate outlines, their number labels - is
;; scaffolding, not a result.  Each piece is registered here as it is
;; created and swept away when the command ends, whether that is
;; normally, by ESC, or by an error, so no run leaves litter behind.
;; Whatever the user chooses to keep is dropped from the list first.

(defun pf:temp-add (en)
  (if en (setq pf-temp (cons en pf-temp)))
  en)

(defun pf:temp-drop (en / out x)
  (setq out nil)
  (foreach x pf-temp
    (if (not (eq x en)) (setq out (cons x out))))
  (setq pf-temp (reverse out))
  en)

;; entget returns nil for something already gone, so a piece erased
;; earlier is simply skipped instead of raising an error
(defun pf:temp-clear ( / en)
  (foreach en pf-temp
    (if (and en (entget en)) (entdel en)))
  ;; the length ruler is scaffolding too, and this is the one call
  ;; every handler and every clean exit already makes.  Its STATE goes
  ;; with it: taking the rows down keeps the style, the ft-in family and
  ;; the hint-said flag, so without the reset a ruler colour retuned in
  ;; LAZTUNE looked ignored until the drawing was reopened, and an
  ;; inch drafter's next run labelled its rows in ft-in
  (pf:rulerkill)
  (setq pf:*ruler* nil
        pf-temp    nil))

;; Scaffolding removed early - when a Back re-opens the step that
;; drew it - rather than at command end.
(defun pf:temp-kill (en)
  (if (and en (entget en)) (entdel en))
  (pf:temp-drop en))

;;; -------------------- the length ruler --------------------------------
;;;  DIMSTAMP's ruler, as a helper any LENGTH prompt can stand beside.
;;;  Once a first length has been given, the prompt draws the eighths
;;;  of an inch for a whole inch either side of the last one down a
;;;  strip near the right edge of the view, graded like a tape with the
;;;  last length ringed in the middle -- and one prompt then takes a
;;;  click on a row (that row's value), a typed measurement in any
;;;  spelling (44, 44.5, 44-1/2, 4'4.5, 4'-4-1/2"), Enter, a keyword,
;;;  or a click on empty space as the first of two points to measure
;;;  between, which is what getdist always offered.  A run of
;;;  near-equal lengths is clicked rather than typed over and over.
;;;  The fractions are DASHED because the prompt is a getpoint, where
;;;  the spacebar is Enter: 44 1/2 is two answers there, 44 to this
;;;  question and 1/2 to the next, so a bare fraction is refused
;;;  rather than taken as a length of its own.
;;;
;;;  PERPPTS, CPERPPTS, PERPMARK, CORNERSTP, HEMISTEP and NORMIESTEP
;;;  ask their lengths through it.  Each carries this block under its
;;;  own prefix so the standalone file loads alone, the grouped build
;;;  swaps the copy for the library's, and tests/test_ruler_copies.py
;;;  holds every copy to this one text.  DIMSTAMP keeps its own ruler:
;;;  its current row is drawn as the stamp it would make, on the
;;;  stamp's layer in the stamp's style, which is a different thing
;;;  from a row of nearby lengths.
;;;
;;;  A ruler comes in two families, and the prompt picks which.
;;;
;;;  The TAPE is the one above: the eighths of an inch for a whole inch
;;;  either side of the LAST answer, which is what a run of near-equal
;;;  numbers wants.  It needs a last answer to be built round, so the
;;;  first prompt of a run stands alone.
;;;
;;;  The LADDER is the other: a fixed (LO HI STEP) of the values that
;;;  prompt is actually answered with, every one of them offered from
;;;  the first prompt on.  A corner radius is 3" to 2'-0" by 3" and a
;;;  tape of eighths round nothing helps nobody -- 3, 6, 9, 12 is the
;;;  whole vocabulary, and a drafter picks out of it rather than types
;;;  into it.  Its rows are graded off the VALUE, not off a distance
;;;  from the current row: the foot marks are the deep ones and the
;;;  half-foot next, which is where a tape's deep marks are too.  A
;;;  ladder still takes a typed measurement that is not on it, and the
;;;  answer is then ringed among the rungs as the current row.
;;;
;;;  Nothing in here reads a knob.  A tool hands its knobs in as one
;;;  STYLE list and keeps the ruler between prompts as one STATE list:
;;;    STYLE  (COLOR CURRENT-COLOR SCREEN-X ROW-FRAC TXT-FRAC TICK-FRAC
;;;            RING-FRAC REACH) -- a caller's tunables block says what
;;;            each one moves
;;;    STATE  (LEN FEET ENTS BOX ROWS LAY STYLE SAID LADDER) -- the
;;;            length the ruler stands round (nil = none), the family it
;;;            is labelled in (T = feet), what is drawn, its layer, the
;;;            style, whether the one-line hint has been said, and the
;;;            ladder it is standing on (nil = a tape)
;;;  Values are INCHES, the unit this shop draws in, and the ruler
;;;  steps in eighths of one, which is what a tape reads in.

;; T when C is 0-9.
(defun pf:len-digit-p (c)
  (and (>= (ascii c) 48) (<= (ascii c) 57)))

;; T when S reads as a plain decimal number: digits, at most one dot,
;; at least one digit, nothing else.
(defun pf:len-num-p (s / i n c dots digits ok)
  (setq n (strlen s) i 1 dots 0 digits 0 ok T)
  (while (and ok (<= i n))
    (setq c (substr s i 1))
    (cond
      ((pf:len-digit-p c) (setq digits (1+ digits)))
      ((= c ".") (setq dots (1+ dots)))
      (T (setq ok nil)))
    (setq i (1+ i)))
  (and ok (> digits 0) (< dots 2)))

;; S cut on spaces, tabs and dashes, empty pieces dropped -- the
;; separators an inches part is written with, so "4 1/2" and "4-1/2"
;; come apart the same way.  It cuts a keyword list the same way.
(defun pf:len-split (s / i n c buf out)
  (setq n (strlen s) i 1 buf "" out nil)
  (while (<= i n)
    (setq c (substr s i 1))
    (if (or (= c " ") (= c "\t") (= c "-"))
      (progn
        (if (/= buf "") (setq out (cons buf out)))
        (setq buf ""))
      (setq buf (strcat buf c)))
    (setq i (1+ i)))
  (if (/= buf "") (setq out (cons buf out)))
  (reverse out))

;; One token of an inches part -- a decimal number, or a fraction N/D
;; -- as a number of inches.  nil when it is neither.
(defun pf:len-token (tok / slash n d)
  (if (setq slash (vl-string-search "/" tok))
    (progn
      (setq n (substr tok 1 slash)
            d (substr tok (+ slash 2)))
      (if (and (pf:len-num-p n) (pf:len-num-p d) (/= (atof d) 0.0))
        (/ (atof n) (atof d))))
    (if (pf:len-num-p tok) (atof tok))))

;; The inches part of a measurement as a number of inches: every token
;; added up, so "4", "4.5", "4 1/2", "4-1/2" and "1/2" all read.  An
;; empty part is 0, which is how 4' reads as 4'-0".  nil when any
;; token is neither a number nor a fraction.
(defun pf:len-inches (s / toks total v tk)
  (setq toks (pf:len-split s) total 0.0)
  (foreach tk toks
    (if (and total (setq v (pf:len-token tk)))
      (setq total (+ total v))
      (setq total nil)))
  total)

;; Read a typed measurement as (INCHES HASFEET): the length in inches,
;; exactly as typed and NOT rounded, and T when feet were spelled --
;; carried through so the ruler is labelled in the family the length
;; was typed in.  Lenient, the way DIMSTAMP reads: the inch mark is
;; optional and may be two apostrophes, the dash after the feet mark is
;; optional, inches may be decimal, and a fraction may be spaced or
;; dashed -- 44, 44.5, 44 1/2, 4'4.5 and 4'-4 1/2" all read.  nil when
;; the text is not a measurement at all.
(defun pf:parse-len (s / n apos feetstr rest hasfeet feet inch)
  (setq s (vl-string-trim " \t" s)
        n (strlen s))
  (cond
    ((and (>= n 2) (= (substr s (1- n) 2) "''"))
     (setq s (substr s 1 (- n 2))))
    ((and (>= n 1) (= (substr s n 1) "\""))
     (setq s (substr s 1 (1- n)))))
  (setq s (vl-string-trim " \t" s) hasfeet nil feet 0.0)
  (if (setq apos (vl-string-search "'" s))
    (progn
      (setq feetstr (vl-string-trim " \t" (substr s 1 apos))
            rest    (vl-string-trim " \t-" (substr s (+ apos 2))))
      (if (pf:len-num-p feetstr)
        (setq feet (atof feetstr) hasfeet T)
        (setq rest nil)))
    (setq rest (vl-string-trim " \t" s)))
  (setq inch (if rest (pf:len-inches rest)))
  (if (and inch (or hasfeet (/= rest "")))
    (list (+ (* feet 12.0) inch) hasfeet)))

;; INCHES to the nearest eighth, as an integer count of eighths -- the
;; unit the ruler is built in.
(defun pf:len-eighths (inches)
  (fix (+ 0.5 (* 8.0 inches))))

;; Spell TOTAL-EIGHTHS out as text, in the HASFEET family.  STACKED nil
;; is the PLAIN spelling ("44 1/2\"", what the command line says);
;; STACKED T is the DRAWN one, the fraction stacked through AutoCAD's
;; \S code at the size of the text around it, for a ruler label and
;; nothing else.
(defun pf:spell-len (total-eighths hasfeet stacked / feet remain whole f8
                         g num den fr)
  (if hasfeet
    (setq feet   (/ total-eighths 96)
          remain (- total-eighths (* feet 96)))
    (setq feet 0 remain total-eighths))
  (setq whole (/ remain 8)
        f8    (- remain (* whole 8))
        num   0
        den   1)
  (if (/= f8 0)
    (progn
      (setq g (gcd f8 8))
      (setq num (/ f8 g) den (/ 8 g))))
  (setq fr (cond
             ((= num 0) "")
             ((null stacked) (strcat " " (itoa num) "/" (itoa den)))
             (T (strcat "{\\H1.0000x;\\S" (itoa num) "/" (itoa den) ";}"))))
  (strcat (if (and stacked (/= num 0)) "\\A1;" "")
          (if hasfeet (strcat (itoa feet) "'-") "")
          (itoa whole) fr "\""))

;; What to say when something typed is not a length at all.  The
;; examples are the lazy spellings on purpose: the ones worth showing
;; are the ones that save keystrokes.  A fraction is shown DASHED, never
;; spaced: at a click-or-type prompt the spacebar is Enter, so 44 1/2
;; entered 44 and handed the 1/2 to the next question as half an inch.
(defun pf:len-unread (v)
  (princ (strcat "\n\"" v "\" is not a length - try 44, 44.5, 44-1/2,"
                 " 4'4.5 or 4'-4-1/2\".")))

;; The RULER TIER an offset of OFFSET eighths from the current value
;; falls in -- 'jump for a whole inch, 'half/'quarter/'eighth for the
;; finer steps, biggest to smallest; a row's tick length and text
;; height read off it.
(defun pf:ruler-tier (offset / a m)
  (setq a (abs offset) m (rem a 8))
  (cond
    ((= m 0) 'jump)
    ((= m 4) 'half)
    ((member m '(2 6)) 'quarter)
    (T 'eighth)))

;; The nearby values to offer, as (EIGHTHS TIER) pairs: every eighth
;; for a whole inch either side, and with feet in play the 2" and 3"
;; jumps beyond that as well.  A row at or below zero is dropped.
;; Unsorted -- the ruler sorts once it also has the current row.
(defun pf:ruler-rows (total-eighths hasfeet / out i off)
  (setq out nil i 1)
  (while (<= i 8)
    (setq out (cons (list (- total-eighths i) (pf:ruler-tier i)) out))
    (setq out (cons (list (+ total-eighths i) (pf:ruler-tier i)) out))
    (setq i (1+ i)))
  (if hasfeet
    (progn
      (setq i 2)
      (while (<= i 3)
        (setq off (* i 8))
        (setq out (cons (list (- total-eighths off) 'jump) out))
        (setq out (cons (list (+ total-eighths off) 'jump) out))
        (setq i (1+ i)))))
  (vl-remove-if '(lambda (pr) (<= (car pr) 0)) out))

;; The RULER TIER a LADDER rung falls in, read off the value itself
;; rather than off a distance from the current row: a whole foot is the
;; deepest mark, a half foot the next, a quarter foot after that, and
;; everything else is a plain rung.  That is where a tape's deep marks
;; are, so a ladder of radii reads as a ruler and not as a list.
(defun pf:ladder-tier (eighths)
  (cond
    ((= 0 (rem eighths 96)) 'jump)        ; a whole foot
    ((= 0 (rem eighths 48)) 'half)        ; a half foot
    ((= 0 (rem eighths 24)) 'quarter)     ; a quarter foot
    (T 'eighth)))

;; The rungs of LADDER, given as (LO HI STEP) in inches: every step from
;; LO to HI, as the same (EIGHTHS TIER) pairs a tape's rows are.  A rung
;; at or below zero is dropped, as a tape's rows are.
;;
;; A ladder is a KNOB, and a knob is whatever a drafter left in it -- a
;; string, two numbers where three were wanted, a step of zero.  So the
;; shape is read here rather than trusted: anything that is not three
;; numbers with a positive step has no rungs, and pf:ruler-show reads
;; that as no ladder.  A settings line typed wrong costs the ruler, not
;; the command.  Unsorted -- the ruler sorts once it also has the
;; current row.
(defun pf:ladder-rows (ladder / lo hi step v out)
  (setq out nil)
  (if (and (= (type ladder) 'LIST) (= 3 (length ladder))
           (numberp (car ladder)) (numberp (cadr ladder))
           (numberp (caddr ladder)) (> (caddr ladder) 0.0))
    (progn
      (setq lo   (pf:len-eighths (car ladder))
            hi   (pf:len-eighths (cadr ladder))
            step (pf:len-eighths (caddr ladder))
            v    lo)
      (if (> step 0)
        (while (<= v hi)
          (if (> v 0) (setq out (cons (list v (pf:ladder-tier v)) out)))
          (setq v (+ v step))))))
  out)

;; Ascending by value -- the comparator the ruler sorts rows with.
(defun pf:ruler-val-lt (a b) (< (car a) (car b)))

;; What the screen is showing, as (LEFT BOTTOM WIDTH HEIGHT) in drawing
;; units: VIEWSIZE is the view's height and SCREENSIZE its aspect.
;; This is what pins the ruler to the same strip of screen at any zoom.
(defun pf:ruler-view ( / ctr vh ss aspect vw)
  (setq ctr (getvar "VIEWCTR")
        vh  (getvar "VIEWSIZE")
        ss  (getvar "SCREENSIZE"))
  (setq aspect (if (and ss (listp ss) (numberp (car ss))
                        (numberp (cadr ss)) (> (cadr ss) 0))
                 (/ (float (car ss)) (float (cadr ss)))
                 1.6))                    ; no viewport to measure
  (setq vw (* vh aspect))
  (list (- (car ctr) (/ vw 2.0)) (- (cadr ctr) (/ vh 2.0)) vw vh))

;; Which way a row reaches from a spine pinned SCREEN-X of the way
;; across the view: always toward the middle, so a ruler pinned near an
;; edge is never drawn past it.  1.0 toward higher x, -1.0 lower.
(defun pf:ruler-dir (screen-x)
  (if (> screen-x 0.5) -1.0 1.0))

;; Label height for a row of this TIER, against a row spacing of GAP,
;; the biggest label being FRAC of the spacing.
(defun pf:ruler-hgt (tier gap frac / base)
  (setq base (* gap frac))
  (cond
    ((eq tier 'half) (* base 0.8))
    ((eq tier 'quarter) (* base 0.65))
    ((eq tier 'eighth) (* base 0.5))
    (T base)))                     ; 'current and 'jump

;; Tick length for a row of this TIER, same measure.
(defun pf:ruler-tick (tier gap frac / base)
  (setq base (* gap frac))
  (cond
    ((eq tier 'half) (* base 0.75))
    ((eq tier 'quarter) (* base 0.55))
    ((eq tier 'eighth) (* base 0.35))
    (T base)))                     ; 'current and 'jump

;; The ruler is laid out in the UCS -- VIEWCTR is a UCS point, and so
;; is every click the hit test reads -- and entmake takes the WORLD.
;; So each point goes through trans on its way into the drawing: under
;; a UCS whose origin a drafter has moved to the pool's corner, the
;; ruler was drawn that far away from the view it was measured off,
;; out of sight, while the prompt still answered clicks on the empty
;; strip where it should have been.

;; A ruler stroke from (X1 Y1) to (X2 Y2) on LAY in ACI colour COL.
(defun pf:ruler-line (x1 y1 x2 y2 lay col)
  (entmakex (list '(0 . "LINE") '(100 . "AcDbEntity") (cons 8 lay)
                  (cons 62 col) '(100 . "AcDbLine")
                  (cons 10 (trans (list x1 y1 0.0) 1 0))
                  (cons 11 (trans (list x2 y2 0.0) 1 0)))))

;; The ring that marks the current row.
(defun pf:ruler-ring (x y r lay col)
  (entmakex (list '(0 . "CIRCLE") '(100 . "AcDbEntity") (cons 8 lay)
                  (cons 62 col) '(100 . "AcDbCircle")
                  (cons 10 (trans (list x y 0.0) 1 0)) (cons 40 r))))

;; A ruler label: one unwrapped MTEXT of height HGT at PT in the
;; current text style, attached top left (ATT 1) or top right (3) so
;; it grows away from the spine, and running along the UCS X axis
;; (group 11, a WORLD direction) so it reads level in a plan view of
;; that UCS.
(defun pf:ruler-label (pt hgt str lay col att)
  (entmakex (list '(0 . "MTEXT") '(100 . "AcDbEntity") (cons 8 lay)
                  (cons 62 col) '(100 . "AcDbMText")
                  (cons 10 (trans (list (car pt) (cadr pt) 0.0) 1 0))
                  (cons 40 hgt) '(41 . 0.0) (cons 71 att) '(72 . 5)
                  (cons 1 str) (cons 11 (trans '(1.0 0.0 0.0) 1 0 T))
                  '(73 . 1) '(44 . 1.0))))

;; Draw the ruler down its strip of the current view round
;; TOTAL-EIGHTHS, in the HASFEET family, on layer LAY, sized and
;; coloured by STYLE: one row per suggestion plus the ringed current
;; row among them, the whole thing centred vertically in the view.
;; LADDER nil is the tape, the eighths either side of TOTAL-EIGHTHS;
;; a (LO HI STEP) is the ladder, its rungs instead.  TOTAL-EIGHTHS may
;; be nil ON A LADDER and only there -- a ladder is the values a prompt
;; is answered with and stands whether or not one has been given yet,
;; where a tape is built round the last answer and has nothing to be
;; without it.  A rung equal to the current row is dropped, so the row
;; is ringed once rather than drawn twice.
;; Returns (ENTS BOX ROWS): the entities drawn, BOX as (XMIN XMAX YTOL)
;; for the hit test, and ROWS as (EIGHTHS ROW-Y) pairs.
(defun pf:draw-ruler (total-eighths hasfeet lay style ladder / rows n i row
                          val tier y hgt tl spx ents result view vx vy vw vh
                          gap base rcol dir far near)
  (setq rows (if ladder
               (vl-remove-if '(lambda (pr) (equal (car pr) total-eighths))
                             (pf:ladder-rows ladder))
               (pf:ruler-rows total-eighths hasfeet)))
  (if total-eighths
    (setq rows (cons (list total-eighths 'current) rows)))
  (setq rows (vl-sort rows 'pf:ruler-val-lt))
  (setq view (pf:ruler-view)
        vx   (car view)  vy (cadr view)
        vw   (caddr view) vh (cadddr view))
  (setq n    (length rows)
        gap  (* vh (nth 3 style))
        spx  (+ vx (* vw (nth 2 style)))
        dir  (pf:ruler-dir (nth 2 style))   ; rows run inward
        base (- (+ vy (/ vh 2.0)) (* gap (/ (- n 1) 2.0)))
        i    0
        ents nil
        result nil)
  (foreach row rows
    (setq val  (car row) tier (cadr row))
    (setq y    (+ base (* i gap))
          hgt  (pf:ruler-hgt tier gap (nth 4 style))
          tl   (pf:ruler-tick tier gap (nth 5 style))
          rcol (if (eq tier 'current) (nth 1 style) (nth 0 style)))
    (setq ents (cons (pf:ruler-line spx y (+ spx (* dir tl)) y lay rcol)
                     ents))
    ;; half a label's height above the tick puts it astride its own
    ;; row, and the attachment turns with the row: a label on a row
    ;; that reaches left is hung by its RIGHT edge, so it grows away
    ;; from the spine rather than back across it
    (setq ents (cons (pf:ruler-label (list (+ spx (* dir (+ tl (* gap 0.35))))
                                            (+ y (/ hgt 2.0)))
                                      hgt (pf:spell-len val hasfeet T)
                                      lay rcol (if (< dir 0.0) 3 1))
                     ents))
    (if (eq tier 'current)
      (setq ents (cons (pf:ruler-ring spx y (* gap (nth 6 style)) lay rcol)
                       ents)))
    (setq result (cons (list val y) result))
    (setq i (1+ i)))
  (setq ents (cons (pf:ruler-line spx base spx (+ base (* (- n 1) gap))
                                   lay (nth 0 style))
                   ents))
  ;; the strip a click counts as a pick in: the reach on the side the
  ;; rows run, half a spacing on the other -- the tick's own side
  (setq near (+ spx (* dir gap (nth 7 style)))
        far  (- spx (* dir (/ gap 2.0))))
  (list ents
        (list (min near far) (max near far) (/ gap 2.0))
        (reverse result)))

;; The row (if any) that PT lands on: inside the ruler's strip in X and
;; close enough in Y to one of ROWS.  Returns the row's EIGHTHS, or nil
;; when PT is empty space.
(defun pf:ruler-hit (pt box rows / r best bd d)
  (setq best nil bd nil)
  (if (and box (>= (car pt) (car box)) (<= (car pt) (cadr box)))
    (foreach r rows
      (setq d (abs (- (cadr pt) (cadr r))))
      (if (and (<= d (caddr box)) (or (null bd) (< d bd)))
        (setq best (car r) bd d))))
  best)

;; A ruler that is not up yet, to draw on LAY in STYLE.
(defun pf:ruler-new (lay style)
  (list nil nil nil nil nil lay style nil nil))

;; The ruler taken down: its entities erased and forgotten.  The family
;; and the hint flag are kept, since neither is about what is drawn; the
;; ladder is not, since it is what the next prompt asks for and the next
;; prompt says so itself.
;;
;; entdel refuses on a locked layer, and it refuses quietly -- so a
;; ruler that would not come down stayed in the drawing, and every
;; redraw added another.  The tools unlock their own ruler layer before
;; drawing on it; this is the line that says so if one gets through
;; anyway (the step routines draw on the current layer), once per
;; take-down, naming the layer the rows are left on.
(defun pf:ruler-off (state / e left)
  (setq left 0)
  (foreach e (nth 2 state)
    (if (and e (entget e) (not (entdel e))) (setq left (1+ left))))
  (if (> left 0)
    (princ (strcat "
  " (itoa left) " ruler item(s) could not be"
                   " erased - layer " (vl-princ-to-string (nth 5 state))
                   " is locked.  Unlock it and ERASE them.")))
  (list nil (nth 1 state) nil nil nil (nth 5 state) (nth 6 state)
        (nth 7 state) nil))

;; The ruler the next prompt stands beside: the tape round LEN when
;; LADDER is nil, the rungs of LADDER when it is not -- with LEN ringed
;; among them when there is one.  Drawn fresh when it is not up, or is
;; up round some other length or on some other ladder; left alone when
;; it already is what was asked for; taken down when neither is given,
;; since there is then nothing to build one out of.  Whether it is UP is
;; what is drawn, not what it stands round: a ladder with no answer yet
;; stands round nothing and is up all the same.
;; The one-line hint is said the first time a run draws one.
(defun pf:ruler-show (state len ladder / rr)
  ;; a ladder nothing can be built out of is no ladder at all, and is
  ;; dropped here rather than drawn as an empty one
  (if (and ladder (null (pf:ladder-rows ladder))) (setq ladder nil))
  (cond
    ((and (null len) (null ladder)) (pf:ruler-off state))
    ((and (nth 2 state) (equal (nth 0 state) len)
          (equal (nth 8 state) ladder)) state)
    (T
     (setq state (pf:ruler-off state))
     (setq rr (pf:draw-ruler (if len (pf:len-eighths len)) (nth 1 state)
                              (nth 5 state) (nth 6 state) ladder))
     (if (not (nth 7 state))
       (princ (strcat "\n  A ruler of " (if ladder "the usual" "nearby")
                      " lengths is beside the drawing: click a row to"
                      " take it, or type a length (44, 44-1/2, 3'8).")))
     (list len (nth 1 state) (car rr) (cadr rr) (caddr rr)
           (nth 5 state) (nth 6 state) T ladder))))

;; One length prompt beside the ruler in STATE, and every way of
;; answering it: Enter (nil back, for the caller to read as it always
;; did), a keyword out of KWS (handed back as the keyword), a typed
;; measurement in any spelling pf:parse-len reads, a click on a ruler
;; row (that row's value), or a click on empty space, which is the
;; first of two points to measure the length between.  Zero, a
;; negative and text that is not a length are refused and asked again,
;; as initget 6 used to refuse them.  Returns (VALUE STATE): the
;; answer, and the ruler as it now stands.
;;
;; READER is the one thing a caller can add to the reading: a function
;; of the typed string returning inches, for a spelling this tree reads
;; somewhere and the library does not -- SPA's "600mm".  It is tried
;; AFTER the standard spellings, so a measurement written the tree's
;; way still reads the tree's way at a prompt that has one, and what it
;; returns is refused on the same terms as anything else: zero and a
;; negative are not lengths whoever read them.  nil = no such spelling,
;; which is every caller but one.
;;
;; The caller SHOWS the ruler first -- (setq rl (pf:ruler-show rl last
;; ladder) rr (pf:ask-len prompt kws rl nil) v (car rr) rl (cadr rr)) --
;; and that order is not a nicety: an Esc inside this prompt runs the
;; caller's *error*, and what that handler can take down is the ruler
;; the CALLER's state names.  A ruler drawn in here, in a state only
;; this function held, would outlive the Esc.  The caller keeps the
;; state between prompts and takes the ruler down with pf:ruler-off
;; before a prompt that does not take it and on every way out.
(defun pf:ask-len (prompt kws state reader / pk v out done toks)
  (setq done nil out nil)
  (while (not done)
    (if kws (initget 128 kws) (initget 128))
    (setq pk (getpoint prompt))
    (if lzd:ask (lzd:ask prompt pk) pk)
    (cond
      ((null pk) (setq done T))
      ((= (type pk) 'STR)
       (cond
         ((member pk (pf:len-split (if kws kws ""))) (setq out pk done T))
         ;; a leading minus is refused here, since the reader treats a
         ;; dash as the separator in 4-1/2 and would read -5 as 5
         ((= (substr (vl-string-trim " \t" pk) 1 1) "-")
          (princ "\nA length must be more than zero."))
         ;; a fraction with nothing in front of it is almost always the
         ;; tail of 44 1/2 typed with a space -- which this prompt, a
         ;; getpoint, took as Enter after 44 -- landing on the NEXT
         ;; question.  Taken, it was half an inch there, and nothing
         ;; said so.  Refused, the drafter sees what happened and can
         ;; still give half an inch as 0-1/2 or .5
         ((and (= 1 (length (setq toks (pf:len-split
                                          (vl-string-trim " \t\"'" pk)))))
               (vl-string-search "/" (car toks)))
          (princ (strcat "\n\"" pk "\" on its own?  A space ends the answer"
                         " at this prompt - type 44-1/2, or 0-1/2 for half"
                         " an inch.")))
         ((setq v (pf:parse-len pk))
          (if (> (car v) 0.0)
            (progn
              (setq out (car v) done T)
              ;; a typed spelling picks the ruler's family -- feet typed
              ;; means feet on the ruler -- and a change relabels every
              ;; row, so the one standing is taken down here.  Down, not
              ;; forgotten: a ladder stands round no length, so there is
              ;; nothing for forgetting one to redraw
              (if (not (eq (cadr v) (nth 1 state)))
                (setq state (pf:ruler-off
                              (list (nth 0 state) (cadr v) (nth 2 state)
                                    (nth 3 state) (nth 4 state) (nth 5 state)
                                    (nth 6 state) (nth 7 state)
                                    (nth 8 state))))))
            (princ "\nA length must be more than zero.")))
         ((and reader (setq v (apply reader (list pk))))
          (if (and (numberp v) (> v 0.0))
            (setq out v done T)
            (princ "\nA length must be more than zero.")))
         (T (pf:len-unread pk))))
      ((setq v (pf:ruler-hit pk (nth 3 state) (nth 4 state)))
       (setq out (/ v 8.0) done T))
      (T
       (setq v (getdist pk "\nSecond point of the length: "))
       (if lzd:ask (lzd:ask "\nSecond point of the length: " v) v)
       (if (and (numberp v) (> v 0.0))
         (setq out v done T)
         (princ "\nA length must be more than zero.")))))
  (list out state))
;;; -------------------- end of the length ruler -------------------------

;; The ruler standing beside one of the hopper offsets -- RUN STATE,
;; not a setting: it is what the run put there.  A module global rather
;; than a local of pf:get-off, because the reader is several calls down
;; from the command and what a command's *error* can take down is what
;; the command can see: Esc at an offset is the likeliest way out of
;; the question, and a ruler left standing is scratch in somebody's
;; drawing.  pf:temp-clear is where every handler and every clean exit
;; already sweeps this run's scaffolding, so that is where it goes.
(setq pf:*ruler* nil)

;; The scratch layer the rows are drawn on, made if it is missing.  A
;; layer of its own is what lets a drafter turn the ruler off without
;; turning anything of the fit off with it.
;; LOCKED is not left alone: entmake draws onto a locked layer but
;; entdel refuses there, so every ruler drawn stayed in the drawing
;; for good and each redraw added another copy -- and LAYISO's
;; lock-and-fade locks this layer with everything else.  It is
;; calofin scratch, so it is unlocked, said once, and left unlocked.
(defun pf:rulerlayer ( / ed fl)
  (if (not (tblsearch "LAYER" *PF-RULER-LAYER*))
    (entmake (list '(0 . "LAYER") '(100 . "AcDbSymbolTableRecord")
                   '(100 . "AcDbLayerTableRecord")
                   (cons 2 *PF-RULER-LAYER*) '(70 . 0) '(62 . 7)
                   (cons 6 "CONTINUOUS")))
    (progn
      (setq ed (entget (tblobjname "LAYER" *PF-RULER-LAYER*))
            fl (cdr (assoc 70 ed)))
      (if (and fl (= 4 (logand 4 fl))
               (entmod (subst (cons 70 (- fl 4)) (assoc 70 ed) ed)))
        (princ (strcat "\nABHD: layer " *PF-RULER-LAYER*
                       " was locked - unlocked so the ruler can be"
                       " taken down again.")))))
  *PF-RULER-LAYER*)

;; This file's knobs, in the order the ruler reads them.
(defun pf:ruler-style ()
  (list *PF-RULER-COLOR* *PF-RULER-CUR-COLOR* *PF-RULER-SCREEN-X*
        *PF-RULER-ROW-FRAC* *PF-RULER-TXT-FRAC* *PF-RULER-TICK-FRAC*
        *PF-RULER-RING-FRAC* *PF-RULER-REACH*))

;; Take the ruler down.  pf:temp-clear calls it, which is every
;; handler and every clean exit.
(defun pf:rulerkill ()
  (if pf:*ruler* (setq pf:*ruler* (pf:ruler-off pf:*ruler*))))

;; One prompt of PROMPT beside the ruler on LADDER, taking Back and
;; Undo where pf:back-word took them and Enter as nothing.  Returns the
;; answer in inches, 'PF-BACK, or nil for Enter -- the caller decides
;; what Enter means, as it always did.
(defun pf:ask-rung (prompt ladder back / rr v)
  (setq pf:*ruler*
          (pf:ruler-show (if pf:*ruler* pf:*ruler*
                             (pf:ruler-new (pf:rulerlayer)
                                           (pf:ruler-style)))
                         nil ladder)
        rr (pf:ask-len prompt (if back "Back Undo" nil) pf:*ruler* nil)
        v  (car rr)
        pf:*ruler* (cadr rr))
  (pf:rulerkill)
  (if (and (= (type v) 'STR) (member v '("Back" "Undo"))) 'PF-BACK v))

;; T when a typed string means "go back a step" (typed prompts cannot
;; take initget keywords, so Back is typed like a value).
(defun pf:back-word (s)
  (member (strcase s) '("B" "BACK" "U" "UNDO")))

;; T when a prompt that DOES take keywords was answered Back - or its
;; hidden synonym Undo.  getpoint/getdist/getint hand a keyword back as
;; a string where a value would be a list or a number, so the type test
;; is what separates the two.
(defun pf:back-kw (v)
  (and (= (type v) 'STR) (member v '("Back" "Undo"))))

;; ---- "this one is mine" stamping -------------------------------------
;; ABHD writes onto layers the drawing may already be using - FGStep in
;; particular - so it must never clear a layer wholesale.  Everything it
;; creates carries a small piece of extended data naming this command,
;; and only stamped objects are ever erased again.

(defun pf:tag-mine (en / ed)
  (if en
    (progn
      (regapp "ABHD")
      (setq ed (entget en))
      (entmod (append ed (list (list -3 (list "ABHD" (cons 1000 "ABHD"))))))))
  en)

;; Erase only ABHD's own objects on a layer; anything the user drew
;; there is left alone.  Returns how many went.
(defun pf:purge-mine (name / ss i n en mine stuck ed flags)
  (setq n 0 stuck 0 mine nil)
  (if (tblsearch "LAYER" name)
    (progn
      (setq ss (ssget "_X" (list (cons 8 name))))
      (if ss
        (progn
          (setq i 0)
          (repeat (sslength ss)
            (setq en (ssname ss i))
            (if (assoc -3 (entget en '("ABHD")))
              (setq mine (cons en mine)))
            (setq i (1+ i)))))
      ;; entdel answers nil on a locked layer and erases nothing, and
      ;; this layer can be the drafter's own, locked on purpose.  So the
      ;; lock is lifted for the erase and put back after it, and only an
      ;; erase that took is counted: counting the attempts said
      ;; "cleared" over markers still on screen, and the next run wrote
      ;; its own markers over them
      (if mine
        (progn
          (setq ed    (entget (tblobjname "LAYER" name))
                flags (cond ((cdr (assoc 70 ed))) (0)))
          (if (= 4 (logand 4 flags))
            (entmod (subst (cons 70 (- flags 4)) (assoc 70 ed) ed)))
          (foreach en mine
            (if (entdel en) (setq n (1+ n)) (setq stuck (1+ stuck))))
          (if (= 4 (logand 4 flags)) (entmod ed))
          (if (> stuck 0)
            (princ (strcat "\nABHD: " (itoa stuck)
                           " of its own object(s) on layer " name
                           " could not be erased - NOT removed.")))))))
  n)

;; Make sure the DASHED linetype exists (pure entmake, no command
;; calls).  Dash lengths are in drawing units - sized for an inch
;; drawing, so the dashes read at pool scale.
(defun pf:ensure-dashed ()
  (if (not (tblsearch "LTYPE" *PF-MARK-LTYPE*))
    (entmake (list '(0 . "LTYPE") '(100 . "AcDbSymbolTableRecord")
                   '(100 . "AcDbLinetypeTableRecord")
                   (cons 2 *PF-MARK-LTYPE*) '(70 . 0)
                   '(3 . "Dashed __ __ __ __ __")
                   '(72 . 65) '(73 . 2) '(40 . 18.0)
                   '(49 . 12.0) '(74 . 0)
                   '(49 . -6.0) '(74 . 0)))))

;; Draw the dashed ring marking a user-declared sharp corner.
(defun pf:draw-corner-marker (p)
  (pf:ensure-dashed)
  (pf:ensure-layer *PF-WALL-LAYER* *PF-WALL-COLOUR*)
  (entmakex (list '(0 . "CIRCLE") '(100 . "AcDbEntity")
                  (cons 8 *PF-WALL-LAYER*) (cons 6 *PF-MARK-LTYPE*)
                  '(100 . "AcDbCircle")
                  (cons 10 (list (car p) (cadr p) 0.0))
                  (cons 40 *PF-MISS-RADIUS*))))

;; Draw the marker for a user-declared HELD point: a dashed ring at
;; half the miss-ring radius, so it reads apart from corner rings.
(defun pf:draw-hold-marker (p)
  (pf:ensure-dashed)
  (pf:ensure-layer *PF-WALL-LAYER* *PF-WALL-COLOUR*)
  (entmakex (list '(0 . "CIRCLE") '(100 . "AcDbEntity")
                  (cons 8 *PF-WALL-LAYER*) (cons 6 *PF-MARK-LTYPE*)
                  '(100 . "AcDbCircle")
                  (cons 10 (list (car p) (cadr p) 0.0))
                  (cons 40 *PF-HOLD-RADIUS*))))

;; Draw the dashed marker for a user-declared straight wall.
(defun pf:draw-wall-marker (p1 p2)
  (pf:ensure-dashed)
  (pf:ensure-layer *PF-WALL-LAYER* *PF-WALL-COLOUR*)
  (entmakex (list '(0 . "LINE") '(100 . "AcDbEntity")
                  (cons 8 *PF-WALL-LAYER*) (cons 6 *PF-MARK-LTYPE*)
                  '(100 . "AcDbLine")
                  (cons 10 (list (car p1) (cadr p1) 0.0))
                  (cons 11 (list (car p2) (cadr p2) 0.0)))))

;; Bounding box of a point list, as (minx miny maxx maxy).
(defun pf:bbox (pts / x0 y0 x1 y1 q)
  (foreach q pts
    (if (null x0)
      (setq x0 (car q) x1 (car q) y0 (cadr q) y1 (cadr q))
      (setq x0 (min x0 (car q)) x1 (max x1 (car q))
            y0 (min y0 (cadr q)) y1 (max y1 (cadr q)))))
  (list x0 y0 x1 y1))

;; Draw "1", "2", "3" beside each candidate, in that candidate's own
;; colour, with that fit's numbers spelled out to the right of it - so
;; the whole choice can be made from the drawing without reading the
;; command line at all.  The labels stack down the right-hand side of
;; the shape and are sized to the drawing, so they read at any zoom.
;; Returns the list of entities that make up the label.  The figures
;; go on two lines bracketing the number, so the label stays readable
;; instead of trailing a single very long line across the drawing.
(defun pf:label (num colour bb hgt row top bot / x y out e pr)
  (setq x   (+ (caddr bb) (* 0.6 hgt))
        y   (- (cadddr bb) (* row hgt 2.1))
        out nil)
  ;; the number itself, full height
  (setq e (entmakex (list '(0 . "TEXT") '(100 . "AcDbEntity")
                          (cons 8 *PF-OUT-LAYER*) (cons 62 colour)
                          '(100 . "AcDbText")
                          (cons 10 (list x y 0.0))
                          (cons 40 hgt)
                          (cons 1 num))))
  (if e (setq out (cons e out)))
  ;; its figures, smaller, on two lines to the right of the number
  (foreach pr (list (cons top (* 0.55 hgt)) (cons bot (* -0.05 hgt)))
    (setq e (entmakex (list '(0 . "TEXT") '(100 . "AcDbEntity")
                            (cons 8 *PF-OUT-LAYER*) (cons 62 colour)
                            '(100 . "AcDbText")
                            (cons 10 (list (+ x (* 1.4 hgt))
                                           (+ y (cdr pr))
                                           0.0))
                            (cons 40 (* 0.42 hgt))
                            (cons 1 (car pr)))))
    (if e (setq out (cons e out))))
  (reverse out))

;; How far each of PTS lands from the nearest of SEGS, worst first, as
;; (distance . point) pairs - the measurement the list beside the pool
;; and the command line both read.
(defun pf:off-keyed (pts segs / out q s d dmin)
  (setq out nil)
  (foreach q pts
    (setq dmin nil)
    (foreach s segs
      (setq d (pf:seg-dist q s))
      (if (or (null dmin) (< d dmin)) (setq dmin d)))
    (setq out (cons (cons dmin q) out)))
  (reverse (pf:sort-car out)))

;; The one line that NAMES the bad points, under the list that measures
;; them.  BPCALLOUT's own wording - commas between all but the last
;; pair, "and" before the last, is/are by count - so the sentence on
;; the sheet reads the same whichever tool wrote it, led by
;; *PF-BAD-PREFIX* because here it is one of the drawing's notes:
;;
;;     "- Pt.12 is bad."
;;     "- Pt.12 and Pt.15 are bad."
;;     "- Pt.12, Pt.15 and Pt.20 are bad."
(defun pf:bad-phrase (names / n s i)
  (setq n (length names))
  (cond
    ((= n 0) "")
    ((= n 1) (strcat *PF-BAD-PREFIX* "Pt." (car names) *PF-BAD-ONE*))
    (T
     (setq s (strcat *PF-BAD-PREFIX* "Pt." (car names)) i 1)
     (while (< i (1- n))
       (setq s (strcat s ", Pt." (nth i names))
             i (1+ i)))
     (strcat s " and Pt." (nth (1- n) names) *PF-BAD-MANY*))))

;; CALOFIN-LIB.lsp's cal:ftin is this function; the copy is here because a standalone file has to load alone.
(defun pf:ftin (v mode prec / neg den tot ft n in num g)
  (setq neg  (minusp v)
        prec (max 0 (min (if (= mode 3) 6 8) prec))
        den  (if (= mode 3) (expt 10 prec) (expt 2 prec))
        tot  (fix (+ (* (abs v) den) 0.5))
        ft   (/ tot (* 12 den))
        n    (- tot (* ft 12 den))
        in   (/ n den)
        num  (- n (* in den)))
  (strcat (if (and neg (> tot 0)) "-" "")
          (itoa ft) "'-" (itoa in)
          (cond ((= mode 3)
                 (if (> prec 0) (strcat "." (substr (itoa (+ den num)) 2)) ""))
                ((= num 0) "")
                (T (setq g (gcd num den))
                   (strcat " " (itoa (/ num g)) "/" (itoa (/ den g)))))
          "\""))

;; Ring every point the chosen fit could not hold, on its own layer,
;; so they are easy to zoom to and judge: a mis-shot, a duplicate, or
;; a real feature the tolerance is too tight for.  Also writes the list
;; of them to the side of the shape, worst first, as
;; "Pt.17   off by 0'-1 7/8"" - so the misses can be worked through
;; without hunting for red circles.
;;
;; Ring every bad point and list it beside the pool with how far off it
;; landed.  BAD is what the kept fit failed to hold; OMIT is what the
;; drafter left OUT of the fit at step 8 or at a Redo.  Both are bad
;; points and both are ringed the same way: a shot the fit could not
;; reach and a shot nobody wanted it to reach are the same thing to
;; whoever has to go back out and re-shoot it.  They are listed apart
;; because only one of them is the fitter's doing - a left-out point is
;; still MEASURED against the kept line, which is the number that says
;; whether leaving it out was right.
;;
;; Under the two lists goes one line naming them all (pf:bad-phrase).
;; Returns (bad-pairs left-out-pairs), each (distance . point), worst
;; first.
(defun pf:mark-unheld (bad omit segs bb hgt / q keyed okeyed pair th x y
                                              line names)
  ;; markers from an earlier run describe a fit that no longer exists;
  ;; only ABHD's own are removed, never anything else on the layer
  (pf:purge-mine *PF-MISS-LAYER*)
  (setq keyed nil okeyed nil)
  (if (or bad omit)
    (progn
      (pf:ensure-layer *PF-MISS-LAYER* *PF-MISS-COLOUR*)
      ;; rings on the points themselves - the left-out ones included
      (foreach q (append bad omit)
        (pf:tag-mine
          (entmakex (list '(0 . "CIRCLE") '(100 . "AcDbEntity")
                          (cons 8 *PF-MISS-LAYER*) '(100 . "AcDbCircle")
                          (cons 10 (list (car q) (cadr q) 0.0))
                          (cons 40 *PF-MISS-RADIUS*)))))
      ;; how far off each one is, worst first
      (setq keyed  (pf:off-keyed bad segs)
            okeyed (pf:off-keyed omit segs)
            th     (* 0.5 hgt)
            x      (+ (caddr bb) (* 0.6 hgt))
            y      (cadddr bb))
      (pf:tag-mine
        (entmakex (list '(0 . "TEXT") '(100 . "AcDbEntity")
                        (cons 8 *PF-MISS-LAYER*) '(100 . "AcDbText")
                        (cons 10 (list x y 0.0))
                        (cons 40 th)
                        (cons 1 (strcat "POINTS OFF THE LINE ("
                                        (itoa (+ (length bad)
                                                 (length omit)))
                                        ")")))))
      ;; the off-by figure is spelled by arithmetic (cal:ftin's), not
      ;; rtos: rtos follows DIMZIN, and at 0 (acad.dwt's) it wrote
      ;; 1 7/8" for 0'-1 7/8" and 1' for 1'-0" -- the spelling the
      ;; review tools reject, in text left on the drawing
      (foreach pair (append keyed okeyed)
        (setq y    (- y (* th 1.6))
              line (strcat "Pt." (pf:pt-name (cdr pair))
                           "   off by " (pf:ftin (car pair) 4 4)
                           (if (pf:memb (cdr pair) omit)
                             *PF-OMIT-TAIL*
                             "")))
        (pf:tag-mine
          (entmakex (list '(0 . "TEXT") '(100 . "AcDbEntity")
                          (cons 8 *PF-MISS-LAYER*) '(100 . "AcDbText")
                          (cons 10 (list x y 0.0))
                          (cons 40 th)
                          (cons 1 line)))))
      ;; ...and the line that names them, under the measurements
      (setq names (mapcar '(lambda (pair) (pf:pt-name (cdr pair)))
                          (append keyed okeyed))
            y     (- y (* th 1.6)))
      (pf:tag-mine
        (entmakex (list '(0 . "TEXT") '(100 . "AcDbEntity")
                        (cons 8 *PF-MISS-LAYER*) '(100 . "AcDbText")
                        (cons 10 (list x y 0.0))
                        (cons 40 th)
                        (cons 1 (pf:bad-phrase names)))))))
  (list keyed okeyed))

;; Print the hit report for the fit the user kept.  ALLOW is the run's
;; miss allowance (how many points were permitted to sit between the
;; on-the-shape threshold and the tolerance off the result).
(defun pf:report (newsegs pts tol allow prior cmd
                  / ndist nl na hiton hitok miss
                                                q s s2 d dmin worst sum
                                                sumo no nice onpt inner
                                                ns i te ts kk mk nk
                                                hw hq pf-on-eps)
  ;; report against the same on-the-shape threshold the fit used, and
  ;; name the cap off the same count the fit was capped by (pf:build
  ;; reads the distinct points, and PTS here may hold duplicates)
  (setq pf-on-eps (max *PF-ON-EPS* (* *PF-ON-FRAC* tol))
        ndist     (length (pf:dedupe pts)))
  (progn
      ;; -- segment mix, nice radii, arcs anchored on a point --------
      (setq nl 0 na 0 nice 0 onpt 0)
      (foreach s newsegs
        (if (< (abs (caddr s)) 1.0e-9)
          (setq nl (1+ nl))
          (progn
            (setq na (1+ na))
            (if (pf:nice-radius-p
                  (pf:bulge-radius (car s) (cadr s) (caddr s)))
              (setq nice (1+ nice)))
            ;; does this arc pass through a point other than its ends?
            (setq inner nil)
            (foreach q pts
              (if (and (> (pf:dist q (car s)) *PF-EXACT-EPS*)
                       (> (pf:dist q (cadr s)) *PF-EXACT-EPS*)
                       (<= (pf:seg-dist q s) *PF-ANCHOR-EPS*))
                (setq inner T)))
            (if inner (setq onpt (1+ onpt))))))
      ;; -- how the survey points landed ------------------------------
      (setq hiton 0 hitok 0 miss 0 worst 0.0 sum 0.0 sumo 0.0 no 0)
      (foreach q pts
        (setq dmin nil)
        (foreach s newsegs
          (setq d (pf:seg-dist q s))
          (if (or (null dmin) (< d dmin)) (setq dmin d)))
        (if (> dmin worst) (setq worst dmin))
        (setq sum (+ sum dmin))
        (if (> dmin (pf:oneps))
          (setq sumo (+ sumo dmin) no (1+ no)))
        (cond
          ((<= dmin (pf:oneps)) (setq hiton (1+ hiton)))
          ((<= dmin tol)        (setq hitok (1+ hitok)))
          (T                    (setq miss  (1+ miss)))))
      ;; -- smoothness: worst kink at a joint that is not a corner ----
      (setq ns (length newsegs) i 0 mk 0.0 nk 0)
      (while (< i ns)
        (setq s  (nth i newsegs)
              s2 (nth (rem (1+ i) ns) newsegs)
              te (+ (angle (car s) (cadr s)) (* 2.0 (atan (caddr s))))
              ts (- (angle (car s2) (cadr s2)) (* 2.0 (atan (caddr s2))))
              kk (abs (pf:signed-dang te ts)))
        (if (<= kk *PF-CORNER-ANG*)     ; bigger = an intentional corner
          (progn
            (if (> kk mk) (setq mk kk))
            (if (> kk (+ *PF-TANG-TOL* 1.0e-6)) (setq nk (1+ nk)))))
        (setq i (1+ i)))
      (princ (strcat "\n" cmd ": " (itoa ns) " segments ("
                     (itoa nl) " lines + " (itoa na)
                     " curves) written to layer " *PF-POOL-LAYER* "."
                     "\n  Points on the perimeter:      " (itoa hiton)
                     "\n  Points off within tolerance:  " (itoa hitok)
                     "  (allowance " (itoa allow) ")"
                     "\n  Points beyond tolerance:      " (itoa miss)
                     "\n  Worst point deviation:        " (rtos worst 2 3)
                     "\n  Average off, all points:      "
                     (rtos (if (> (length pts) 0)
                             (/ sum (length pts))
                             0.0)
                           2 3)
                     "\n  Average off, off points only: "
                     (if (> no 0)
                       (strcat (rtos (/ sumo no) 2 3)
                               "  (" (itoa no) " point(s))")
                       "-  (every point is on the line)")
                     "\n  Curves through a point:       " (itoa onpt)
                     " of " (itoa na)
                     "\n  Curves on foot/half/inch radii:" (itoa nice)
                     " of " (itoa na)
                     "\n  Largest joint kink:           "
                     (rtos (* 180.0 (/ mk pi)) 2 1) " deg  (limit "
                     (rtos (* 180.0 (/ *PF-TANG-TOL* pi)) 2 1) ")"))
      (if (> nk 0)
        (princ (strcat "\n  (" (itoa nk)
                       " joint(s) needed more than the tangent limit to"
                       " close the loop)")))
      (if pf-walls
        (princ (strcat "\n  (" (itoa (length pf-walls))
                       " declared straight wall(s) kept dead straight)")))
      (if pf-holds
        (progn
          ;; every held point must sit ON the kept fit exactly; one
          ;; that does not means the drawn shape or a declared wall
          ;; overruled it, and that deserves a loud line of its own
          (setq hw 0.0)
          (foreach q pf-holds
            (setq dmin nil)
            (foreach s newsegs
              (setq d (pf:seg-dist q s))
              (if (or (null dmin) (< d dmin)) (setq dmin d)))
            (if (> dmin hw) (setq hw dmin hq q)))
          (if (<= hw *PF-EXACT-EPS*)
            (princ (strcat "\n  (" (itoa (length pf-holds))
                           " held point(s) all landed on the line"
                           " exactly)"))
            (princ (strcat "\n  WARNING: held Pt." (pf:pt-name hq)
                           " is off by " (rtos hw 2 4)
                           " - the drawn shape or a declared wall"
                           " overruled it.")))))
      (if pf-omitted
        (princ (strcat "\n  (" (itoa (length pf-omitted))
                       " point(s) were left OUT of the fit - they are"
                       " ringed with the ones it missed and listed"
                       "\n  beside the pool with how far off the kept"
                       " line each of them landed)")))
      (if (and (pf:cap-for ndist) (> na (pf:cap-for ndist)))
        (princ (strcat "\n  (the curve cap is "
                       (itoa (pf:cap-for ndist))
                       " but " (itoa na) " curves was the fewest"
                       " reachable: a closed loop needs at least 2"
                       " segments)")))
      (if (> miss 0)
        (princ (strcat "\n  (points beyond tolerance: given up to keep"
                       " the shape, or overruled by the curve cap"
                       " and/or the drawn shape)")))
      (if (pf:self-crosses newsegs)
        (princ (strcat "\n  WARNING: the result crosses itself - the"
                       " automatic point order is probably wrong."
                       "  Draw a rough lines-only loop on layer "
                       *PF-POOL-LAYER*
                       " through the points in the right order and"
                       " select it too.")))
      (if (> prior 0)
        (princ (strcat "\n  (" (itoa prior)
                       " earlier fit(s) were already on layer "
                       *PF-OUT-LAYER* " - erase them if you only want"
                       " the new one)"))))
  (princ))

;; ---- guided mode ------------------------------------------------------
;; Re-fit the drawn perimeter LOOP through the survey points: every
;; vertex snaps to the nearest point within TOL, every drawn arc is
;; re-fitted through the points lying along it, and drawn straight
;; walls stay straight.  TOL and FTOL are two different jobs one number
;; used to do: TOL is the reach - which point belongs to which vertex
;; and which drawn arc - and is always the distance the user typed, so
;; every candidate reads the drawn shape the same way; FTOL is how
;; exactly the re-fit then has to hold those points, and is what a
;; candidate varies.  If the result needs more curves than MAXARCS, the
;; fit falls back to the points-driven builder - the drawn loop still
;; supplies the point order.
(defun pf:guided-fit (loop pts dpts tol ftol allow drop maxarcs
                      / verts used n s p1 p2 b cands clean ns newsegs
                        q d)
  ;; -- 1. snap each vertex to its nearest point within tol ----------
  (setq verts (mapcar '(lambda (s) (car s)) loop)
        used  nil)
  (setq verts
    (mapcar
      '(lambda (v / best bd)
         (setq best nil bd tol)
         (foreach q pts
           (setq d (pf:dist v q))
           (if (and (<= d bd) (not (member q used)))
             (setq best q bd d)))
         (if best (progn (setq used (cons best used)) best) v))
      verts))
  ;; -- 2. re-fit every arc segment through the points near it -------
  (setq newsegs nil n 0)
  (repeat (length loop)
    (setq s  (nth n loop)
          p1 (nth n verts)
          p2 (nth (rem (1+ n) (length verts)) verts)
          b  (caddr s))
    (if (< (abs b) 1.0e-9)
      ;; straight wall: trust the user, keep it straight
      (setq newsegs (cons (list p1 p2 0.0) newsegs))
      (progn
        ;; survey points lying near the ORIGINAL arc, excluding the
        ;; ones already consumed as vertices, sorted along the arc and
        ;; de-duplicated
        (setq cands nil)
        (foreach q pts
          (if (and (not (member q used))
                   (<= (pf:seg-dist q s) tol)
                   (> (pf:dist q p1) *PF-EXACT-EPS*)
                   (> (pf:dist q p2) *PF-EXACT-EPS*))
            (setq cands (cons (cons (pf:seg-param q s) q) cands))))
        (setq cands (mapcar 'cdr (pf:sort-car cands)))
        (setq clean nil)
        (foreach q cands
          (if (or (null clean)
                  (> (pf:dist q (car clean)) *PF-EXACT-EPS*))
            (setq clean (cons q clean))))
        (foreach ns (pf:fit-arc-seg p1 p2 b (reverse clean) ftol)
          (setq newsegs (cons ns newsegs)))))
    (setq n (1+ n)))
  (setq newsegs (reverse newsegs))
  ;; -- 3. the drawn shape is trusted, but the curve cap still wins --
  (if (and maxarcs
           (> (pf:arc-count newsegs) maxarcs)
           (>= (length dpts) 3))
    (progn
      (princ (strcat "\n  (the drawn perimeter needs "
                     (itoa (pf:arc-count newsegs))
                     " curves but the cap is " (itoa maxarcs)
                     " - refitting from the points instead)"))
      (setq pf-miss-left allow
            newsegs (pf:coarse-loop (pf:loop-order loop dpts)
                                    ftol maxarcs allow drop T))))
  newsegs)

;; Build one candidate fit in MODE - "tight", "asked" or "few", the
;; three aims listed against *PF-COMPARE*.  A non-nil TOUR means the
;; points drive the shape (points-only and ordering-sketch modes);
;; otherwise the drawn LOOP is re-fitted (guided mode).  TOL is always
;; the distance the user typed - it is what reads the drawn shape and
;; what the table judges every candidate against - and the mode sets
;; the three knobs that actually differ:
;;
;;   FTOL  how exactly the arcs must hold their points.  "tight" fits
;;         to *PF-TIGHT-TOL* (or to TOL when that is tighter yet),
;;         which is what drives its error towards nothing and its
;;         curve count up; the other two fit to TOL.
;;   LEFT  the miss allowance.  "tight" grants none, so no point is
;;         written off; "few" lifts it (and the per-span fair share
;;         with it), which is the whole trick - the arcs run as long
;;         as TOL permits instead of stopping at the standard share,
;;         and every point is still held to TOL by the span fitter.
;;   CAP   the curve cap.  Only "asked" honours it: capping the other
;;         two would be asking for the most curves, or the fewest,
;;         and then overruling the answer.
;;
;; Each call gets its own miss allowance and on-the-shape threshold.
(defun pf:build (tour loop pts dpts tol allow mode
                 / pf-miss-left pf-on-eps ftol left cap drop)
  (setq ftol (if (= mode "tight") (min tol *PF-TIGHT-TOL*) tol)
        left (cond ((= mode "tight") 0)
                   ((= mode "few")   1000000)
                   (T                allow))
        ;; the cap's own count is the DISTINCT points - the survey as
        ;; the drafter sees it.  Not (if tour tour pts) like the drop
        ;; budget below: that one is a per-span fair share and has
        ;; always read the list it is prorating over
        cap  (if (= mode "asked") (pf:cap-for (length dpts)))
        drop (if (= mode "tight")
               0
               (pf:ceil (* *PF-DROP-PCT*
                           (length (if tour tour pts)))))
        pf-miss-left left
        pf-on-eps    (max *PF-ON-EPS* (* *PF-ON-FRAC* ftol)))
  (if tour
    (pf:coarse-loop tour ftol cap left drop (not (= mode "few")))
    (pf:guided-fit loop pts dpts tol ftol left drop cap)))

;; ---- the five SIMPABHD candidates ------------------------------------
;; ABHD asks three numbers and draws the two ends of the trade around
;; them.  SIMPABHD asks none: the two ends are the same two, and the
;; three between them are ready-made answers (*PF-SIMP-COMPARE*).  So
;; the fitter is ABHD's, unchanged - only the budgets handed to it
;; come off a table instead of off the prompts.

;; How many points a SIMPABHD row lets sit OFF the line.  A "pct" row
;; carries a share of the survey; a "hold" row carries a flat COUNT -
;; "all but the 3 worst held" is 3 points however big the survey is,
;; which is the whole point of offering it beside two shares.  The
;; tight end allows none and the few end allows every one of them.
(defun pf:row-allow (row n)
  (cond ((= (car row) "tight") 0)
        ((= (car row) "few")   n)
        ((= (car row) "hold")  (fix (nth 4 row)))
        (T                     (pf:ceil (* (nth 4 row) n)))))

;; Build one SIMPABHD candidate from its row.  The five differ only in
;; what they are ALLOWED, so they all come out of the same fitter:
;;   TOL   the row's own FIT distance, or *PF-SIMP-TOL* where it has
;;         none (the two ends borrow the distance the table is
;;         measured against, exactly as ABHD's do from step 1).  In
;;         guided mode this is pf:guided-fit's ftol, NOT its tol: that
;;         one is the radius a drawn vertex snaps to a survey point
;;         within and the reach an arc gathers its points over, and it
;;         has to stay the distance the whole table is read against.
;;         Handing the tight row its own 0.01 there would snap no
;;         vertex and gather no point, and the row whose job is the
;;         least error would come out the coarsest.  ABHD keeps the
;;         two apart for the same reason.
;;   LEFT  pf:row-allow above, with the few end's lifted to a number
;;         no survey reaches - that lift is what lets its arcs run as
;;         long as the distance permits.
;;   DROP  how many may end up PAST the distance: none for the tight
;;         end, and for a "hold" row the same count it is allowed to
;;         miss by - "all but the 3 worst held" means three points are
;;         given up, not three plus a share.
;;   CAP   only the three middle rows carry one.  Capping the row whose
;;         whole job is to draw the most curves - or the fewest -
;;         would be asking for that and then overruling the answer.
(defun pf:simp-build (tour loop pts dpts row
                      / pf-miss-left pf-on-eps kind n tol left drop cap)
  (setq kind (car row)
        n    (length dpts)
        tol  (cond ((= kind "tight") (min *PF-SIMP-TOL* *PF-TIGHT-TOL*))
                   ((nth 5 row)      (nth 5 row))
                   (T                *PF-SIMP-TOL*))
        left (if (= kind "few") 1000000 (pf:row-allow row n))
        drop (cond ((= kind "tight") 0)
                   ((= kind "hold")  (fix (nth 4 row)))
                   (T (pf:ceil (* *PF-DROP-PCT* n))))
        cap  (if (nth 6 row) (pf:div-arcs n (nth 6 row)))
        pf-miss-left left
        pf-on-eps    (max *PF-ON-EPS* (* *PF-ON-FRAC* tol)))
  (if tour
    (pf:coarse-loop tour tol cap left drop (not (= kind "few")))
    (pf:guided-fit loop pts dpts *PF-SIMP-TOL* tol left drop cap)))

;; Deviation summary for SEGS against PTS: (worst avg avg-off).
;;   worst   - furthest any point sits from the line
;;   avg     - mean over ALL points, so it counts the ones sitting on
;;             the line as the zeros they are
;;   avg-off - mean over only the points that are actually OFF the
;;             line (further than ON from it), which says how far the
;;             strays really stray; nil when nothing is off
(defun pf:devstats (segs pts on / w q s d dmin sum n sumo no)
  (setq w 0.0 sum 0.0 n 0 sumo 0.0 no 0)
  (foreach q pts
    (setq dmin nil)
    (foreach s segs
      (setq d (pf:seg-dist q s))
      (if (or (null dmin) (< d dmin)) (setq dmin d)))
    (if (> dmin w) (setq w dmin))
    (setq sum (+ sum dmin) n (1+ n))
    (if (> dmin on) (setq sumo (+ sumo dmin) no (1+ no))))
  (list w
        (if (> n 0) (/ sum n) 0.0)
        (if (> no 0) (/ sumo no) nil)))

;; A deviation for a table cell; "-" when there is nothing to average.
(defun pf:fmt-dev (x)
  (if x (rtos x 2 2) "-"))

;; ---- offer the fits and let the user pick -----------------------------
;; Knowing up front how much curve to spend on how much accuracy is the
;; hardest part of the command, so instead of asking the user to
;; imagine it, draw the two ends of that trade and the middle: the
;; most curves for the least error, the settings as typed, and the
;; fewest curves that still hold the distance.  Each goes on in its own
;; colour with what it costs, and the one they point at is kept.
;; Everything is judged against the tolerance the user actually typed,
;; so the columns compare like for like even though they were not
;; built alike.
;;
;; SIMP non-nil is SIMPABHD's five instead of ABHD's three: the same
;; screen, the same table, the same pick - built off *PF-SIMP-COMPARE*
;; and pf:simp-build rather than off the three answers.  One function
;; and not two, because everything a drafter reads here - the columns,
;; the "no fit could hold these" note, the click-or-type pick, the
;; erase-the-losers rule, Redo - is the same job either way, and the
;; way two copies of it go wrong is that one of them stops matching
;; what the other promises.
(defun pf:compare (tour loop pts dpts tol allow simp
                   / prior vars v e ent lab st onv segs bad allbad first
                     i pick idx keep ce bb hgt sel picked keyed pr res
                     tbl nfit defl kws word marks okeyed omit names nums)
  (setq prior (pf:prior-fits))
  (pf:ensure-layer *PF-OUT-LAYER* *PF-OUT-COLOUR*)
  (setq tbl  (if simp *PF-SIMP-COMPARE* *PF-COMPARE*)
        nfit (length tbl)
        defl (if simp *PF-SIMP-DEFAULT-FIT* *PF-DEFAULT-FIT*)
        word (if simp "Five" "Three")
        kws  ""
        nums nil)
  (setq i 1)
  (repeat nfit
    (setq kws  (strcat kws (itoa i) " ")
          nums (cons (itoa i) nums)
          i    (1+ i)))
  (setq kws (strcat kws "All None Redo"))
  ;; The default is a LAZTUNE knob, and LAZTUNE and LAZBACKUP put their
  ;; values in AFTER the load-time check near the top of the file, so it
  ;; is checked again here where it is used.  A "tight" or a "4" would
  ;; otherwise make Enter keep no fit at all: every outline erased, no
  ;; report, no bottom question, and nothing said.
  (if (= (type defl) 'INT) (setq defl (itoa defl)))
  (if (not (member defl nums))
    (progn
      (princ (strcat "\n  (the default-fit setting"
                     (if (= (type defl) 'STR)
                       (strcat " \"" defl "\"")
                       "")
                     " is not one of 1-" (itoa nfit)
                     " - Enter keeps fit 2)"))
      (setq defl "2")))
  ;; every candidate is judged against the distance the user typed (or,
  ;; in SIMPABHD, the one the table is read against), so "off the line"
  ;; means the same thing in every row
  (setq onv (max *PF-ON-EPS* (* *PF-ON-FRAC* tol)))
  ;; label height: a twentieth of the shape, so it reads at any zoom
  (setq bb  (pf:bbox pts)
        hgt (/ (max (- (caddr bb) (car bb))
                    (- (cadddr bb) (cadr bb)))
               *PF-LABEL-FRAC*))
  (if (<= hgt 0.0) (setq hgt 1.0))
  (setq pf-phase (strcat "building the " (strcase word T)
                         " candidate fits")
        vars     nil
        allbad   nil
        first    T
        i        1)
  (foreach v tbl
    (setq segs (if simp
                 (pf:simp-build tour loop pts dpts v)
                 (pf:build tour loop pts dpts tol allow (car v)))
          ent  (pf:temp-add
                 (pf:make-pline
                   (mapcar '(lambda (s) (list (car s) (caddr s))) segs)
                   *PF-OUT-LAYER* (cadr v)))
          bad  (pf:unheld segs pts tol)
          st   (pf:devstats segs pts onv)
          ;; the same figures the table prints, spelled out so they
          ;; stand on their own beside the number in the drawing
          lab  (pf:label
                 (itoa i) (cadr v) bb hgt i
                 (strcat (itoa (length segs)) " segs    "
                         (itoa (pf:arc-count segs)) " curves    "
                         (itoa (length bad)) " not held    "
                         (cadddr v))
                 (strcat "worst " (pf:fmt-dev (car st))
                         "    avg all " (pf:fmt-dev (cadr st))
                         "    avg off " (pf:fmt-dev (caddr st))))
          vars (cons (list segs ent bad v lab st) vars)
          i    (1+ i))
    (foreach e lab (pf:temp-add e))
    ;; the note below is about points NO fit could hold, so only the
    ;; fits actually built to the user's distance get a vote.  The
    ;; tight one threads every point by construction - counting it
    ;; would empty the intersection every time and quietly retire the
    ;; warning that catches mis-shots
    (if (not (= (car v) "tight"))
      (if first
        (setq allbad bad first nil)
        (setq allbad (pf:isect allbad bad)))))
  (setq vars (reverse vars))
  (if (null (cadr (car vars)))
    (princ "\nABHD: could not draw the result - is the drawing read-only?")
    (progn
      (princ (strcat "\n\n" word " candidate fits are now drawn on layer "
                     *PF-OUT-LAYER*
                     ",\neach numbered on screen in its own colour:\n"))
      (princ "\n   #  segs  curves  worst off  avg all  avg off  not held  ")
      (princ "\n   -  ----  ------  ---------  -------  -------  --------  ")
      (setq i 1)
      (foreach v vars
        (setq segs (car v) bad (caddr v) ce (cadddr v) st (nth 5 v))
        (princ (strcat "\n   " (itoa i) "  "
                       (pf:pad (itoa (length segs)) 6)
                       (pf:pad (itoa (pf:arc-count segs)) 8)
                       (pf:pad (pf:fmt-dev (car st)) 11)
                       (pf:pad (pf:fmt-dev (cadr st)) 9)
                       (pf:pad (pf:fmt-dev (caddr st)) 9)
                       (pf:pad (itoa (length bad)) 10)
                       (cadddr ce)))
        (setq i (1+ i)))
      (princ (strcat "\n\n  \"not held\" = points further than "
                     (rtos tol 2 3) " from that fit - some of them"
                     " given up on purpose,"
                     "\n  to keep the shape whole where holding them"
                     " would break it into stubs."
                     "\n  \"avg all\" averages every point; \"avg off\""
                     " averages only the points that are off the line"
                     "\n  (further than " (rtos onv 2 3) " from it)."))
      (if simp
        (princ (strcat "\n  All five are measured against the "
                       (rtos tol 2 3) " this command works to, but they"
                       " are not built alike:"
                       "\n  fit 1 spends curves to drive the error"
                       " towards nothing (no point given"
                       "\n  up, no cap), fit 5 holds that distance with"
                       " as few curves as it can,"
                       "\n  and 2, 3 and 4 are three ready-made answers"
                       " in between - each with its"
                       "\n  own slack and its own curve cap, printed"
                       " against it in the last column."
                       "\n  Nothing here was typed: pick the outline"
                       " that looks like the pool."))
        (princ (strcat "\n  All three are measured against the "
                       (rtos tol 2 3) " you typed, but only one is built"
                       " to it:"
                       "\n  the tight fit spends curves to drive the error"
                       " towards nothing (it"
                       "\n  ignores that distance"
                       (if (pf:cap-for (length dpts))
                         " and the curve cap" "")
                       " and gives up no point at all), the middle one is"
                       "\n  your settings exactly, and the few fit holds"
                       " the same distance with as few"
                       "\n  curves as it can - those two may write off up"
                       " to " (itoa (pf:ceil (* *PF-DROP-PCT*
                                                (length (if tour
                                                          tour
                                                          pts)))))
                       " stray point(s) between them.")))
      (if allbad
        (princ (strcat "\n  NOTE: " (itoa (length allbad))
                       " point(s) could not be held by ANY fit built to"
                       " that distance - likely a mis-shot, a duplicate,"
                       " or a corner that needs more points around it."
                       "\n  (the tight fit threads every point it can"
                       " reach, so it does not get a vote here.)")))
      ;; -- let the user choose ---------------------------------------
      ;; Clicking the outline you want beats translating a colour into
      ;; a number, so a pick on screen is offered first; typing the
      ;; number still works for anyone who prefers the keyboard.
      (setq pf-phase "waiting for the choice of fit")
      (princ "\n\n  Click the outline you want to keep, or type its number.")
      (princ (if simp
               "\n  Redo lets you leave more points out and draw the five again."
               "\n  Redo refits with new settings, and lets you leave more points out first."))
      (initget kws)
      (setq pick (getkword
                   (strcat "\n  Keep which fit - click one, or ["
                           (if simp "1/2/3/4/5" "1/2/3")
                           "/All/None/Redo] <" defl ">: ")))
      (if lzd:ask (lzd:ask (getvar "LASTPROMPT") pick) pick)
      (if (null pick)
        ;; no keyword typed: give them a click, and fall back to the
        ;; standing default
        (progn
          ;; entsel answers nil for Enter AND for a click that landed
          ;; between the thin preview lines; ERRNO 7 tells them apart.
          ;; Without asking again, a near-miss on fit 3 quietly kept the
          ;; default and erased the one they reached for.  ERRNO is
          ;; sticky, so it is cleared before each pick it is read after
          (setq sel 'RETRY)
          (while (eq sel 'RETRY)
            (vl-catch-all-apply 'setvar (list "ERRNO" 0))
            (setq sel (entsel (strcat "\n  Pick the outline to keep (or"
                                      " Enter for " defl "): ")))
            (if lzd:ask (lzd:ask (getvar "LASTPROMPT") sel) sel)
            (if lzd:watch (lzd:watch sel) sel)
            (if (and (null sel) (= 7 (getvar "ERRNO")))
              (progn
                (princ (strcat "\n  (nothing there - click one of the"
                               " outlines, or press Enter for " defl ")"))
                (setq sel 'RETRY))))
          (if sel
            (progn
              (setq picked (car sel) i 1)
              (foreach v vars
                (if (or (eq picked (cadr v))
                        (member picked (nth 4 v)))
                  (setq pick (itoa i)))
                (setq i (1+ i)))
              (if (null pick)
                (progn
                  (princ (strcat "\n  (that is not one of the "
                                 (strcase word T) " - keeping "
                                 defl ")"))
                  (setq pick defl))))
            (setq pick defl))))
      ;; anything not explicitly kept stays registered as scaffolding
      ;; and is swept when the command ends
      (cond
        ((= pick "Redo")
         ;; clear this set off the screen right away - the caller
         ;; asks its questions and draws a fresh one
         (foreach v vars
           (if (and (cadr v) (entget (cadr v))) (entdel (cadr v)))
           (foreach e (nth 4 v)
             (if (and e (entget e)) (entdel e))))
         (setq res 'REDO))
        ((= pick "All")
         (foreach v vars
           (pf:temp-drop (cadr v))
           (foreach e (nth 4 v) (pf:temp-drop e)))
         (princ (strcat "\nKeeping all " (strcase word T)
                        ", in their preview colours."))
         (princ "\n  (the number labels are kept too - erase them when done)"))
        ((= pick "None")
         (princ (strcat "\nAll " (strcase word T)
                        " erased - nothing was added to the drawing.")))
        (T
         (setq idx (atoi pick))
         ;; a number no row carries would match nothing below, and the
         ;; losers loop would then erase every fit - so it never gets
         ;; that far unannounced
         (if (not (member pick nums))
           (progn
             (princ (strcat "\n  (\"" pick "\" is not one of the "
                            (strcase word T) " - keeping " defl ")"))
             (setq pick defl idx (atoi defl))))
         (setq i 1)
         (foreach v vars
           (if (= i idx)
             (setq keep v)
             ;; erase the losers now, so the keeper is clear on screen
             ;; while the report is read
             (if (and (cadr v) (entget (cadr v))) (entdel (cadr v))))
           (setq i (1+ i)))
         ;; name the aim that was kept, not just its number - they
         ;; were built to different ends and the report that follows is
         ;; read against the settings as typed
         (if keep
           (princ (strcat "\n  Keeping fit " pick " - "
                          (cadddr (cadddr keep)) ".")))
         (if (cadr keep)
           (progn
             (pf:temp-drop (cadr keep))
             (pf:set-bylayer (cadr keep))))))
      (if keep
        (progn
          ;; the points LEFT OUT are measured against the kept line
          ;; too, and ringed with the ones it missed: both are bad
          ;; points to whoever has to go back and re-shoot one
          (setq omit   (mapcar 'car pf-omitted)
                marks  (pf:mark-unheld (caddr keep) omit (car keep)
                                       bb hgt)
                keyed  (car marks)
                okeyed (cadr marks))
          ;; the hit report is read against what the KEPT fit was
          ;; allowed.  In ABHD that is the run's own answer to step 2;
          ;; in SIMPABHD each row carries its own, so a report under
          ;; the run's would name a budget that fit never had
          (pf:report (car keep) pts tol
                     (if simp
                       (pf:row-allow (cadddr keep) (length dpts))
                       allow)
                     prior
                     (if simp "SIMPABHD" "ABHD"))
          (if keyed
            (progn
              (princ (strcat "\n  " (itoa (length keyed))
                             " point(s) beyond the distance are ringed"
                             " on layer " *PF-MISS-LAYER*
                             " and listed beside the pool, worst first:"))
              (foreach pr keyed
                (princ (strcat "\n    Pt." (pf:pt-name (cdr pr))
                               "   off by " (rtos (car pr) 4 4))))))
          (if okeyed
            (progn
              (princ (strcat "\n  " (itoa (length okeyed))
                             " point(s) you left out, ringed with them"
                             " and measured against the line you kept"
                             " - worst first:"))
              (foreach pr okeyed
                (princ (strcat "\n    Pt." (pf:pt-name (cdr pr))
                               "   off by " (rtos (car pr) 4 4)
                               *PF-OMIT-TAIL*)))))
          ;; and the one line that names them all, written beside the
          ;; pool under the measurements and echoed here
          (setq names (mapcar '(lambda (pr) (pf:pt-name (cdr pr)))
                              (append keyed okeyed)))
          (if names
            (princ (strcat "\n  " (pf:bad-phrase names))))
          ;; one perimeter was chosen, so the floor can be drawn too
          (pf:bottom (car keep) dpts T)))))
  (princ)
  res)

;; ---- the pool bottom (hopper) ----------------------------------------
;; After a perimeter is kept, the floor can be drawn in the same
;; sitting: the SHALLOW BREAK and DEEP BREAK lines across the pool,
;; and the hopper - the flat deep-end floor - as an inward offset of
;; the perimeter beyond the deep break.  Three offsets shape it,
;; asked by survey point number: one at each deep break point and one
;; at the back of the hopper, blending gradually in between when they
;; differ.  A slope line joins each of the hopper's ends to the
;; shallow break point on its side - straight, guided along the
;; perimeter's curve, or guided through points the user picks at
;; pinned offsets, asked per side.  The hopper and guided slopes are
;; drawn as few long arcs (merged within *PF-BOTTOM-FIT* - curved,
;; not faceted, not heavy).  Lines and dimensions all land on
;; *PF-POOL-LAYER*.

;; Unit vector of V, or nil when V is (near) zero-length.
(defun pf:unit (v / l)
  (setq l (sqrt (pf:dot v v)))
  (if (> l 1.0e-12) (pf:scl v (/ 1.0 l))))

;; Closest point ON segment (p1 p2 bulge) to P - pf:seg-dist's twin,
;; returning the foot of the distance instead of the distance.
(defun pf:seg-near (p seg / p1 p2 b v w len2 t2 g c r a1 a2 ap sweep
                            rel)
  (setq p  (pf:2d p)
        p1 (pf:2d (car seg))
        p2 (pf:2d (cadr seg))
        b  (caddr seg))
  (if (< (abs b) 1.0e-9)
    ;; straight: project onto the segment, clamp to its ends
    (progn
      (setq v    (pf:sub p2 p1)
            w    (pf:sub p p1)
            len2 (pf:dot v v))
      (if (< len2 1.0e-20)
        p1
        (progn
          (setq t2 (/ (pf:dot w v) len2))
          (if (< t2 0.0) (setq t2 0.0))
          (if (> t2 1.0) (setq t2 1.0))
          (pf:add p1 (pf:scl v t2)))))
    ;; arc: the radial foot when P falls inside the sweep, else the
    ;; nearer endpoint
    (progn
      (setq g (pf:arc-geom p1 p2 b))
      (if (null g)
        (if (<= (pf:dist p p1) (pf:dist p p2)) p1 p2)
        (progn
          (setq c  (car g)  r (cadr g)
                a1 (caddr g) a2 (cadddr g)
                ap (angle c p))
          (if (> b 0.0)
            (setq sweep (pf:norm-ang (- a2 a1)) rel (pf:norm-ang (- ap a1)))
            (setq sweep (pf:norm-ang (- a1 a2)) rel (pf:norm-ang (- ap a2))))
          (if (<= rel sweep)
            (pf:add c (pf:scl (list (cos ap) (sin ap)) r))
            (if (<= (pf:dist p p1) (pf:dist p p2)) p1 p2)))))))

;; Closest point on the whole loop to P.
(defun pf:curve-near (p segs / best bd s q d)
  (foreach s segs
    (setq q (pf:seg-near p s)
          d (pf:dist p q))
    (if (or (null bd) (< d bd)) (setq best q bd d)))
  best)

;; The subset of PTS sitting within EPS of the loop SEGS - the
;; perimeter's own survey points, as opposed to depth shots and deck
;; points that only happen to be nearby.
(defun pf:near-loop (pts segs eps / out q s d dmin)
  (foreach q pts
    (setq dmin nil)
    (foreach s segs
      (setq d (pf:seg-dist q s))
      (if (or (null dmin) (< d dmin)) (setq dmin d)))
    (if (and dmin (<= dmin eps)) (setq out (cons q out))))
  (reverse out))

;; Sample the closed loop into points spaced about STEP apart, walking
;; it in order: each segment contributes its start point plus enough
;; interior points that no gap exceeds STEP (its end is the next
;; segment's start, so nothing doubles up).
(defun pf:sample-loop (segs step / out s p1 p2 b g c r a1 a2 sweep
                                   len k j aa)
  (setq out nil)
  (foreach s segs
    (setq p1  (pf:2d (car s))
          p2  (pf:2d (cadr s))
          b   (caddr s)
          out (cons p1 out)
          g   (if (>= (abs b) 1.0e-9) (pf:arc-geom p1 p2 b)))
    (if g
      (progn
        (setq c  (car g)   r  (cadr g)
              a1 (caddr g) a2 (cadddr g))
        (if (> b 0.0)
          (setq sweep (pf:norm-ang (- a2 a1)))
          (setq sweep (- (pf:norm-ang (- a1 a2)))))
        (setq len (* r (abs sweep))
              k   (max 1 (fix (/ len step)))
              j   1)
        (while (< j k)
          (setq aa  (+ a1 (* sweep (/ (float j) (float k))))
                out (cons (list (+ (car c) (* r (cos aa)))
                                (+ (cadr c) (* r (sin aa))))
                          out)
                j   (1+ j))))
      (progn
        (setq len (pf:dist p1 p2)
              k   (max 1 (fix (/ len step)))
              j   1)
        (while (< j k)
          (setq out (cons (pf:add p1 (pf:scl (pf:sub p2 p1)
                                             (/ (float j) (float k))))
                          out)
                j   (1+ j))))))
  (reverse out))

;; Signed shoelace area of a point ring: positive = counter-clockwise.
;; Only the SIGN is used, to orient the inward normals.
(defun pf:loop-area (pts / sum prev q)
  (setq sum 0.0 prev (last pts))
  (foreach q pts
    (setq sum  (+ sum (- (* (car prev) (cadr q))
                         (* (car q) (cadr prev))))
          prev q))
  (/ sum 2.0))

;; Index of the sample nearest P.
(defun pf:near-idx (p pts / k best bd q d)
  (setq k 0 best 0 bd nil)
  (foreach q pts
    (setq d (pf:dist p q))
    (if (or (null bd) (< d bd)) (setq best k bd d))
    (setq k (1+ k)))
  best)

;; Inward unit normal of the sampled loop at index I.  The tangent
;; comes from the neighbouring samples; SGN is +1 for a counter-
;; clockwise ring (interior on the left of travel), -1 for clockwise.
(defun pf:samp-normal (i pts sgn / n u)
  (setq n (length pts)
        u (pf:unit (pf:sub (nth (rem (1+ i) n) pts)
                           (nth (rem (+ i n -1) n) pts))))
  (if (null u)
    (setq u (pf:unit (pf:sub (nth (rem (1+ i) n) pts) (nth i pts)))))
  (if (null u) (setq u '(1.0 0.0)))
  (pf:scl (pf:perp u) sgn))

;; A LINE on LAYER (nil = the pool layer) with linetype LTYP
;; (nil = ByLayer).
(defun pf:make-line (p1 p2 layer ltyp / dxf)
  (setq dxf (list '(0 . "LINE") '(100 . "AcDbEntity")
                  (cons 8 (if layer layer *PF-POOL-LAYER*))))
  (if ltyp (setq dxf (append dxf (list (cons 6 ltyp)))))
  (entmakex (append dxf
                    (list '(100 . "AcDbLine")
                          (cons 10 (list (car p1) (cadr p1) 0.0))
                          (cons 11 (list (car p2) (cadr p2) 0.0))))))

;; Make sure the DASHED2 linetype (the half-size dashes marking the
;; underwater break stubs) exists - pure entmake, like pf:ensure-dashed.
(defun pf:ensure-dashed2 ()
  (if (not (tblsearch "LTYPE" *PF-STUB-LTYPE*))
    (entmake (list '(0 . "LTYPE") '(100 . "AcDbSymbolTableRecord")
                   '(100 . "AcDbLinetypeTableRecord")
                   (cons 2 *PF-STUB-LTYPE*) '(70 . 0)
                   '(3 . "Dashed (.5x) _ _ _ _ _")
                   '(72 . 65) '(73 . 2) '(40 . 9.0)
                   '(49 . 6.0) '(74 . 0)
                   '(49 . -3.0) '(74 . 0)))))

;; An OPEN polyline through PTS on the pool layer, with the segment
;; bulges BLS (one per segment, nil = all straight).
(defun pf:make-open-pline (pts bls / dxf q)
  (setq dxf (list '(0 . "LWPOLYLINE") '(100 . "AcDbEntity")
                  (cons 8 *PF-POOL-LAYER*)
                  '(100 . "AcDbPolyline")
                  (cons 90 (length pts)) '(70 . 0)))
  (foreach q pts
    (setq dxf (append dxf (list (cons 10 q)
                                (cons 42 (if bls (car bls) 0.0))))
          bls (cdr bls)))
  (entmakex dxf))

;; One arc from sample I to sample J through their middle sample: its
;; bulge when every sample between them stays within *PF-BOTTOM-FIT*
;; of it, else nil.  (0.0 - a straight stretch - is a valid answer:
;; the offset of a dead-straight wall IS straight.)
(defun pf:arc-fits (pts i j / a b m bl seg k ok)
  (setq a   (nth i pts)
        b   (nth j pts)
        m   (nth (/ (+ i j) 2) pts)
        bl  (pf:bulge-3pt a m b)
        seg (list a b bl)
        ok  T
        k   (1+ i))
  (while (and ok (< k j))
    (if (> (pf:seg-dist (nth k pts) seg) *PF-BOTTOM-FIT*)
      (setq ok nil))
    (setq k (1+ k)))
  (if ok bl))

;; Replace a densely sampled run with as FEW arcs as hold every
;; sample within *PF-BOTTOM-FIT* of the drawn curve: spans grow
;; greedily (longest first), each drawn as the 3-point arc through
;; its middle sample, and every point in KEEP stays a vertex exactly,
;; so the dimension anchors sit ON the line.  Returns (verts bulges)
;; ready for pf:make-open-pline.
(defun pf:merge-arcs (pts keep / n idx q k i j bl verts bls prevk
                                stop rest)
  (setq n   (length pts)
        idx (list 0 (1- n)))
  (foreach q keep
    (setq k (pf:near-idx q pts))
    (if (and (> k 0) (< k (1- n)) (not (member k idx)))
      (setq idx (cons k idx))))
  (setq idx (mapcar 'car
                    (pf:sort-car (mapcar '(lambda (k) (cons k k))
                                         idx))))
  (setq verts (list (car pts))
        bls   nil
        prevk (car idx)
        rest  (cdr idx))
  (while rest
    (setq stop (car rest)
          i    prevk)
    (while (< i stop)
      (setq j stop bl nil)
      (while (and (null bl) (> j (1+ i)))
        (if (null (setq bl (pf:arc-fits pts i j)))
          (setq j (1- j))))
      (if (null bl)
        (setq j  (1+ i)
              bl (pf:arc-fits pts i j)))
      (setq verts (cons (nth j pts) verts)
            bls   (cons bl bls)
            i     j))
    (setq prevk stop
          rest  (cdr rest)))
  (list (reverse verts) (reverse bls)))

;; The dimension style to stamp on a new dim: NAME when the drawing
;; actually has it, else the current style - with a note the first
;; time each missing name comes up (pf-dim-warned is run-scoped).
(defun pf:dim-style (name)
  (if (and name (tblsearch "DIMSTYLE" name))
    name
    (progn
      (if (and name (not (member name pf-dim-warned)))
        (progn
          (setq pf-dim-warned (cons name pf-dim-warned))
          (princ (strcat "\n  (dimension style \"" name
                         "\" is not in this drawing - using the"
                         " current style instead)"))))
      (getvar "DIMSTYLE"))))

;; An aligned dimension measuring PA to PB, in dimension style STY
;; (nil = current), its dimension line through PDL - or right on the
;; measured stretch when PDL is nil.  The empty group 1 makes AutoCAD
;; fill in the measured value (the "auto" dimension text) and build
;; the dimension block; nil comes back when the drawing cannot take a
;; dimension, and the caller says so once.
(defun pf:make-dim (pa pb sty pdl / m)
  (setq m (if pdl pdl (pf:mid pa pb)))
  (entmakex (list '(0 . "DIMENSION") '(100 . "AcDbEntity")
                  (cons 8 *PF-POOL-LAYER*)
                  '(100 . "AcDbDimension")
                  (cons 3 (pf:dim-style sty))
                  (cons 10 (list (car m) (cadr m) 0.0))
                  '(70 . 33)                     ; aligned + block flag
                  '(1 . "")                      ; text = the measurement
                  '(100 . "AcDbAlignedDimension")
                  (cons 13 (list (car pa) (cadr pa) 0.0))
                  (cons 14 (list (car pb) (cadr pb) 0.0)))))

;; Show an offset the way it was typed: architectural when it came in
;; as feet-and-inches, plain inches otherwise.  DEF is (value . ftin).
(defun pf:fmt-off (def)
  (if (cdr def) (rtos (car def) 4 4) (rtos (car def) 2 2)))

;; ---- an offset that fights its neighbours ----------------------------
;; Copied from CALOFIN-LIB.lsp under this file's own prefix, so the
;; standalone file loads alone -- see STANDARDS.md section 4.

;; The entries of PAIRS -- ((position . value) ...) in position order --
;; that sit AGAINST the run on both sides by more than TOL.  Returns
;; ((index . what the neighbours put there) ...).  Fighting BOTH
;; neighbours is the test, and it is what keeps a real curve quiet: 40,
;; 38, 30 is a wall bending away, every value between its neighbours,
;; and nothing is said about it however far the middle one sits off the
;; chord.  40, 10, 30 is a digit.
(defun pf:spikes (pairs tol / n i a b c span expect out)
  (setq n (length pairs) i 1 out nil)
  (while (< i (1- n))
    (setq a    (nth (1- i) pairs)
          b    (nth i pairs)
          c    (nth (1+ i) pairs)
          span (- (car c) (car a)))
    (if (> span 1.0e-9)
      (progn
        (setq expect (+ (cdr a) (* (- (cdr c) (cdr a))
                                   (/ (- (car b) (car a)) span))))
        (if (and (> (abs (- (cdr b) expect)) tol)
                 (or (and (> (- (cdr a) (cdr b)) tol)
                          (> (- (cdr c) (cdr b)) tol))
                     (and (> (- (cdr b) (cdr a)) tol)
                          (> (- (cdr b) (cdr c)) tol))))
          (setq out (cons (cons i expect) out)))))
    (setq i (1+ i)))
  (reverse out))

;; Name a waypoint whose offset fights both its neighbours along this
;; side, and say what they put there.  ANCHORS is the offset profile in
;; order along the side -- the deep end, the waypoints, the shallow
;; break -- and NAMES is (position . "17") for the waypoints in it.
;; Only a waypoint is named: the two ends are pinned by the hopper and
;; the break rather than typed as measurements of the wall.
;;
;; Nothing is changed.  The line follows the offsets exactly as they
;; were given, because an offset the drafter measured is the one thing
;; this command may not quietly overwrite -- it says what it noticed
;; and leaves the number alone.
(defun pf:review-offsets (anchors names / e a b c nm)
  (foreach e (pf:spikes anchors *PF-SPIKE-TOL*)
    (setq b  (nth (car e) anchors)
          nm (assoc (car b) names))
    (if nm
      (progn
        (setq a (nth (1- (car e)) anchors)
              c (nth (1+ (car e)) anchors))
        (princ (strcat "\n  (Pt." (cdr nm) " is offset "
                       (rtos (cdr b) 2 2) ", against "
                       (rtos (cdr a) 2 2) " and " (rtos (cdr c) 2 2)
                       " on both sides of it - the wall between those"
                       " puts it near " (rtos (cdr e) 2 2)
                       ".  The line follows what you typed.)")))))
  (princ))

;; Read an offset distance, remembering HOW it was typed - as
;; feet-and-inches (3'6) or as plain inches (42) - because that
;; choice picks the dimension style later.  Returns (value . T) for
;; feet-and-inches, (value . nil) for inches; Enter takes DEF, a
;; (value . ftin) pair from the previous entry.  Negative input is
;; refused, zero too unless ALLOWZERO (a waypoint may pin the line
;; to the wall).  With BACK non-nil, typing B (Back; Undo works too)
;; returns the symbol PF-BACK instead.
;; LADDER stands the question beside the LENGTH RULER, which is what
;; the three hopper offsets hand in: they are the stations a hopper is
;; LAID OUT to, not lengths taped off the drawing.  An ALLOWZERO
;; question admits a zero and the ruler's prompt does not -- no length
;; on a ruler is zero -- so a ladder handed to one is ignored rather
;; than quietly tightening what the question takes.  The two routes
;; agree on everything the answer carries, the FTIN flag included: the
;; ruler's state records the family the answer was spelled in, whether
;; it was typed or clicked off a row, which is the same question
;; (wcmatch s "*'*") asks of a typed string.
(defun pf:get-off (msg def allowzero back ladder / s v res prompt)
  (setq res nil
        prompt (strcat msg " <" (pf:fmt-off def) ">"
                       (if back " [Back]" "") ": "))
  (while (null res)
    (if (and ladder (not allowzero))
      (progn
        (setq v (pf:ask-rung prompt ladder back))
        (cond
          ((eq v 'PF-BACK) (setq res 'PF-BACK))
          ((null v) (setq res def))              ; Enter takes the default
          (T (setq res (cons v (nth 1 pf:*ruler*))))))
      (progn
        (setq s (getstring T prompt))
        (if lzd:ask (lzd:ask (getvar "LASTPROMPT") s) s)
        (cond
          ((= s "") (setq res def))
          ((and back (pf:back-word s)) (setq res 'PF-BACK))
          (T
           (setq v (distof s 4))
           (cond
             ((null v)
              (princ "\n  (that is not a distance - type inches like 42, or feet and inches like 3'6)"))
             ((or (< v 0.0) (and (= v 0.0) (not allowzero)))
              (princ (strcat "\n  (the offset must be a positive distance"
                             (if allowzero " or zero" "") ")")))
             (T (setq res (cons v (if (wcmatch s "*'*") T nil))))))))))
  res)

;; The survey point marking the BACK of the hopper: cast a ray from
;; the middle of the deep break line, perpendicular to it, away from
;; the shallow break, and take the point closest to that ray on that
;; side.  nil when no survey point lies beyond the deep break at all.
(defun pf:hopper-back (dp1 dp2 sp1 sp2 dpts / mid u q t2 lat back bd)
  (setq mid (pf:mid dp1 dp2)
        u   (pf:unit (pf:perp (pf:sub dp2 dp1))))
  (if u
    (progn
      (if (> (pf:dot u (pf:sub (pf:mid sp1 sp2) mid)) 0.0)
        (setq u (pf:scl u -1.0)))
      (setq back nil bd nil)
      (foreach q dpts
        (setq t2  (pf:dot (pf:sub q mid) u)
              lat (abs (pf:dot (pf:sub q mid) (pf:perp u))))
        (if (and (> t2 *PF-EXACT-EPS*)
                 (or (null bd) (< lat bd)))
          (setq back q bd lat)))
      back)))

;; The hopper outline: walk the sampled perimeter from the deep break
;; point at sample I1 to the one at I2, whichever way round passes the
;; back point at IB, pushing every point inward by an offset that
;; blends OFF1 at the start through OFF3 at the back to OFF2 at the
;; end - a straight run over arc length, so differing offsets change
;; gradually.  P1 and P2 are the exact break positions and stand in
;; for their samples, so the hopper's ends land exactly off them.
;; Returns (hopperPts backPos perimeterPts walkDir), or nil when the
;; two deep break points share a sample.
(defun pf:hopper-pts (samps sgn i1 i2 ib p1 p2 off1 off2 off3
                      / n fwdb fwd2 dir cnt kb idxs i k base cum lt lb
                        prev q out j cj offv bl)
  (setq n    (length samps)
        fwdb (rem (+ (- ib i1) n) n)
        fwd2 (rem (+ (- i2 i1) n) n))
  ;; walk whichever way round passes the back of the hopper
  (if (<= fwdb fwd2)
    (setq dir 1  cnt fwd2 kb fwdb)
    (setq dir -1 cnt (rem (+ (- i1 i2) n) n)
          kb  (rem (+ (- i1 ib) n) n)))
  (if (< cnt 2)
    nil
    (progn
      ;; the perimeter points under the hopper, break to break
      (setq idxs nil i i1 k 0)
      (while (<= k cnt)
        (setq idxs (cons i idxs)
              i    (rem (+ i dir n) n)
              k    (1+ k)))
      (setq idxs (reverse idxs)
            base nil)
      (foreach i idxs (setq base (cons (nth i samps) base)))
      (setq base (reverse base)
            base (cons p1 (cdr base))
            base (reverse (cons p2 (cdr (reverse base)))))
      ;; arc length along the walk places the blend
      (setq cum nil lt 0.0 prev nil)
      (foreach q base
        (if prev (setq lt (+ lt (pf:dist prev q))))
        (setq cum (cons lt cum) prev q))
      (setq cum (reverse cum)
            lb  (nth kb cum))
      (if (< lt 1.0e-9)
        nil
        (progn
          (setq out nil j 0)
          (foreach q base
            (setq cj   (nth j cum)
                  offv (if (<= cj lb)
                         (+ off1 (* (- off3 off1)
                                    (if (> lb 1.0e-9) (/ cj lb) 1.0)))
                         (+ off3 (* (- off2 off3)
                                    (if (> (- lt lb) 1.0e-9)
                                      (/ (- cj lb) (- lt lb))
                                      1.0))))
                  out  (cons (pf:add q (pf:scl
                                         (pf:samp-normal (nth j idxs)
                                                         samps sgn)
                                         offv))
                             out)
                  j    (1+ j)))
          (setq out (reverse out))
          ;; the hopper's corners sit ON the deep break line itself,
          ;; OFF1 and OFF2 in from its ends - not merely near it
          (setq bl (pf:unit (pf:sub p2 p1)))
          (if bl
            (setq out (cons (pf:add p1 (pf:scl bl off1)) (cdr out))
                  out (reverse (cons (pf:add p2 (pf:scl bl (- off2)))
                                     (cdr (reverse out))))))
          (list out kb base dir))))))

;; Offset at arc position CJ, read off the piecewise profile ANCHORS
;; ((position . offset) ... sorted ascending, both ends included):
;; the offset runs straight between neighbouring anchors.
(defun pf:off-at (cj anchors / prev a res span)
  (setq prev (car anchors) res nil)
  (foreach a (cdr anchors)
    (if (and (null res) (<= cj (car a)))
      (setq span (- (car a) (car prev))
            res  (if (< span 1.0e-9)
                   (cdr a)
                   (+ (cdr prev)
                      (* (- (cdr a) (cdr prev))
                         (/ (- cj (car prev)) span))))))
    (if (null res) (setq prev a)))
  (if res res (cdr prev)))

;; A guided slope line: walk CNT samples from index IA in direction
;; DIR (the side away from the hopper), following the perimeter with
;; an inward offset that starts at OFFA on the hopper's end and eases
;; to nothing at the shallow break.  WAYPTS - (surveyPt offset ftin)
;; entries the user picked along this side - pin the offset to those
;; values where they sit, measured square off the wall (along the
;; local inward normal); between anchors the offset runs straight
;; over arc length, so the picked points steer the line and the curve
;; carries it the rest of the way.  PA and PB are the exact break
;; positions; the first point lands exactly on the hopper's corner EA
;; (which sits on the deep break line), the last exactly on the
;; shallow break point.
;; Returns (linePts dimTriples) - one (wallPt linePt ftin) per
;; accepted waypoint, so its offset can be dimensioned in the style
;; its format asks for - or nil when the walk is too short to bother
;; (the caller draws a straight line then).
(defun pf:slope-pts (samps sgn ia dir cnt pa pb offa waypts ea
                     / n idxs i k base cum lt prev q out j anchors wp
                       woff wfl bk bd d dims dv fade w cj out2 wnames)
  (setq n (length samps))
  (if (< cnt 2)
    nil
    (progn
      (setq idxs nil i ia k 0)
      (while (<= k cnt)
        (setq idxs (cons i idxs)
              i    (rem (+ i dir n) n)
              k    (1+ k)))
      (setq idxs (reverse idxs)
            base nil)
      (foreach i idxs (setq base (cons (nth i samps) base)))
      (setq base (reverse base)
            base (cons pa (cdr base))
            base (reverse (cons pb (cdr (reverse base)))))
      (setq cum nil lt 0.0 prev nil)
      (foreach q base
        (if prev (setq lt (+ lt (pf:dist prev q))))
        (setq cum (cons lt cum) prev q))
      (setq cum (reverse cum))
      (if (< lt 1.0e-9)
        nil
        (progn
          ;; the offset profile: pinned at both ends and at each
          ;; waypoint the user gave along this side
          (setq anchors (list (cons 0.0 offa)) dims nil)
          (foreach wp waypts
            (setq woff (cadr wp) wfl (caddr wp) wp (car wp)
                  bk nil bd nil k 0)
            (foreach q base
              (setq d (pf:dist wp q))
              (if (or (null bd) (< d bd)) (setq bk k bd d))
              (setq k (1+ k)))
            (cond
              ((> bd *PF-BOTTOM-STEP*)
               (princ (strcat "\n  (Pt." (pf:pt-name wp)
                              " is not on this side of the pool - its"
                              " offset is ignored)")))
              ((or (= bk 0) (= bk cnt))
               (princ (strcat "\n  (Pt." (pf:pt-name wp)
                              " sits on a break point - its offset is"
                              " ignored, the breaks rule there)")))
              (T
               (setq anchors (cons (cons (nth bk cum) woff) anchors)
                     wnames  (cons (cons (nth bk cum) (pf:pt-name wp))
                                   wnames)
                     dims    (cons (list (nth bk base) bk wfl)
                                   dims)))))
          (setq anchors (pf:sort-car anchors)
                anchors (append anchors (list (cons lt 0.0))))
          ;; the profile is in order along the side now, so a waypoint
          ;; offset that fights both its neighbours can be named before
          ;; the line is drawn through it
          (pf:review-offsets anchors wnames)
          (setq out nil j 0)
          (foreach q base
            (setq out (cons (pf:add q (pf:scl
                                        (pf:samp-normal (nth j idxs)
                                                        samps sgn)
                                        (pf:off-at (nth j cum)
                                                   anchors)))
                            out)
                  j   (1+ j)))
          (setq out (reverse out))
          ;; the line must DEPART from the hopper's corner EA, not
          ;; merely have its first vertex moved there: pull the early
          ;; stretch by the gap between the corner and the plain
          ;; normal-offset start, fading the pull to nothing by the
          ;; first pinned anchor (or the shallow break when there is
          ;; none), so waypoint offsets stay exact
          (if ea
            (progn
              (setq dv   (pf:sub ea (car out))
                    fade (car (cadr anchors)))
              (if (< fade 1.0e-9) (setq fade lt))
              (setq out2 nil j 0)
              (foreach q out
                (setq cj   (nth j cum)
                      w    (if (< cj fade) (- 1.0 (/ cj fade)) 0.0)
                      out2 (cons (pf:add q (pf:scl dv w)) out2)
                      j    (1+ j)))
              (setq out (reverse out2))))
          (list out
                (mapcar '(lambda (pr) (list (car pr)
                                            (nth (cadr pr) out)
                                            (caddr pr)))
                        (reverse dims))))))))

;; Drop consecutive duplicates closer than a hundredth - a tight
;; offset can fold neighbouring samples onto each other.
(defun pf:thin-run (pts / out prev q)
  (foreach q pts
    (if (or (null prev) (> (pf:dist prev q) *PF-THIN-EPS*))
      (setq out (cons q out) prev q)))
  (reverse out))

;; Draw the rest of the bottom package: the hopper outline, the slope
;; lines, and an aligned dimension on each of the three hopper
;; offsets plus every waypoint offset.  GUIDED holds the user's
;; answer for each side: nil = straight, T = guided along the
;; perimeter's curve, or a list of (surveyPt offset ftin) waypoints =
;; guided through those pinned offsets.  Dims not anchored to a break
;; point (the hopper back, the waypoints) carry the dimension style
;; their typed format asks for: *PF-DIM-FTIN* when the offset came in
;; as feet-and-inches (BFL for the back one), *PF-DIM-IN* for plain
;; inches.  LINES holds the two break lines pf:bottom already drew;
;; everything stays scaffolding until the end, so an error in between
;; sweeps the lot - the bottom only ever lands complete.
(defun pf:bottom-draw (segs sp1 sp2 dp1 dp2 back off1 off2 off3 bfl
                       lines guided
                       / made samps sgn i1 i2 ib hp hpts base kb dir
                         n is1 is2 sl spec wdims desc1 desc2 e1 e2 q e
                         dimfail u)
  (setq pf-phase "building the hopper"
        samps    (pf:sample-loop segs *PF-BOTTOM-STEP*)
        sgn      (if (< (pf:loop-area samps) 0.0) -1.0 1.0)
        i1       (pf:near-idx dp1 samps)
        i2       (pf:near-idx dp2 samps)
        ib       (pf:near-idx (pf:curve-near back segs) samps)
        hp       (pf:hopper-pts samps sgn i1 i2 ib dp1 dp2
                                off1 off2 off3))
  (if (null hp)
    ;; the break lines stay scaffolding and are swept with the rest
    (princ "\n  (the deep break points sit on top of each other on the perimeter - the pool bottom was not added)")
    (progn
      (setq hpts (car hp)  kb  (cadr hp)
            base (caddr hp) dir (cadddr hp)
            e1   (car hpts) e2  (last hpts)
            made lines)
      (if (<= (pf:dist dp1 dp2) (+ off1 off2))
        (princ "\n  (warning: the two deep end offsets meet or overlap across the pool)"))
      ;; the deep break becomes THREE lines on the pool layer: dashed
      ;; stubs from each wall in to the hopper's corners, and a solid
      ;; (ByLayer) run across the hopper between them - the single
      ;; placeholder line drawn during the questions goes away
      (if (and (cadr lines) (entget (cadr lines)))
        (entdel (cadr lines)))
      (pf:ensure-dashed2)
      (pf:ensure-layer *PF-POOL-LAYER* *PF-POOL-COLOUR*)
      (setq made (cons (pf:temp-add (pf:tag-mine
                         (pf:make-line dp1 e1 nil *PF-STUB-LTYPE*)))
                       made)
            made (cons (pf:temp-add (pf:tag-mine
                         (pf:make-line e1 e2 nil nil)))
                       made)
            made (cons (pf:temp-add (pf:tag-mine
                         (pf:make-line e2 dp2 nil *PF-STUB-LTYPE*)))
                       made))
      ;; the hopper outline: the dense samples merge into as few long
      ;; arcs as hold the shape, the back anchor kept as a vertex so
      ;; its dimension sits on the line
      (setq sl   (pf:merge-arcs (pf:thin-run hpts)
                                (list (nth kb hpts)))
            made (cons (pf:temp-add (pf:tag-mine
                         (pf:make-open-pline (car sl) (cadr sl))))
                       made))
      ;; the slope lines: each hopper end joins the shallow break
      ;; point on its own side of the loop, so the two never cross -
      ;; walking away from the hopper from each deep break end, the
      ;; shallow projection met first is that side's partner
      (setq n   (length samps)
            is1 (pf:near-idx sp1 samps)
            is2 (pf:near-idx sp2 samps))
      (if (< (rem (+ (* dir (- i1 is2)) n n) n)
             (rem (+ (* dir (- i1 is1)) n n) n))
        (setq q sp1 sp1 sp2 sp2 q
              q is1 is1 is2 is2 q))
      ;; straight, eased in along the perimeter's own curve, or eased
      ;; through the offsets the user pinned at picked points
      (setq wdims nil
            spec  (car guided)
            sl    (if spec
                    (pf:slope-pts samps sgn i1 (- dir)
                                  (rem (+ (* dir (- i1 is1)) n n) n)
                                  dp1 sp1 off1
                                  (if (eq spec T) nil spec) e1)))
      (setq q     (if sl (pf:merge-arcs (pf:thin-run (car sl))
                                        (mapcar 'cadr (cadr sl)))))
      (setq made  (cons (pf:temp-add (pf:tag-mine
                          (if sl
                            (pf:make-open-pline (car q) (cadr q))
                            (pf:make-line e1 sp1 nil nil))))
                        made)
            wdims (if sl (append wdims (cadr sl)))
            desc1 (cond ((null sl) "straight")
                        ((cadr sl) (strcat "guided through "
                                           (itoa (length (cadr sl)))
                                           " point(s)"))
                        (T "guided")))
      (setq spec (cadr guided)
            sl   (if spec
                   (pf:slope-pts samps sgn i2 dir
                                 (rem (+ (* dir (- is2 i2)) n n) n)
                                 dp2 sp2 off2
                                 (if (eq spec T) nil spec) e2)))
      (setq q     (if sl (pf:merge-arcs (pf:thin-run (car sl))
                                        (mapcar 'cadr (cadr sl)))))
      (setq made  (cons (pf:temp-add (pf:tag-mine
                          (if sl
                            (pf:make-open-pline (car q) (cadr q))
                            (pf:make-line e2 sp2 nil nil))))
                        made)
            wdims (if sl (append wdims (cadr sl)) wdims)
            desc2 (cond ((null sl) "straight")
                        ((cadr sl) (strcat "guided through "
                                           (itoa (length (cadr sl)))
                                           " point(s)"))
                        (T "guided")))
      ;; dimension each offset right where it applies.  The deep end
      ;; gets the K/L/M-style string: wall-to-hopper, hopper width,
      ;; hopper-to-wall, all chained on one line a foot off the deep
      ;; break on the shallow-end side - the string reads from the
      ;; shallow end, not from over the deep end it measures.  Break-
      ;; point dims keep the current style; the back and waypoint dims
      ;; get the style their typed format asks for, on the measured
      ;; stretch itself
      (setq u (pf:unit (pf:perp (pf:sub dp2 dp1))))
      (if (and u
               (< (pf:dot u (pf:sub (pf:mid sp1 sp2) (pf:mid dp1 dp2)))
                  0.0))
        (setq u (pf:scl u -1.0)))       ; u points to the shallow side
      (setq dimfail nil)
      (foreach q (append
                   (list (list dp1 e1 nil
                               (if u (pf:add (pf:mid dp1 e1)
                                             (pf:scl u *PF-DIM-OFF*))))
                         (list e1 e2 nil
                               (if u (pf:add (pf:mid e1 e2)
                                             (pf:scl u *PF-DIM-OFF*))))
                         (list e2 dp2 nil
                               (if u (pf:add (pf:mid e2 dp2)
                                             (pf:scl u *PF-DIM-OFF*))))
                         (list (nth kb base) (nth kb hpts)
                               (if bfl *PF-DIM-FTIN* *PF-DIM-IN*)
                               nil))
                   (mapcar '(lambda (pr) (list (car pr) (cadr pr)
                                               (if (caddr pr)
                                                 *PF-DIM-FTIN*
                                                 *PF-DIM-IN*)
                                               nil))
                           wdims))
        ;; stamped like everything else this command draws: the file's
        ;; rule is that only ABHD's own objects are ever erased again,
        ;; and a dimension it made is one of its own
        (setq e (pf:tag-mine
                  (pf:make-dim (car q) (cadr q) (caddr q) (cadddr q))))
        (if e
          (setq made (cons (pf:temp-add e) made))
          (setq dimfail T)))
      (if dimfail
        (princ (strcat "\n  (a dimension could not be created - the"
                       " offsets are " (rtos off1 2 2) ", "
                       (rtos off2 2 2) " and " (rtos off3 2 2) ")")))
      ;; the flow finished: promote it all from scaffolding to result
      (foreach e made (if e (pf:temp-drop e)))
      (princ (strcat "\nPool bottom added on layer " *PF-POOL-LAYER*
                     ": the shallow break, the three-piece deep break"
                     " (dashed stubs, solid middle), the curved hopper"
                     " (offsets " (rtos off1 2 2) " / "
                     (rtos off3 2 2) " / " (rtos off2 2 2)
                     "), the slope lines (" desc1 " / " desc2
                     "), and every dimension - the deep-end string a"
                     " foot off the break, on the shallow side."))))
  (princ))

;; Ask how one slope line should run.  NM names the deep break point
;; whose side is being asked about; DPTS are the survey points and
;; DEFO - a (value . ftin) pair - seeds the offset default.  Returns
;; nil for straight, T for guided, or a list of (surveyPt offset
;; ftin) waypoints for a guided line that passes through picked
;; points at pinned offsets.
(defun pf:ask-slope (nm dpts defo / ans wp spec o seed marks mk done cands)
  (initget "Straight Guided Points Back Undo")
  (setq ans (getkword (strcat
              "\n  Slope line from the offset at Pt." nm
              " [Straight/Guided/Points/Back] <Straight>: ")))
  (if lzd:ask (lzd:ask "pf:ask-slope" ans) ans)
  (setq slopemarks nil)     ; the caller's register of this side's rings
  (cond
    ((member ans '("Back" "Undo")) 'PF-BACK)
    ((= ans "Guided") T)
    ((/= ans "Points") nil)
    (T
     (princ "\n  Name survey points along this side, between the breaks - click")
     (princ "\n  each, or type its number; each gets its own offset, measured")
     (princ "\n  square off the wall.  The line follows the curve through them")
     (princ "\n  and eases to the shallow break.")
     (setq spec     nil
           marks    nil
           seed     defo
           done     nil
           cands    (pf:cands-of dpts)
           pf-phase "picking slope waypoints")
     (while (not done)
       (setq wp (pf:askpoint (strcat "  Point on the Pt." nm
                                     " side - pick it or type its number")
                             "Enter = done" T cands *PF-SNAP*))
       (cond
         ((null wp) (setq done T))
         ((eq wp 'PF-BACK)               ; Back: un-pick the last waypoint
          (if spec
            (progn
              (pf:temp-kill (car marks))
              (setq marks (cdr marks)
                    spec  (cdr spec)
                    seed  (if spec
                            (cons (cadr (car spec)) (caddr (car spec)))
                            defo))
              (princ "\n  Stepping back one point."))
            (setq done 'PF-BACK)))       ; none yet: back to the choice
         (T
          (setq wp (car wp))
          ;; the dashed ring is scaffolding: it confirms the pick and
          ;; clears itself when the command ends (or on a Back)
          (setq mk (pf:temp-add (pf:tag-mine (pf:draw-corner-marker wp))))
          (setq pf-phase "reading a slope waypoint offset")
          ;; no ladder: this offset admits ZERO -- a waypoint flush
          ;; with the line is a real answer -- and no length on a ruler
          ;; is zero
          (setq o (pf:get-off (strcat "\n  What is the offset at Pt."
                                      (pf:pt-name wp) "?")
                              seed T T nil))
          (if (eq o 'PF-BACK)
            (progn                       ; un-pick this waypoint, re-ask
              (pf:temp-kill mk)
              (princ "\n  Stepping back one point."))
            (setq spec  (cons (list wp (car o) (cdr o)) spec)
                  marks (cons mk marks)
                  seed  o))
          (setq pf-phase "picking slope waypoints"))))
     (cond
       ((eq done 'PF-BACK)               ; re-ask Straight/Guided/Points
        (pf:ask-slope nm dpts defo))
       (spec
        (setq slopemarks marks)
        (reverse spec))
       (T
        (princ "\n  (no points picked - guiding along the curve instead)")
        T)))))

;; The interactive flow, run once a perimeter is in hand.  SEGS is
;; the closed loop, DPTS the survey points.  With ASK the user is
;; first offered the bottom (Enter or No skips it - the ABHD ending);
;; without, the flow starts straight away (the ADAB command, which
;; exists only for this).
(defun pf:bottom (segs dpts ask / ans s1 s2 d1 d2 sp1 sp2 dp1 dp2 cands
                                   back off1 off2 off3 o1 o2 o3 bfl
                                   lines nm1 nm2 g1 g2 g1m g2m
                                   slopemarks stage go quit v e)
  ;; Staged so every prompt after the first offers Back - [Back] at
  ;; the point picks, B typed at the offsets - re-opening the previous
  ;; question and removing the scaffolding it drew.  Enter at a pick
  ;; still cancels the whole bottom, as before.  A break line whose
  ;; ends land wrong re-opens its own pick instead of aborting.
  (setq stage (if ask 0 1) go T quit nil cands (pf:cands-of dpts))
  (while (and go (not quit))
    (cond
      ;; -- offer the bottom (the ABHD ending; ADAB starts at 1)
      ((= stage 0)
       (setq pf-phase "asking about the pool bottom")
       (cond
         ;; cover mode: a cover sheet records the perimeter and nothing
         ;; below it, so this is answered No without being asked --
         ;; ABHDCOVER sets the flag and c:ABHD clears it again
         (abhd:*nobottom*
          (princ "\n\n  Cover sheet - skipping the bottom of the pool.")
          (setq go nil))
         (t
          (initget "Yes No")
          (setq ans (getkword
                      "\n\n  Add the bottom of the pool (breaks and hopper)? [Yes/No] <No>: "))
          (if lzd:ask (lzd:ask "\n\n  Add the bottom of the pool (breaks and hopper)? [Yes/No] <No>: " ans) ans)
          (if (= ans "Yes") (setq stage 1) (setq go nil)))))

      ;; -- the shallow break, one end per stage
      ;; Each end is a survey point NAMED - clicked, or typed by number
      ;; - and a second end that is the first one again is refused
      ;; where it stands, so a break line of no length is never carried
      ;; on to be found later
      ((= stage 1)
       (princ "\n\n  SHALLOW BREAK - where the flat shallow floor starts sloping down.")
       (princ "\n  Name its two ends - click each survey point, or type its number.")
       (setq pf-phase "picking the shallow break")
       (setq v (pf:askpoint "  First shallow break point" "Enter = no bottom"
                            ask cands *PF-SNAP*))
       (cond
         ((null v)
          (princ "\n  (point pick cancelled - the pool bottom was not added)")
          (setq quit T))
         ((eq v 'PF-BACK) (setq stage 0))
         (T (setq s1 (car v) stage 2))))
      ((= stage 2)
       (setq v (pf:askpoint (strcat "  Second shallow break point, from Pt."
                                    (pf:pt-name s1))
                            "Enter = no bottom" T cands *PF-SNAP*))
       (cond
         ((null v)
          (princ "\n  (point pick cancelled - the pool bottom was not added)")
          (setq quit T))
         ((eq v 'PF-BACK) (setq stage 1))
         ((< (pf:dist (car v) s1) *PF-EXACT-EPS*)
          (princ (strcat "\n  (that is Pt." (pf:pt-name s1)
                         " again - the shallow break needs two different"
                         " points)")))
         (T (setq s2 (car v) stage 3))))

      ;; -- the deep break
      ((= stage 3)
       (princ "\n  DEEP BREAK - where the slope levels out into the hopper.")
       (setq pf-phase "picking the deep break")
       (setq v (pf:askpoint "  First deep break point" "Enter = no bottom"
                            T cands *PF-SNAP*))
       (cond
         ((null v)
          (princ "\n  (point pick cancelled - the pool bottom was not added)")
          (setq quit T))
         ((eq v 'PF-BACK) (setq stage 2))
         (T (setq d1 (car v) stage 4))))
      ((= stage 4)
       (setq v (pf:askpoint (strcat "  Second deep break point, from Pt."
                                    (pf:pt-name d1))
                            "Enter = no bottom" T cands *PF-SNAP*))
       (cond
         ((null v)
          (princ "\n  (point pick cancelled - the pool bottom was not added)")
          (setq quit T))
         ((eq v 'PF-BACK) (setq stage 3))
         ((< (pf:dist (car v) d1) *PF-EXACT-EPS*)
          (princ (strcat "\n  (that is Pt." (pf:pt-name d1)
                         " again - the deep break needs two different"
                         " points)")))
         (T
          (setq d2 (car v))
          ;; the break ends land exactly on the kept perimeter
           (setq sp1  (pf:curve-near s1 segs)
                 sp2  (pf:curve-near s2 segs)
                 dp1  (pf:curve-near d1 segs)
                 dp2  (pf:curve-near d2 segs)
                 back (pf:hopper-back dp1 dp2 sp1 sp2 dpts))
           (cond
             ((null back)
              (princ (strcat "\n  (no survey point lies beyond the"
                             " deep break - are the two break lines"
                             " swapped?  Pick the deep break again)"))
              (setq stage 3))
             (T
              ;; both break lines go down now, solid, so what was
              ;; declared is visible while the offsets are typed;
              ;; they stay scaffolding until the whole flow lands.
              ;; A re-commit (after a Back) sweeps the old pair first.
              (foreach e lines (pf:temp-kill e))
              (pf:ensure-layer *PF-POOL-LAYER* *PF-POOL-COLOUR*)
              (setq lines (list (pf:temp-add (pf:tag-mine
                                  (pf:make-line sp1 sp2 nil nil)))
                                (pf:temp-add (pf:tag-mine
                                  (pf:make-line dp1 dp2 nil nil)))))
              (princ (strcat "\n  Back of the hopper: Pt."
                             (pf:pt-name back)
                             " (the survey point straight out from"
                             " the deep break)."))
              (setq nm1 (pf:pt-name d1)
                    nm2 (pf:pt-name d2))
              (princ "\n  Three offsets pull the hopper in from the perimeter;")
              (princ "\n  they blend gradually where they differ.  Type inches (42)")
              (princ "\n  or feet and inches (3'6).")
              (setq stage 5))))))

      ;; -- the three hopper offsets
      ((= stage 5)
       (setq pf-phase "reading the hopper offsets")
       (setq o1 (pf:get-off (strcat "\n  What is the deep end offset at Pt."
                                    nm1 "?")
                            (cons *PF-HOP-OFF* nil) nil T
                            *PF-HOP-OFF-LADDER*))
       (if (eq o1 'PF-BACK)
         (setq stage 4)
         (setq off1 (car o1) stage 6)))
      ((= stage 6)
       (setq o2 (pf:get-off (strcat "\n  What is the deep end offset at Pt."
                                    nm2 "?")
                            o1 nil T *PF-HOP-OFF-LADDER*))
       (if (eq o2 'PF-BACK)
         (setq stage 5)
         (setq off2 (car o2) stage 7)))
      ((= stage 7)
       (setq o3 (pf:get-off (strcat "\n  What is the offset at the back of the"
                                    " hopper (Pt." (pf:pt-name back) ")?")
                            o1 nil T *PF-HOP-OFF-LADDER*))
       (if (eq o3 'PF-BACK)
         (setq stage 6)
         (progn
           (setq off3 (car o3)
                 bfl  (cdr o3))
           (setq *PF-HOP-OFF* off1)
           ;; each slope line can run straight to the shallow break,
           ;; follow the perimeter's curve gently in, or pass through
           ;; picked points at pinned offsets
           (setq pf-phase "asking about the slope lines")
           (princ "\n  Each slope line can run STRAIGHT to the shallow break, be GUIDED")
           (princ "\n  by the perimeter - easing in along its curve - or pass through")
           (princ "\n  POINTS you pick along that side, each with its own offset.")
           (setq stage 8))))

      ;; -- one slope choice per side; Back at a choice re-opens the
      ;; -- previous question, sweeping that side's waypoint rings
      ((= stage 8)
       (foreach e g1m (pf:temp-kill e))
       (setq g1m nil
             v   (pf:ask-slope nm1 dpts o1))
       (if (eq v 'PF-BACK)
         (setq stage 7)
         (setq g1 v g1m slopemarks stage 9)))
      ((= stage 9)
       (foreach e g2m (pf:temp-kill e))
       (setq g2m nil
             v   (pf:ask-slope nm2 dpts o2))
       (if (eq v 'PF-BACK)
         (setq stage 8)
         (setq g2 v g2m slopemarks stage 10)))

      ;; -- everything is in hand: draw the bottom
      (T
       (pf:bottom-draw segs sp1 sp2 dp1 dp2 back
                       off1 off2 off3 bfl lines
                       (list g1 g2))
       (setq go nil))))
  (princ))

;; ---- walking the settings chain --------------------------------------
;; The chain is one chain whichever command is walking it; only the
;; numbers printed on it move.  ABHD asks all eight steps; SIMPABHD
;; asks none of the first three, so its step 4 is the drafter's step 1
;; and its step 8 is step 5.
;;
;; Steps 1 to 6 are the settings and run as the Back-walkable chain in
;; pf:fit-session; step 7 is the selection and step 8 the points to
;; leave out of it, and those two are AFTER the chain because each
;; needs what the one before it produced.

;; "Step 4 of 8 - " in ABHD, "Step 1 of 5 - " in SIMPABHD.
(defun pf:step-n (step simp)
  (strcat "\n\n  Step " (itoa (if simp (- step 3) step))
          " of " (if simp "5" "8") " - "))

;; Back out of the question at STEP, where LO is the first question
;; the running command actually asks.  At LO there is nothing behind
;; this question, so the step re-opens instead - which is what makes
;; Back at SIMPABHD's first prompt safe rather than a way out of the
;; run.
(defun pf:step-back (step lo)
  (cond ((> step lo)
         (princ "\n  Stepping back one question.")
         (1- step))
        (T
         (princ "\n  Already at the first question.")
         step)))

;; ---- the numeric parameters ------------------------------------------
;; Asked identically at the start of a run and again on a Redo -
;; Enter keeps the shown value each time.

;; Each takes BACK: non-nil adds Back (and its hidden Undo synonym) to
;; the prompt and returns PF-BACK when it is answered, so the caller
;; can re-open the step before it.  Offering Back never loosens the
;; value check - initget keeps its bits either way.

;; Maximum distance from a point; remembered in *PF-TOL*.
(defun pf:ask-tol (back / tol)
  (if back (initget 6 "Back Undo") (initget 6))
  (setq tol (getdist (strcat "\n  Maximum distance from a point <"
                             (rtos *PF-TOL* 2 3) ">"
                             (if back " [Back]" "") ": ")))
  (if lzd:ask (lzd:ask "pf:ask-tol" tol) tol)
  (cond
    ((pf:back-kw tol) 'PF-BACK)
    (T
     (if (null tol) (setq tol *PF-TOL*))
     (if (> tol *PF-TOL-MAX*)
       (progn
         (princ (strcat "\n  (more than " (rtos *PF-TOL-MAX* 2 1)
                        " and the line is no longer a trace of the points"
                        " - using " (rtos *PF-TOL-MAX* 2 1) ")"))
         (setq tol *PF-TOL-MAX*)))
     (setq *PF-TOL* tol)
     tol)))

;; Share of the points allowed off the line, returned as a fraction;
;; DEF is the fraction Enter keeps.
(defun pf:ask-pct (def back / pct)
  ;; DEF is the knob on a first asking: held to the range a typed
  ;; answer is held to BEFORE it is shown, so the prompt never
  ;; offers <1500> or <-9> and Enter never takes it
  (if (not (and (numberp def) (>= def 0) (<= def 1.0)))
    (setq def (pf:miss-knob)))
  (if back (initget 4 "Back Undo") (initget 4))
  (setq pct (getint (strcat "\n  Percent of points allowed off <"
                            (itoa (fix (+ 0.5 (* 100.0 def))))
                            ">"
                            (if back " [Back]" "") ": ")))
  (if lzd:ask (lzd:ask "pf:ask-pct" pct) pct)
  (cond
    ((pf:back-kw pct) 'PF-BACK)
    ((null pct) def)
    ((> pct 100)
     (princ "\n  (more than 100 makes no sense - using 100)")
     1.0)
    (T (/ pct 100.0))))

;; What the cap prompt shows in its <angle brackets> - the standing
;; answer in words, since one of the three states is a rule rather
;; than a number.
(defun pf:cap-word ()
  (cond ((eq 'AUTO *PF-MAX-ARCS*) "Auto")
        (*PF-MAX-ARCS*            (itoa *PF-MAX-ARCS*))
        (T                        "None")))

;; Curve cap; remembered in *PF-MAX-ARCS* - 'AUTO (a third of the
;; points), a number, or nil for no cap.  Auto and None are keywords
;; rather than numbers because neither IS a number: Auto is a rule
;; that only becomes one once the points are counted.
(defun pf:ask-cap (back / mx)
  (if back (initget 4 "Auto None Back Undo") (initget 4 "Auto None"))
  (setq mx (getint (strcat "\n  Maximum curves <" (pf:cap-word) ">"
                           (if back " [Auto/None/Back]" " [Auto/None]")
                           ": ")))
  (if lzd:ask (lzd:ask "pf:ask-cap" mx) mx)
  (cond
    ((pf:back-kw mx) 'PF-BACK)
    (T
     (cond ((null mx) nil)                         ; Enter: keep as-is
           ((eq 'STR (type mx))
            (setq *PF-MAX-ARCS* (if (= mx "Auto") 'AUTO nil)))
           (T (setq *PF-MAX-ARCS* mx)))
     *PF-MAX-ARCS*)))

;; ---- steps 4, 5 and 6: the declaration loops -------------------------
;; Each collects a list and draws its dashed marker as it goes, so Back
;; here means what it means in every other draw-as-you-go loop in the
;; toolset: take back the item declared last, marker and all, and ask
;; for it again.  At the first item there is nothing left to take back,
;; so the whole step re-opens instead and its Yes/No question is asked
;; again - which is how a wrong Yes gets undone.  Each returns its list
;; oldest-first, or PF-BACK when the step is to re-open, and leaves the
;; markers it drew in pf-decl-marks so the caller can sweep them if the
;; step is later re-opened from the one below it.

(defun pf:declare-walls (cands / out go c1 c2 mk again res)
  (setq out nil pf-decl-marks nil go T res nil)
  (while go
    (setq pf-phase "picking a straight wall")
    (setq c1 (pf:askpoint
               "  First end of the straight wall - pick it or type its number"
               "Enter = done" T cands *PF-SNAP*))
    (cond
      ((eq c1 'PF-BACK)
       (if pf-decl-marks
         (progn (pf:temp-kill (car pf-decl-marks))
                (setq pf-decl-marks (cdr pf-decl-marks) out (cdr out))
                (princ "\n  Stepping back one wall."))
         (progn (princ "\n  Already at the first wall.")
                (setq go nil res T))))
      ((null c1) (setq go nil))
      (T
       (setq c2 (pf:ask-wall-end c1 cands))
       (cond
         ;; Back at the second end re-asks the first: nothing was
         ;; committed yet, so there is no marker to sweep
         ((eq c2 'PF-BACK) (princ "\n  Stepping back one point."))
         (T
          (setq mk  (pf:temp-add (pf:tag-mine
                      (pf:draw-wall-marker (car c1) (car c2))))
                pf-decl-marks (cons mk pf-decl-marks)
                out (cons (list c1 c2) out))
          (princ (strcat "\n  Wall Pt." (cadr c1) " - Pt." (cadr c2) "."))
          (initget "Yes No Back Undo")
          (setq again (getkword "\n  Another straight line? [Yes/No/Back] <No>: "))
          (if lzd:ask (lzd:ask "\n  Another straight line? [Yes/No/Back] <No>: " again) again)
          (cond
            ((member again '("Back" "Undo"))
             (pf:temp-kill (car pf-decl-marks))
             (setq pf-decl-marks (cdr pf-decl-marks) out (cdr out))
             (princ "\n  Stepping back one wall."))
            ((/= again "Yes") (setq go nil))))))))
  (if res 'PF-BACK (reverse out)))

(defun pf:declare-corners (cands / out go c mk res)
  (setq out nil pf-decl-marks nil go T res nil)
  (while go
    (setq pf-phase "picking a sharp corner")
    (setq c (pf:askpoint "  Corner point - pick it or type its number"
                         "Enter = done" T cands *PF-SNAP*))
    (cond
      ((eq c 'PF-BACK)
       (if pf-decl-marks
         (progn (pf:temp-kill (car pf-decl-marks))
                (setq pf-decl-marks (cdr pf-decl-marks) out (cdr out))
                (princ "\n  Stepping back one corner."))
         (progn (princ "\n  Already at the first corner.")
                (setq go nil res T))))
      ((null c) (setq go nil))
      ((pf:memb (car c) (mapcar 'car out))
       (princ (strcat "\n  Pt." (cadr c) " is already declared a corner.")))
      (T (setq mk  (pf:temp-add (pf:tag-mine (pf:draw-corner-marker (car c))))
               pf-decl-marks (cons mk pf-decl-marks)
               out (cons c out))
         (princ (strcat "\n  Corner Pt." (cadr c) ".")))))
  (if res 'PF-BACK (reverse out)))

(defun pf:declare-holds (cands / out go c mk res)
  (setq out nil pf-decl-marks nil go T res nil)
  (while go
    (setq pf-phase "picking a held point")
    (setq c (pf:askpoint "  Point to hold exactly - pick it or type its number"
                         "Enter = done" T cands *PF-SNAP*))
    (cond
      ((eq c 'PF-BACK)
       (if pf-decl-marks
         (progn (pf:temp-kill (car pf-decl-marks))
                (setq pf-decl-marks (cdr pf-decl-marks) out (cdr out))
                (princ "\n  Stepping back one held point."))
         (progn (princ "\n  Already at the first held point.")
                (setq go nil res T))))
      ((null c) (setq go nil))
      ((pf:memb (car c) (mapcar 'car out))
       (princ (strcat "\n  Pt." (cadr c) " is already held.")))
      (T (setq mk  (pf:temp-add (pf:tag-mine (pf:draw-hold-marker (car c))))
               pf-decl-marks (cons mk pf-decl-marks)
               out (cons c out))
         (princ (strcat "\n  Held Pt." (cadr c) ".")))))
  (if res 'PF-BACK (reverse out)))

;; ---- redo-time editing of walls and corners --------------------------
;; A Redo may change more than the numbers: straight walls and sharp
;; corners can be added or removed before the refit.  Both editors
;; work on the run-scoped pf-walls / pf-corners lists and keep the
;; dashed markers in step with them.

;; Erase this run's scaffolding markers of one entity type on the
;; marker layer (walls are the LINEs, rings the CIRCLEs), so the set
;; can be redrawn to match an edited declaration list.
(defun pf:sweep-marks (etype / keep en ed)
  (setq keep nil)
  (foreach en pf-temp
    (setq ed (if (and en (entget en)) (entget en)))
    (if (and ed
             (= etype (cdr (assoc 0 ed)))
             (= (strcase *PF-WALL-LAYER*)
                (strcase (cdr (assoc 8 ed)))))
      (entdel en)
      (setq keep (cons en keep))))
  (setq pf-temp (reverse keep)))

;; Add or remove declared straight walls.  Ends are NAMED - clicked or
;; typed by number, out of the points in the fit; each change is
;; confirmed by name and the dashed markers follow.
(defun pf:edit-walls (dpts / cands ans c1 c2 wp1 best bd w d res)
  (setq ans T res nil cands (pf:cands-of dpts))
  (while ans
    (initget "Add Remove Keep Back Undo")
    (setq ans (getkword (strcat
                "\n  Straight walls (" (itoa (length pf-walls))
                " declared) - [Add/Remove/Keep/Back] <Keep>: ")))
    (if lzd:ask (lzd:ask (getvar "LASTPROMPT") ans) ans)
    (cond
      ((member ans '("Back" "Undo")) (setq ans nil res T))
      ((= ans "Add")
       (setq pf-phase "picking a straight wall")
       (setq c1 (pf:askpoint
                  "  First end of the straight wall - pick it or type its number"
                  "Enter = none" T cands *PF-SNAP*)
             c2 nil)
       (if (and c1 (not (eq c1 'PF-BACK)))
         (progn
           (setq c2 (pf:ask-wall-end c1 cands))
           (if (eq c2 'PF-BACK) (setq c2 nil))))
       (if c2
         (progn
           (setq pf-walls (append pf-walls (list (list (car c1) (car c2)))))
           (pf:temp-add (pf:tag-mine (pf:draw-wall-marker (car c1) (car c2))))
           (princ (strcat "\n  wall Pt." (cadr c1)
                          " - Pt." (cadr c2) " added")))))
      ((= ans "Remove")
       (if (null pf-walls)
         (princ "\n  (no straight walls to remove)")
         (progn
           (setq pf-phase "removing a straight wall")
           (initget "Back Undo")
           (setq wp1 (getpoint "\n  Pick near the straight wall to remove [Back]: "))
           (if lzd:ask (lzd:ask "\n  Pick near the straight wall to remove [Back]: " wp1) wp1)
           (if (pf:back-kw wp1) (setq wp1 nil))
           (if wp1
             (progn
               ;; a UCS click against walls held in world numbers:
               ;; untranslated, a moved UCS removed some other wall
               (setq wp1 (pf:2d (trans wp1 1 0)) best nil bd nil)
               (foreach w pf-walls
                 (setq d (pf:seg-dist wp1 (list (car w) (cadr w) 0.0)))
                 (if (or (null bd) (< d bd)) (setq best w bd d)))
               (setq pf-walls (pf:remove best pf-walls))
               ;; redraw the wall markers to match what is left
               (pf:sweep-marks "LINE")
               (foreach w pf-walls
                 (pf:temp-add (pf:tag-mine
                   (pf:draw-wall-marker (car w) (cadr w)))))
               (princ (strcat "\n  wall Pt." (pf:pt-name (car best))
                              " - Pt." (pf:pt-name (cadr best))
                              " removed")))))))
      (T (setq ans nil))))
  (if res 'PF-BACK))

;; Add or remove declared sharp corners the same way.  (The corners
;; the fitter finds by itself - turns over *PF-CORNER-ANG* - are not
;; declarations and cannot be removed here.)
(defun pf:edit-corners (dpts / cands ans c best w res)
  (setq ans T res nil cands (pf:cands-of dpts))
  (while ans
    (initget "Add Remove Keep Back Undo")
    (setq ans (getkword (strcat
                "\n  Sharp corners (" (itoa (length pf-corners))
                " declared) - [Add/Remove/Keep/Back] <Keep>: ")))
    (if lzd:ask (lzd:ask (getvar "LASTPROMPT") ans) ans)
    (cond
      ((member ans '("Back" "Undo")) (setq ans nil res T))
      ((= ans "Add")
       (setq pf-phase "picking a sharp corner")
       (setq c (pf:askpoint "  Corner point - pick it or type its number"
                            "Enter = none" T cands *PF-SNAP*))
       (if (and c (not (eq c 'PF-BACK)))
         (if (pf:memb (car c) pf-corners)
           (princ "\n  (that corner is already declared)")
           (progn
             (setq pf-corners (append pf-corners (list (car c))))
             (pf:temp-add (pf:tag-mine (pf:draw-corner-marker (car c))))
             (princ (strcat "\n  corner Pt." (cadr c) " added"))))))
      ((= ans "Remove")
       (if (null pf-corners)
         (princ "\n  (no declared corners to remove)")
         (progn
           (setq pf-phase "removing a sharp corner")
           (setq c (pf:askpoint
                     "  The declared corner to remove - pick it or type its number"
                     "Enter = none" T cands *PF-SNAP*))
           (cond
             ((or (null c) (eq c 'PF-BACK)) nil)
             ((not (pf:memb (car c) pf-corners))
              (princ (strcat "\n  (Pt." (cadr c) " is not a declared corner)")))
             (T
               (setq best (pf:nearest (car c) pf-corners))
               (setq pf-corners (pf:remove best pf-corners))
               ;; the rings share their look with the omit markers;
               ;; redraw the corner and hold rings (spent omit rings
               ;; go quietly - the omissions already happened)
               (pf:sweep-marks "CIRCLE")
               (foreach w pf-corners
                 (pf:temp-add (pf:tag-mine (pf:draw-corner-marker w))))
               (foreach w pf-holds
                 (pf:temp-add (pf:tag-mine (pf:draw-hold-marker w))))
               (princ (strcat "\n  corner Pt." (pf:pt-name best)
                              " removed")))))))
      (T (setq ans nil))))
  (if res 'PF-BACK))

;; Add or remove HELD points the same way.
(defun pf:edit-holds (dpts / cands ans c best w res)
  (setq ans T res nil cands (pf:cands-of dpts))
  (while ans
    (initget "Add Remove Keep Back Undo")
    (setq ans (getkword (strcat
                "\n  Held points (" (itoa (length pf-holds))
                " declared) - [Add/Remove/Keep/Back] <Keep>: ")))
    (if lzd:ask (lzd:ask (getvar "LASTPROMPT") ans) ans)
    (cond
      ((member ans '("Back" "Undo")) (setq ans nil res T))
      ((= ans "Add")
       (setq pf-phase "picking a held point")
       (setq c (pf:askpoint "  Point to hold exactly - pick it or type its number"
                            "Enter = none" T cands *PF-SNAP*))
       (if (and c (not (eq c 'PF-BACK)))
         (if (pf:memb (car c) pf-holds)
           (princ "\n  (that point is already held)")
           (progn
             (setq pf-holds (append pf-holds (list (car c))))
             (pf:temp-add (pf:tag-mine (pf:draw-hold-marker (car c))))
             (princ (strcat "\n  held Pt." (cadr c) " added"))))))
      ((= ans "Remove")
       (if (null pf-holds)
         (princ "\n  (no held points to remove)")
         (progn
           (setq pf-phase "removing a held point")
           (setq c (pf:askpoint
                     "  The held point to release - pick it or type its number"
                     "Enter = none" T cands *PF-SNAP*))
           (cond
             ((or (null c) (eq c 'PF-BACK)) nil)
             ((not (pf:memb (car c) pf-holds))
              (princ (strcat "\n  (Pt." (cadr c) " is not a held point)")))
             (T
               (setq best (pf:nearest (car c) pf-holds))
               (setq pf-holds (pf:remove best pf-holds))
               ;; redraw the rings to match what is left
               (pf:sweep-marks "CIRCLE")
               (foreach w pf-corners
                 (pf:temp-add (pf:tag-mine (pf:draw-corner-marker w))))
               (foreach w pf-holds
                 (pf:temp-add (pf:tag-mine (pf:draw-hold-marker w))))
               (princ (strcat "\n  held Pt." (pf:pt-name best)
                              " released")))))))
      (T (setq ans nil))))
  (if res 'PF-BACK))

;; ---- leaving points out ----------------------------------------------
;; Asked once the whole survey is in hand - at step 8 - and again at
;; every Redo, because those are the two moments the drafter can see
;; which shot is the bad one.  Every pick TOGGLES: a point in the fit
;; goes out (it, and any duplicate shot on the same spot, leave PTS,
;; the stats and the miss allowance alike) and gets a dashed ring; a
;; ringed one named again comes back in and takes its ring with it.
;;
;; pf-omitted carries (point its-saved-copies ring) per entry, which is
;; what makes a restore exact rather than a re-add: the duplicates come
;; back as they were read, not as one merged shot.
;;
;; Returns (points-still-in-the-fit points-omitted-by-THIS-call).  The
;; second list is what a caller with declarations already matched needs
;; in order to drop the walls, corners and holds that just lost their
;; point; step 8 runs before that matching, so there is nothing there
;; for it to prune and pf:declared-in names and drops them by itself.
(defun pf:omit-loop (pts / cand w w1 w2 ent ring pts2 omits)
  (setq omits nil)
  (princ "\n  Name each one - click it, or type its number (Enter for none):")
  (princ "\n  mis-shots, duplicates, anything the line should not chase;")
  (princ "\n  each gets a dashed ring.")
  (if pf-omitted
    (princ (strcat "\n  " (itoa (length pf-omitted))
                   " point(s) are already out - naming one of those"
                   " puts it BACK IN.")))
  (while (setq cand (pf:askpoint
                      "  Point to omit, or a ringed one to restore - pick it or type its number"
                      "Enter = done" nil
                      (pf:cands-of
                        (append (pf:dedupe pts) (mapcar 'car pf-omitted)))
                      *PF-SNAP*))
    ;; the prompt offers no Back: there is nothing behind a list you
    ;; are still building, and reading Back as Enter would move the run
    ;; ON, which is the opposite of what was asked for.  So say what to
    ;; do instead and ask again - naming a ringed point again is how one
    ;; is taken back here.  Without this the sentinel reached (car ...)
    ;; below and killed the command.
    (if (eq cand 'PF-BACK)
      (princ (strcat "\n  Nothing to go back to here - name a ringed"
                     " point again to put it back in, or press Enter"
                     " when the list is right."))
      (progn
        (setq w1 (car cand)
              w2 (pf:nearest w1 (mapcar 'car pf-omitted)))
        (cond
          ;; a ringed point: naming it again un-omits it - the saved
          ;; entries (its duplicates too) rejoin the fit, its ring goes
          ((and w2 (< (pf:dist w1 w2) *PF-EXACT-EPS*))
           (setq ent        (assoc w2 pf-omitted)
                 pts        (append pts (cadr ent))
                 pf-omitted (pf:remove ent pf-omitted)
                 omits      (pf:remove w2 omits))
           (if (and (caddr ent) (entget (caddr ent)))
             (progn
               (pf:temp-drop (caddr ent))
               (entdel (caddr ent))))
           (princ (strcat "  - Pt." (pf:pt-name w2) " back in")))
          ;; otherwise omit: pull it - and its duplicates - out of the
          ;; fit, the stats and the miss allowance alike, and remember
          ;; how to undo it
          (w1
           (setq pts2 nil ent nil)
           (foreach w pts
             (if (< (pf:dist w w1) *PF-EXACT-EPS*)
               (setq ent (cons w ent))
               (setq pts2 (cons w pts2))))
           (setq pts        (reverse pts2)
                 ring       (pf:temp-add (pf:tag-mine
                                           (pf:draw-corner-marker w1)))
                 pf-omitted (cons (list w1 ent ring) pf-omitted)
                 omits      (cons w1 omits))
           (princ (strcat "  - omitting Pt." (pf:pt-name w1))))))))
  (list pts omits))

;; The walls, corners and holds that just lost a point to OMITS, gone.
;; A restored point gets none of them back: the wall went when it went
;; out, and a wall the drafter no longer means is worse than one they
;; have to declare twice.
(defun pf:prune-declared (omits / pts2 w)
  (setq pts2 nil)
  (foreach w pf-walls
    (if (not (or (pf:memb (car w) omits) (pf:memb (cadr w) omits)))
      (setq pts2 (cons w pts2))))
  (if (< (length pts2) (length pf-walls))
    (princ "\n  (a declared wall lost an end and was dropped)"))
  (setq pf-walls (reverse pts2)
        pts2     nil)
  (foreach w pf-corners
    (if (not (pf:memb w omits)) (setq pts2 (cons w pts2))))
  (setq pf-corners (reverse pts2)
        pts2       nil)
  ;; a held point that was just omitted is out of the fit entirely -
  ;; nothing left to hold
  (foreach w pf-holds
    (if (not (pf:memb w omits)) (setq pts2 (cons w pts2))))
  (if (< (length pts2) (length pf-holds))
    (princ "\n  (an omitted point was held - its hold went with it)"))
  (setq pf-holds (reverse pts2))
  (princ))

;; ---- the run itself, shared by ABHD and SIMPABHD ---------------------
;; Everything from the first question to the last sweep: the settings
;; chain, the selection, the mode, the candidates and the Redo loop.
;; SIMP non-nil is SIMPABHD - the same run with its first three
;; questions not asked and five candidates drawn instead of three.
;;
;; One function and not two.  What a second copy would have to keep in
;; step is not the fitter (that is pf:build's job) but every promise
;; the run makes around it: that Back walks the chain, that a step
;; re-entered from below throws away what the earlier pass collected,
;; that declared walls and holds snap onto survey points and say so
;; when they were picked wide, that an omitted point takes its wall
;; with it, that the point order forgets what was omitted.  Those are
;; the ones that rot quietly.
;;
;; It is dynamically scoped on purpose: pf-walls, pf-corners,
;; pf-holds, pf-ptnames, pf-omitted and pf-miss-pct are bound HERE and
;; read by the fitter, the reporter and the ask helpers, which is how
;; they were already bound by the commands this was lifted out of.
;; pf-phase and pf-temp are deliberately NOT bound here: the caller's
;; error handler reads the one and sweeps the other, and a binding of
;; either in this frame would hide the run's own state from the
;; handler that has to clean up after it.
(defun pf:fit-session (simp
                       / cmd lo tol ans go wp1 wp2 rawwalls rawcnrs
                         rawholds w step rstep v mk wallmk cnrmk
                         holdmk pf-decl-marks ss i en ed lay typ ext
                         nunsup nocs segs pts dpts allow loop tour ok
                         npt pf-nmoved again omits
                         pf-omitted pf-miss-pct pf-walls pf-corners
                         pf-holds pf-ptnames pf-dim-warned cands)
  ;; -- steps 1 to 6: the settings, walked as one chain --------------
  ;; Every question after the first offers Back (Undo is its hidden
  ;; synonym), so a mistyped tolerance or a wrong Yes costs one
  ;; keystroke instead of the whole run.  STEP is the position in the
  ;; chain and the only way through it: a step answered Back drops it
  ;; by one, and a step re-entered from below throws away whatever the
  ;; earlier pass collected there - markers included - so the second
  ;; answer replaces the first instead of piling on top of it.
  ;;
  ;; SIMPABHD starts the SAME chain at step 4.  Its three numbers are
  ;; not asked, so there is nothing behind the walls question and Back
  ;; there re-opens it instead of falling out of the run; the internal
  ;; step numbers do not move, only the ones printed (pf:step-n).
  (setq step (if simp 4 1) rawwalls nil rawcnrs nil rawholds nil
        wallmk nil cnrmk nil holdmk nil
        cmd    (if simp "SIMPABHD" "ABHD")
        lo     (if simp 4 1))
  (if simp (setq tol *PF-SIMP-TOL*))
  ;; steps 4 to 6 name survey points before any are selected, so the
  ;; whole drawing's are the candidates there; the selection decides
  ;; afterwards which of the declarations it holds
  (setq cands nil)
  (while (<= step 6)
    (cond

      ;; -- step 1: how close must the line stay to the points? ------
      ;; This is the one prompt people misread, so it says in plain
      ;; words what the number means and which way it moves the result.
      ;; initget 6 refuses zero and negative values - a zero tolerance
      ;; would silently collapse the fit into single-point stubs.
      ((= step 1)
       (setq pf-phase "reading the tolerance")
       (princ (strcat (pf:step-n step simp)
                      "how far may the fitted line sit from a survey point?"))
       (princ "\n  Type a distance in drawing units (1 = one inch, 2 at most), or")
       (princ "\n  pick two points in the drawing to measure one.")
       (princ "\n  Smaller = hugs the points.  Bigger = smoother, with fewer curves.")
       ;; the first question of the command: nothing to go back to
       (setq tol  (pf:ask-tol nil)
             step 2))

      ;; -- step 2: how many of the points may sit off the line? -----
      ;; Enter means the standard share; the answer is per run, on
      ;; purpose.
      ((= step 2)
       (setq pf-phase "reading the miss percentage")
       (princ (strcat (pf:step-n step simp)
                      "what percent of the points may sit OFF the line"))
       (princ "\n  (off, but still within the distance above)?")
       (princ (strcat "\n  Press Enter for the recommended "
                      (itoa (fix (+ 0.5 (* 100.0 (pf:miss-knob)))))
                      " percent - a fifth of an AB survey an inch off"
                      "\n  is what a built shell measures like."))
       (setq v (pf:ask-pct *PF-MISS-PCT* T))
       (if (eq v 'PF-BACK)
         (progn (princ "\n  Stepping back one question.")
                (setq step 1))
         (setq pf-miss-pct v
               step        3)))

      ;; -- step 3: optional cap on how many curves the result may use
      ((= step 3)
       (setq pf-phase "reading the curve limit")
       (princ (strcat (pf:step-n step simp)
                      "limit how many curves the result may use?"))
       (princ "\n  Type a whole number, None for no limit, or Auto for the")
       (princ (strcat "\n  recommended cap - one curve per "
                      (rtos *PF-ARC-DIV* 2 0)
                      " points, worked out once they are"
                      "\n  selected (a "
                      (itoa (pf:rec-arcs 30))
                      "-curve cap on a 30-point survey)."))
       (if (eq (pf:ask-cap T) 'PF-BACK)
         (progn (princ "\n  Stepping back one question.")
                (setq step 2))
         (setq step 4)))

      ;; -- step 4: any dead-straight walls to declare? --------------
      ;; Each declared wall is marked with a dashed line right away and
      ;; comes out of the fit as a straight LINE between those two
      ;; survey points, no matter what the arcs around it are doing.
      ((= step 4)
       ;; re-entered from step 5: throw away what the earlier pass
       ;; declared here, dashed markers and all, so the new answer
       ;; replaces the old instead of piling on top of it
       (foreach mk wallmk (pf:temp-kill mk))
       (setq wallmk nil)
       (setq pf-phase "asking about straight lines")
       (princ (strcat (pf:step-n step simp)
                      "does the pool edge have any dead-straight walls?"))
       (princ "\n  If Yes you will name the two end points of each - click the")
       (princ "\n  survey point, or type its number; a dashed line marks each wall.")
       (initget "Yes No Back Undo")
       (setq ans      (getkword "\n  Any straight lines? [Yes/No/Back] <No>: ")
             rawwalls nil)
       (if lzd:ask (lzd:ask "\n  Any straight lines? [Yes/No/Back] <No>: " ans) ans)
       (cond
         ((member ans '("Back" "Undo"))
          (setq step (pf:step-back step lo)))
         ((= ans "Yes")
          (if (null cands) (setq cands (pf:collect-points)))
          (setq rawwalls (if cands (pf:declare-walls cands) nil)
                wallmk   pf-decl-marks)
          (cond
            ((null cands)
             (princ (strcat "\n  No survey points in this drawing to declare"
                            " a wall on - a wall is named by its two"
                            " survey points."))
             (setq step 5))
            ((eq rawwalls 'PF-BACK)
             (setq rawwalls nil))              ; re-ask this step's Yes/No
            (T
              (if rawwalls
                (princ (strcat "\n  " (itoa (length rawwalls))
                               " straight wall(s) noted - the dashed markers on "
                               *PF-WALL-LAYER*
                               " clear themselves when the command finishes.")))
              (setq step 5))))
         (T (setq step 5))))

      ;; -- step 5: any sharp corners to declare? --------------------
      ;; The fitter finds obvious corners itself (turns over
      ;; *PF-CORNER-ANG*), but a gentler one still reads as a corner on
      ;; site.  A declared point is exempt from the tangency rule: the
      ;; fit breaks there instead of rounding it off.
      ((= step 5)
       (foreach mk cnrmk (pf:temp-kill mk))
       (setq cnrmk nil)
       (setq pf-phase "asking about sharp corners")
       (princ (strcat (pf:step-n step simp)
                      "are there any sharp corners the fit must not round off?"))
       (princ "\n  Obvious ones are found automatically; declare the gentler ones here.")
       (princ "\n  If Yes you will name each corner point - click it, or type its number.")
       (initget "Yes No Back Undo")
       (setq ans     (getkword "\n  Any sharp corners? [Yes/No/Back] <No>: ")
             rawcnrs nil)
       (if lzd:ask (lzd:ask "\n  Any sharp corners? [Yes/No/Back] <No>: " ans) ans)
       (cond
         ((member ans '("Back" "Undo"))
          (princ "\n  Stepping back one question.")
          (setq step 4))
         ((= ans "Yes")
          (if (null cands) (setq cands (pf:collect-points)))
          (setq rawcnrs (if cands (pf:declare-corners cands) nil)
                cnrmk   pf-decl-marks)
          (cond
            ((null cands)
             (princ (strcat "\n  No survey points in this drawing to declare"
                            " a corner on."))
             (setq step 6))
            ((eq rawcnrs 'PF-BACK)
             (setq rawcnrs nil))
            (T
              (if rawcnrs
                (princ (strcat "\n  " (itoa (length rawcnrs))
                               " corner(s) noted - the markers clear themselves"
                               " when the command finishes.")))
              (setq step 6))))
         (T (setq step 6))))

      ;; -- step 6: any points that must be held absolutely? ---------
      ;; Control shots and tie-ins are surveyed as exact positions: a
      ;; held point always ends a span, so the fit passes through it
      ;; exactly and the miss allowance can never write it off.
      ((= step 6)
       (foreach mk holdmk (pf:temp-kill mk))
       (setq holdmk nil)
       (setq pf-phase "asking about held points")
       (princ (strcat (pf:step-n step simp)
                      "any points that must be held ABSOLUTELY?"))
       (princ "\n  A held point can never be fudged: the line passes through it")
       (princ "\n  exactly, in every candidate.  If Yes you will name each one -")
       (princ "\n  click it, or type its number; a small dashed ring marks it.")
       (initget "Yes No Back Undo")
       (setq ans      (getkword "\n  Any held points? [Yes/No/Back] <No>: ")
             rawholds nil)
       (if lzd:ask (lzd:ask "\n  Any held points? [Yes/No/Back] <No>: " ans) ans)
       (cond
         ((member ans '("Back" "Undo"))
          (princ "\n  Stepping back one question.")
          (setq step 5))
         ((= ans "Yes")
          (if (null cands) (setq cands (pf:collect-points)))
          (setq rawholds (if cands (pf:declare-holds cands) nil)
                holdmk   pf-decl-marks)
          (cond
            ((null cands)
             (princ (strcat "\n  No survey points in this drawing to hold."))
             (setq step 7))
            ((eq rawholds 'PF-BACK)
             (setq rawholds nil))
            (T
              (if rawholds
                (princ (strcat "\n  " (itoa (length rawholds))
                               " held point(s) noted - the markers clear"
                               " themselves when the command finishes.")))
              (setq step 7))))
         (T (setq step 7))))))


  ;; -- step 7: the selection ----------------------------------------
  ;; only entity types this command can actually read, so a sloppy
  ;; crossing window over dimensions, hatches or text is harmless.
  ;; SPLINE and ELLIPSE are let in ON PURPOSE - not to fit them, but
  ;; so the classifier below can name them in a useful message.
  (setq pf-phase "waiting for the selection")
  (if pf-pick
    (setq ss pf-pick)
    (progn
      (princ (strcat (pf:step-n 7 simp)
                     "select the survey points (POINTS layer or ab_pt"))
      (princ "\n  blocks) and, if you have one, the POOL perimeter or ordering sketch.")
      (princ "\n  Select objects: ")
      (setq ss (ssget '((0 . "POINT,INSERT,LINE,ARC,CIRCLE,LWPOLYLINE,POLYLINE,SPLINE,ELLIPSE"))))
      (if lzd:watch (lzd:watch ss) ss)))
  (if (null ss)
    (princ "\nNothing usable selected (points, and optionally POOL lines/arcs/polylines).")
    (progn
      ;; -- sort the selection into perimeter segments and points -----
      (setq pf-phase "reading the selected entities")
      (setq segs nil pts nil i 0 nunsup 0 nocs 0
            npt 0 pf-ptnames nil pf-nmoved 0)
      (while (< i (sslength ss))
        (setq en  (ssname ss i)
              ed  (entget en)
              lay (strcase (cdr (assoc 8 ed)))
              typ (cdr (assoc 0 ed))
              ext (cdr (assoc 210 ed))
              i   (1+ i))
        ;; geometry drawn in a tilted UCS reads back in its own plane,
        ;; so a flat 2D fit of it would be wrong - count and warn.  The
        ;; plane seen from below, (0 0 -1), is no tilt: the outline's
        ;; ends (pf:ent-segs) and a point block's insertion (pf:ins-w)
        ;; are both taken to world, so it is neither warned about nor
        ;; mirrored
        (if (and ext (< (abs (caddr ext)) 0.999)) (setq nocs (1+ nocs)))
        (cond
          ;; survey points stored as block references (e.g. "ab_pt"):
          ;; a block with this name is ALWAYS a point, on any layer, and
          ;; its insertion point is taken as the location (the blocks are
          ;; never exploded - non-destructive).  Checked first so such
          ;; blocks are never mistaken for perimeter geometry.
          ((and (= typ "INSERT")
                (= (strcase (cdr (assoc 2 ed))) (strcase *PF-POINT-BLOCK*)))
           (pf:add-point (pf:2d (pf:ins-w ed))
                         (pf:block-number en)))
          ;; curve types we cannot fit, sitting on the POOL layer: count
          ;; them so the user gets told what to do, instead of a
          ;; mystifying "the perimeter does not close" later on
          ((and (= lay (strcase *PF-POOL-LAYER*))
                (member typ '("SPLINE" "ELLIPSE")))
           (setq nunsup (1+ nunsup)))
          ;; ABHD's own pool-bottom geometry lives on the POOL layer
          ;; too (stamped) - never read it back as a guide
          ((and (= lay (strcase *PF-POOL-LAYER*))
                (assoc -3 (entget en '("ABHD"))))
           nil)
          ;; perimeter / ordering sketch on the POOL layer
          ((= lay (strcase *PF-POOL-LAYER*))
           (setq segs (append segs (pf:ent-segs en))))
          ;; plain POINT entities on the POINTS layer
          ((and (= lay (strcase *PF-POINT-LAYER*)) (= typ "POINT"))
           (pf:add-point (pf:2d (cdr (assoc 10 ed))) nil))
          ;; any other block dropped on the POINTS layer -> a point too
          ((and (= typ "INSERT") (= lay (strcase *PF-POINT-LAYER*)))
           (pf:add-point (pf:2d (pf:ins-w ed))
                         (pf:block-number en)))))
      (if (> nunsup 0)
        (princ (strcat "\n" cmd ": warning - " (itoa nunsup)
                       " SPLINE/ELLIPSE object(s) on layer "
                       *PF-POOL-LAYER*
                       " were ignored (only lines, arcs, circles and"
                       " polylines can be read - explode or convert"
                       " them first).")))
      (if (> nocs 0)
        (princ (strcat "\n" cmd ": warning - " (itoa nocs)
                       " selected object(s) are not drawn in the world"
                       " plane; the fit is flat (XY) and may be wrong."
                       "  Set UCS to World and flatten them first.")))
      ;; a moved point is a deduction, not a shot - say how many were
      ;; left out, so a thin survey is explained rather than mysterious
      (if (and pf-nmoved (> pf-nmoved 0))
        (princ (strcat "\n" cmd ": " (itoa pf-nmoved)
                       " moved point(s) (a \"" *PF-MOVED-MARK*
                       "\" in the number) left out - nobody stood on"
                       " one of those, so the line is not held to it.")))

      ;; -- step 8: which of them to leave out ------------------------
      ;; The whole survey is in hand now, which is the first moment
      ;; anybody can see WHICH shot is the bad one - the one on the
      ;; coping, the double-shot, the rod held crooked.  Until this
      ;; step the omit list was only reachable from a Redo, so the
      ;; first fit was always drawn round a point the drafter could
      ;; already see was wrong and then redone.  Enter is the whole
      ;; question in one keystroke, and every point left out is still
      ;; MEASURED against the fit that is kept and ringed beside it.
      (if pts
        (progn
          (setq pf-phase "picking points to omit")
          (princ (strcat (pf:step-n 8 simp)
                         "any of those points to leave OUT of the fit?"))
          (setq pts (car (pf:omit-loop pts)))
          (if pf-omitted
            (princ (strcat "\n  " (itoa (length pf-omitted))
                           " point(s) left out - "
                           (itoa (length (pf:dedupe pts)))
                           " in the fit.")))))

      ;; the miss allowance: this share of the points (the answer to
      ;; step 2, rounded UP to a whole point) may sit off the result
      ;; by up to TOL
      (setq dpts  (if pts (pf:dedupe pts))
            allow (pf:ceil (* (pf:misspct) (length dpts))))
      ;; a declaration was made on a NAMED point before the selection
      ;; existed, so it is matched to the selection by that point's own
      ;; identity - and one made on a point the selection does not hold
      ;; is named and dropped, never snapped onto some other point
      (setq pf-walls nil)
      (foreach w rawwalls
        (if (and (pf:declared-in (car w) dpts "wall")
                 (pf:declared-in (cadr w) dpts "wall"))
          (setq pf-walls (cons (list (car (car w)) (car (cadr w)))
                               pf-walls))))
      (setq pf-walls (reverse pf-walls))
      (setq pf-corners nil)
      (foreach w rawcnrs
        (if (pf:declared-in w dpts "corner")
          (setq pf-corners (cons (car w) pf-corners))))
      (setq pf-corners (reverse pf-corners))
      ;; duplicates collapse to one
      (setq pf-holds nil)
      (foreach w rawholds
        (if (and (pf:declared-in w dpts "hold")
                 (not (pf:memb (car w) pf-holds)))
          (setq pf-holds (cons (car w) pf-holds))))
      (setq pf-holds (reverse pf-holds))
      (if (> (length dpts) *PF-SLOW-NOTE*)
        (princ (strcat "\n" cmd ": " (itoa (length dpts))
                       " points - ordering and fitting will take a"
                       " little while, please wait...")))
      (cond
        ;; leaving every point out is something step 8 lets you do, and
        ;; "none were found" is the wrong thing to say when the reason
        ;; is that they were all taken out again
        ((and (null pts) pf-omitted)
         (princ (strcat "\nEvery selected point was left out at step 8"
                        " (" (itoa (length pf-omitted))
                        " of them) - there is nothing left to fit.")))
        ((null pts)
         (princ (strcat "\nNo survey points found (looked for POINT entities on layer "
                        *PF-POINT-LAYER* " and \"" *PF-POINT-BLOCK*
                        "\" block insertions).")))
        ((and (null segs) (< (length dpts) 3))
         (princ "\nPoints-only mode needs at least 3 distinct points."))
        (T
         ;; work out the mode, then hand all three modes to the same
         ;; compare-and-choose step
         (setq tour nil loop nil ok T)
         (cond
           ((null segs)
            ;; ---- POINTS-ONLY: order the points ourselves ----------
            (princ "\nNo POOL geometry selected - ordering the points automatically.")
            (setq pf-phase "ordering the points"
                  tour     (pf:order-points dpts)))
           ((null (setq loop (pf:chain segs)))
            (setq ok nil))                     ; pf:chain said why
           ((not (pf:has-arcs loop))
            ;; ---- ORDERING SKETCH: the drawn loop is all straight
            ;; lines, so it only tells us the ORDER of the points;
            ;; the shape itself comes from the points
            (if (< (length dpts) 3)
              (progn
                (princ (strcat "\nThe lines-only POOL sketch only orders"
                               " the points, and at least 3 distinct"
                               " points are needed to build a shape."))
                (setq ok nil))
              (progn
                (princ "\nPOOL sketch is lines only - using it just to order the points.")
                (setq pf-phase "following the sketch order"
                      tour     (pf:loop-order loop dpts)))))
           (T
            (princ "\nUsing the drawn POOL perimeter as the guide.")
            (if pf-walls
              (princ (strcat "\n  (declared straight walls only steer"
                             " the points-built fit; here your drawn"
                             " straight segments are already kept)")))
            (if pf-holds
              (princ (strcat "\n  (held points only bind the"
                             " points-built fit; the drawn shape wins"
                             " here - the report flags any held point"
                             " the kept fit missed)")))))
         (if ok
           (progn
             (setq again T)
             (while again
               (setq again nil)
               (if (eq 'REDO (pf:compare tour loop pts dpts tol allow simp))
                 (progn
                   ;; -- redo: maybe omit points, then re-ask the
                   ;; numbers and draw a fresh trio -----------------
                   (setq pf-phase "picking points to omit")
                   (princ "\n\nRedoing the fit.  Any points to leave out this time?")
                   (setq omits (pf:omit-loop pts)
                         pts   (car omits)
                         omits (cadr omits)
                         dpts  (pf:dedupe pts))
                   ;; declared walls and corners anchored on a point
                   ;; omitted this round make no sense any more
                   (if omits (pf:prune-declared omits))
                   (if pf-omitted
                     (princ (strcat "\n  " (itoa (length pf-omitted))
                                    " point(s) omitted in total - "
                                    (itoa (length dpts))
                                    " in the fit.")))
                   (if (< (length dpts) 3)
                     (princ "\nToo few points remain for a fit - nothing redone.")
                     (progn
                       ;; walls and corners may change for the retry
                       (princ "\n\n  Straight walls and sharp corners can change too -")
                       (princ "\n  Enter keeps each list as it is.")
                       (if simp
                         (princ (strcat "\n  (there are no numbers to"
                                        " re-ask - " cmd
                                        " works to "
                                        (rtos *PF-SIMP-TOL* 2 3)
                                        " and draws the same five.)")))
                       ;; the Redo settings are a chain like the opening
                       ;; questions, and walk back the same way: Back at
                       ;; any of the six re-opens the one before it, and
                       ;; Back at the first has nowhere to go
                       ;; SIMPABHD asked no numbers, so its Redo has
                       ;; none to re-ask: the walls, corners and holds
                       ;; can still change, and so can the omit list
                       ;; above - that IS its Redo
                       (setq rstep 1)
                       (while (<= rstep (if simp 3 6))
                         (cond
                           ((= rstep 1)
                            (setq pf-phase "editing straight walls")
                            (pf:edit-walls dpts)   ; first: no Back out
                            (setq rstep 2))
                           ((= rstep 2)
                            (setq pf-phase "editing sharp corners")
                            (setq rstep (if (eq (pf:edit-corners dpts) 'PF-BACK)
                                          (progn (princ "\n  Stepping back one question.") 1)
                                          3)))
                           ((= rstep 3)
                            (setq pf-phase "editing held points")
                            (setq rstep (if (eq (pf:edit-holds dpts) 'PF-BACK)
                                          (progn (princ "\n  Stepping back one question.") 2)
                                          4)))
                           ((= rstep 4)
                            (princ "\n\n  New settings - Enter keeps each one as it is.")
                            (setq pf-phase "reading the tolerance"
                                  v        (pf:ask-tol T))
                            (if (eq v 'PF-BACK)
                              (progn (princ "\n  Stepping back one question.")
                                     (setq rstep 3))
                              (setq tol v rstep 5)))
                           ((= rstep 5)
                            (setq pf-phase "reading the miss percentage"
                                  v        (pf:ask-pct pf-miss-pct T))
                            (if (eq v 'PF-BACK)
                              (progn (princ "\n  Stepping back one question.")
                                     (setq rstep 4))
                              (setq pf-miss-pct v rstep 6)))
                           ((= rstep 6)
                            (setq pf-phase "reading the curve limit")
                            (setq rstep (if (eq (pf:ask-cap T) 'PF-BACK)
                                          (progn (princ "\n  Stepping back one question.") 5)
                                          7)))))
                       (setq allow (pf:ceil (* (pf:misspct)
                                               (length dpts))))
                       ;; the point order must forget the omitted ones
                       (cond
                         ((null loop)
                          (setq pf-phase "ordering the points"
                                tour     (pf:order-points dpts)))
                         ((not (pf:has-arcs loop))
                          (setq tour (pf:loop-order loop dpts))))
                       (setq again T))))))))))))
  (princ))

;; ---- the commands ----------------------------------------------------
(defun c:ABHD ( / stale pf-temp *error* pf-old-err pf-phase
                    undo-open pf-pick)
  ;; report which step failed if anything goes wrong, sweep away any
  ;; preview geometry drawn so far, then restore the old handler - a
  ;; cancelled run must not leave dashed markers or candidate outlines
  ;; lying around
  (setq pf-temp   nil
        pf-old-err *error*
        *error*
          (lambda (m)
            (if (and m (not (wcmatch (strcase m)
                     "*BREAK*,*CANCEL*,*QUIT*,*EXIT*")))
              (princ (strcat "\nABHD stopped while "
                             (if pf-phase pf-phase "starting up")
                             " -- " m)))
            (pf:temp-clear)
            ;; close the group after the sweep so one U takes back the
            ;; whole run, previews included; only if it ever opened
            (if undo-open (vl-catch-all-apply 'command-s (list "_.UNDO" "_End")))
            (setq undo-open nil)
            (setq *error* pf-old-err)
            ;; cover mode must not outlive the run that asked for it,
            ;; or the next ABHD would skip its bottom without a word
            (setq abhd:*nobottom* nil)
            (if lzd:report (lzd:report "ABHD" pf:*version* m))
            (princ)))
          (if lzd:begin (lzd:begin "ABHD" pf:*version*))

  ;; sweep leftovers from a run that was interrupted before it could
  ;; tidy up after itself
  (setq stale (pf:purge-mine *PF-WALL-LAYER*))
  (if (> stale 0)
    (princ (strcat "\nABHD: cleared " (itoa stale)
                   " leftover marker(s) from layer " *PF-WALL-LAYER*
                   ".")))

  ;; a pickfirst selection if there is one - kept for step 7, so the
  ;; survey can be highlighted before the command is typed.  Probed
  ;; here, before the undo group opens: the typed prompts between here
  ;; and step 7 leave a pickfirst set alone, a command call would not
  (setq pf-pick (ssget "_I" '((0 . "POINT,INSERT,LINE,ARC,CIRCLE,LWPOLYLINE,POLYLINE,SPLINE,ELLIPSE"))))
  (if lzd:watch (lzd:watch pf-pick) pf-pick)

  ;; one undo group around the whole fit - a U after ABHD takes back
  ;; the perimeter, the bottom and the markers in one step (the stale
  ;; purge above stays outside it, so U does not resurrect old junk)
  ;; only when undo is recording - _Begin in a drawing with UNDO
  ;; off (bit 1 of UNDOCTL clear) errors out of the command
  (if (= 1 (logand 1 (getvar "UNDOCTL")))
    (progn
      (command "_.UNDO" "_Begin")
      (setq undo-open T)))

  (princ "\n\nABHD - fit a pool perimeter through the surveyed points.")

  (pf:fit-session nil)

  ;; sweep the dashed wall markers and any candidate the user did not
  ;; keep - the command tidies up after itself
  (pf:temp-clear)
  (if undo-open (command "_.UNDO" "_End"))
  (setq undo-open nil)
  (setq *error* pf-old-err)   ; restore the previous error handler
  (setq abhd:*nobottom* nil)  ; cover mode lasts one run only
  (if lzd:end (lzd:end "ABHD"))
  (princ))

;; ---- SIMPABHD: the same fit with nothing to decide first -------------
;; ABHD's first three questions are the ones that stop a run before it
;; starts.  How far may the line sit off a point?  What share may be
;; off?  How many curves?  None of the three can be answered from the
;; command line, because the answer is the shape they produce - which
;; is why ABHD draws three of them and lets the drafter point.
;;
;; SIMPABHD takes that the rest of the way: it asks NONE of the three
;; and draws FIVE.  Two are ABHD's own ends of the trade - fit 1 the
;; least error there is, fit 5 the fewest curves that still hold the
;; distance - so whatever a typed answer could have produced sits
;; between them.  The three in the middle are ready-made answers, each
;; a share, a distance and a curve cap together, printed beside its
;; outline (*PF-SIMP-COMPARE*).  Everything after that is ABHD: the
;; same walls, corners and held points, the same selection, the same
;; table, the same pick, the same report, the same pool bottom.
;;
;; It is the same run, not a simpler one - pf:fit-session walks the
;; same chain from step 4, so a rule ABHD keeps is a rule this keeps.
(defun c:SIMPABHD ( / stale pf-temp *error* pf-old-err pf-phase
                        undo-open pf-pick)
  ;; report which step failed if anything goes wrong, sweep away any
  ;; preview geometry drawn so far, then restore the old handler - a
  ;; cancelled run must not leave dashed markers or candidate outlines
  ;; lying around
  (setq pf-temp   nil
        pf-old-err *error*
        *error*
          (lambda (m)
            (if (and m (not (wcmatch (strcase m)
                     "*BREAK*,*CANCEL*,*QUIT*,*EXIT*")))
              (princ (strcat "\nSIMPABHD stopped while "
                             (if pf-phase pf-phase "starting up")
                             " -- " m)))
            (pf:temp-clear)
            ;; close the group after the sweep so one U takes back the
            ;; whole run, previews included; only if it ever opened
            (if undo-open (vl-catch-all-apply 'command-s (list "_.UNDO" "_End")))
            (setq undo-open nil)
            (setq *error* pf-old-err)
            ;; cover mode is ABHDCOVER's, and it must not outlive any
            ;; run that reached the bottom flow with it set
            (setq abhd:*nobottom* nil)
            (if lzd:report (lzd:report "SIMPABHD" pf:*version* m))
            (princ)))
          (if lzd:begin (lzd:begin "SIMPABHD" pf:*version*))

  ;; sweep leftovers from a run that was interrupted before it could
  ;; tidy up after itself
  (setq stale (pf:purge-mine *PF-WALL-LAYER*))
  (if (> stale 0)
    (princ (strcat "\nSIMPABHD: cleared " (itoa stale)
                   " leftover marker(s) from layer " *PF-WALL-LAYER*
                   ".")))

  ;; a pickfirst selection if there is one - kept for the selection
  ;; step, so the survey can be highlighted before the command is
  ;; typed.  Probed here, before the undo group opens: the typed
  ;; prompts in between leave a pickfirst set alone, a command call
  ;; would not
  (setq pf-pick (ssget "_I" '((0 . "POINT,INSERT,LINE,ARC,CIRCLE,LWPOLYLINE,POLYLINE,SPLINE,ELLIPSE"))))
  (if lzd:watch (lzd:watch pf-pick) pf-pick)

  ;; one undo group around the whole fit - a U after SIMPABHD takes
  ;; back the perimeter, the bottom and the markers in one step (the
  ;; stale purge above stays outside it, so U does not resurrect old
  ;; junk).  Only when undo is recording - _Begin in a drawing with
  ;; UNDO off (bit 1 of UNDOCTL clear) errors out of the command
  (if (= 1 (logand 1 (getvar "UNDOCTL")))
    (progn
      (command "_.UNDO" "_Begin")
      (setq undo-open T)))

  (princ "\n\nSIMPABHD - fit a pool perimeter, with nothing to decide first.")
  (princ (strcat "\n  No numbers are asked.  Five perimeters are drawn to "
                 (rtos *PF-SIMP-TOL* 2 3)
                 " - the least"
                 "\n  error there is, the fewest curves that hold it, and"
                 " three ready-made"
                 "\n  answers in between - and you keep the one that looks"
                 " like the pool."))

  (pf:fit-session T)

  ;; sweep the dashed wall markers and any candidate the user did not
  ;; keep - the command tidies up after itself
  (pf:temp-clear)
  (if undo-open (command "_.UNDO" "_End"))
  (setq undo-open nil)
  (setq *error* pf-old-err)   ; restore the previous error handler
  (setq abhd:*nobottom* nil)  ; cover mode lasts one run only
  (if lzd:end (lzd:end "SIMPABHD"))
  (princ))

;; ABHD for a cover sheet: the same fit, with the pool-bottom question
;; answered No before it is asked.  A cover records the perimeter and
;; nothing below it, so the breaks, the hopper offsets and the slope
;; lines are work the sheet has no room for.
;;
;; A command of its own rather than a mode, so that a button runs
;; exactly the command named on it; the flag is cleared by c:ABHD on
;; both its exits, so it cannot leak into the next run.
(defun c:ABHDCOVER ()
  (setq abhd:*nobottom* t)
  (princ "\nABHDCOVER: cover sheet - the pool bottom will be skipped.")
  (c:ABHD)
  (princ))

;; ---- ADAB: the pool bottom on its own --------------------------------
;; The end of the ABHD flow as a command of its own: select an
;; existing perimeter - one closed polyline, or the exploded
;; lines/arcs that form one - and go straight to the breaks, the
;; hopper offsets and the slope lines.  The survey points do not have
;; to be selected: with none in the selection, every ab_pt block and
;; POINTS-layer point in the drawing is gathered and only those
;; sitting ON the loop (within *PF-PICKUP-EPS*) are used, so stray
;; depth shots and deck points stay out of it.  Points that ARE
;; selected are trimmed by the same rule.  For when the perimeter was
;; fitted (or drawn) some other day and only the floor is needed.
(defun c:ADAB ( / ss i en ed typ ext lay segs pts dpts loop nocs nskip
                    nall npt pf-nmoved stale pf-temp pf-ptnames
                    pf-dim-warned
                    *error* pf-old-err pf-phase undo-open pf-pick)
  (setq pf-temp   nil
        pf-old-err *error*
        *error*
          (lambda (m)
            (if (and m (not (wcmatch (strcase m)
                     "*BREAK*,*CANCEL*,*QUIT*,*EXIT*")))
              (princ (strcat "\nADAB stopped while "
                             (if pf-phase pf-phase "starting up")
                             " -- " m)))
            (pf:temp-clear)
            (if undo-open (vl-catch-all-apply 'command-s (list "_.UNDO" "_End")))
            (setq undo-open nil)
            (setq *error* pf-old-err)
            (if lzd:report (lzd:report "ADAB" pf:*version* m))
            (princ)))
          (if lzd:begin (lzd:begin "ADAB" pf:*version*))
  ;; sweep leftovers from a run interrupted before it could tidy up
  (setq stale (pf:purge-mine *PF-WALL-LAYER*))
  (if (> stale 0)
    (princ (strcat "\nADAB: cleared " (itoa stale)
                   " leftover marker(s) from layer " *PF-WALL-LAYER*
                   ".")))
  ;; a pickfirst selection if there is one, otherwise ask for it -
  ;; probed before the undo group opens, which would clear the set
  (setq pf-pick (ssget "_I" '((0 . "POINT,INSERT,LINE,ARC,CIRCLE,LWPOLYLINE,POLYLINE"))))
  (if lzd:watch (lzd:watch pf-pick) pf-pick)
  ;; one undo group around the whole bottom, same reasoning as c:ABHD
  ;; only when undo is recording - _Begin in a drawing with UNDO
  ;; off (bit 1 of UNDOCTL clear) errors out of the command
  (if (= 1 (logand 1 (getvar "UNDOCTL")))
    (progn
      (command "_.UNDO" "_Begin")
      (setq undo-open T)))
  (princ "\n\nADAB - draw the pool bottom over an existing perimeter.")
  (setq pf-phase "waiting for the selection")
  (if pf-pick
    (setq ss pf-pick)
    (progn
      (princ "\n\n  Select the pool perimeter - one closed polyline, or its exploded")
      (princ "\n  lines/arcs.  The survey points sitting on it are found by")
      (princ "\n  themselves; select them too only if they live somewhere unusual.")
      (princ "\n  Select objects: ")
      (setq ss (ssget '((0 . "POINT,INSERT,LINE,ARC,CIRCLE,LWPOLYLINE,POLYLINE"))))
      (if lzd:watch (lzd:watch ss) ss)))
  (if (null ss)
    (princ "\nNothing usable selected (survey points and the perimeter geometry).")
    (progn
      (setq pf-phase "reading the selected entities")
      (setq segs nil pts nil i 0 nocs 0 nskip 0
            npt 0 pf-ptnames nil pf-nmoved 0)
      (while (< i (sslength ss))
        (setq en  (ssname ss i)
              ed  (entget en)
              typ (cdr (assoc 0 ed))
              lay (strcase (cdr (assoc 8 ed)))
              ext (cdr (assoc 210 ed))
              i   (1+ i))
        (if (and ext (< (abs (caddr ext)) 0.999)) (setq nocs (1+ nocs)))
        (cond
          ;; ab_pt blocks are survey points wherever they sit
          ((and (= typ "INSERT")
                (= (strcase (cdr (assoc 2 ed))) (strcase *PF-POINT-BLOCK*)))
           (pf:add-point (pf:2d (pf:ins-w ed))
                         (pf:block-number en)))
          ;; a plain POINT counts on any layer here - the selection
          ;; is explicit, so there is no guessing involved
          ((= typ "POINT")
           (pf:add-point (pf:2d (cdr (assoc 10 ed))) nil))
          ;; other blocks only count as points on the points layer
          ((= typ "INSERT")
           (if (= lay (strcase *PF-POINT-LAYER*))
             (pf:add-point (pf:2d (pf:ins-w ed))
                           (pf:block-number en))))
          ;; ABHD's own scaffolding and results must never be read
          ;; back as perimeter: miss rings, dashed markers, and an
          ;; earlier bottom all live on known layers or carry the
          ;; ABHD stamp
          ((or (= lay (strcase *PF-MISS-LAYER*))
               (= lay (strcase *PF-WALL-LAYER*))
               (= lay (strcase *PF-BOTTOM-LAYER*))
               (assoc -3 (entget en '("ABHD"))))
           (setq nskip (1+ nskip)))
          (T
           (setq segs (append segs (pf:ent-segs en))))))
      (if (> nocs 0)
        (princ (strcat "\nADAB: warning - " (itoa nocs)
                       " selected object(s) are not drawn in the world"
                       " plane; the bottom is built flat (XY) and may"
                       " be wrong.  Set UCS to World and flatten them"
                       " first.")))
      (if (> nskip 0)
        (princ (strcat "\n  (" (itoa nskip)
                       " marker/bottom object(s) in the selection were"
                       " ignored)")))
      (setq dpts (if pts (pf:dedupe pts)))
      (cond
        ((null segs)
         (princ "\nNo perimeter found in the selection - include the closed polyline or its exploded lines/arcs."))
        ((null (setq loop (pf:chain segs))) nil)   ; pf:chain said why
        (T
         (if (null dpts)
           ;; no points in the selection: the perimeter knows its own.
           ;; Gather every survey point in the drawing and keep the
           ;; ones sitting on the loop.
           (progn
             (setq pf-phase "gathering the perimeter's points"
                   ss (ssget "_X"
                        (list '(-4 . "<OR")
                              '(-4 . "<AND") '(0 . "INSERT")
                              (cons 2 *PF-POINT-BLOCK*) '(-4 . "AND>")
                              '(-4 . "<AND") '(0 . "POINT")
                              (cons 8 *PF-POINT-LAYER*) '(-4 . "AND>")
                              '(-4 . "<AND") '(0 . "INSERT")
                              (cons 8 *PF-POINT-LAYER*) '(-4 . "AND>")
                              '(-4 . "OR>"))))
             (if ss
               (progn
                 (setq i 0)
                 (while (< i (sslength ss))
                   (setq en  (ssname ss i)
                         ed  (entget en)
                         typ (cdr (assoc 0 ed))
                         i   (1+ i))
                   (pf:add-point (pf:2d (pf:ins-w ed))
                                 (if (= typ "INSERT")
                                   (pf:block-number en))))))
             (setq dpts (if pts (pf:dedupe pts))
                   dpts (pf:near-loop dpts loop *PF-PICKUP-EPS*))
             (if dpts
               (princ (strcat "\n  " (itoa (length dpts))
                              " survey point(s) sitting on the"
                              " perimeter picked up automatically."))))
           ;; points WERE selected: trim them to the perimeter's own,
           ;; so depth shots and deck points caught by the window do
           ;; not get in the way of the break and waypoint snapping
           (progn
             (setq nall (length dpts)
                   dpts (pf:near-loop dpts loop *PF-PICKUP-EPS*))
             (if (< (length dpts) nall)
               (princ (strcat "\n  (" (itoa (- nall (length dpts)))
                              " selected point(s) well off the"
                              " perimeter were set aside)")))))
         ;; a moved point is a deduction, not a shot - say how many were
         ;; left out, so a thin survey is explained rather than mysterious
         (if (and pf-nmoved (> pf-nmoved 0))
           (princ (strcat "\nADAB: " (itoa pf-nmoved)
                          " moved point(s) (a \"" *PF-MOVED-MARK*
                          "\" in the number) left out - nobody stood on"
                          " one of those, so the line is not held to it.")))
         (if (null dpts)
           (princ (strcat "\nNo survey points sit on this perimeter"
                          " (within " (rtos *PF-PICKUP-EPS* 2 1)
                          ") - looked for \"" *PF-POINT-BLOCK*
                          "\" blocks anywhere and points on layer "
                          *PF-POINT-LAYER*
                          ".  Select the points explicitly if they"
                          " live elsewhere."))
           (pf:bottom loop dpts nil))))))
  (pf:temp-clear)
  (if undo-open (command "_.UNDO" "_End"))
  (setq undo-open nil)
  (setq *error* pf-old-err)
  (if lzd:end (lzd:end "ADAB"))
  (princ))

;; ---- TUTORIALABHD ----------------------------------------------------
;; A guided introduction for new users, two ways: Checks lists every
;; rule and safeguard the commands apply, for readers; Demo draws a
;; practice pool and walks it through the whole flow on screen, stage
;; by stage, for lookers - then cleans up after itself.

(defun pf:tut-pause ()
  ((lambda (v) (if lzd:ask (lzd:ask "\n  --- press Enter to continue ---" v) v))
    (getstring "\n  --- press Enter to continue ---"))
  (princ))

;; The stage caption above the demo, replaced at each stage.
(defun pf:tut-cap (p txt hgt / e)
  (setq e (entmakex (list '(0 . "TEXT") '(100 . "AcDbEntity")
                          (cons 8 *PF-OUT-LAYER*) '(62 . 2)
                          '(100 . "AcDbText")
                          (cons 10 (list (car p) (cadr p) 0.0))
                          (cons 40 hgt)
                          (cons 1 txt))))
  (if e (pf:temp-add (pf:tag-mine e)))
  e)

;; The practice survey: a kidney-shaped pool about 30 x 16 ft around
;; CP, drawn as POINTs on the points layer and numbered like ab_pt
;; blocks would be.  Returns the points in walking order.
(defun pf:tut-survey (cp / n i tt r p out)
  (pf:ensure-layer *PF-POINT-LAYER* *PF-POINT-COLOUR*)
  (setq n 44 i 0 out nil)
  (while (< i n)
    (setq tt  (* 2.0 pi (/ (float i) n))
          r   (+ 150.0 (* 45.0 (cos tt)) (* 22.0 (sin (* 2.0 tt)))
                 (* -14.0 (cos (* 3.0 tt))))
          p   (list (+ (car cp) (* r (cos tt) 1.15))
                    (+ (cadr cp) (* r (sin tt) 0.75)))
          i   (1+ i)
          out (cons p out))
    (pf:add-point p nil)
    (pf:temp-add (pf:tag-mine
      (entmakex (list '(0 . "POINT") '(100 . "AcDbEntity")
                      (cons 8 *PF-POINT-LAYER*)
                      '(100 . "AcDbPoint")
                      (cons 10 (list (car p) (cadr p) 0.0)))))))
  (reverse out))

;; The reading tour: every rule and safeguard, in the order the
;; commands apply them.
(defun pf:tut-checks ()
  (princ "\n\nWHAT ABHD NEEDS")
  (princ "\n  * Survey points: ab_pt block inserts (any layer, their number")
  (princ "\n    attribute names them) or POINT entities on layer POINTS.")
  (princ (strcat "\n  * A number carrying the letter \""
                 *PF-MOVED-MARK*
                 "\" is a MOVED point - ABFIND"))
  (princ "\n    writes \"17m\" when it works out where Pt.17 SHOULD have been")
  (princ "\n    from two tape readings.  Nobody stood there, so it is left out")
  (princ "\n    of the fit entirely: not ordered, not fitted, not held, not")
  (princ "\n    counted against the allowance, never ringed as a miss.  The")
  (princ "\n    original it came from is still in.  The run says how many went.")
  (princ "\n  * Optionally on layer POOL: a drawn perimeter (guided mode) or a")
  (princ "\n    lines-only connect-the-dots sketch (sets the point order).")
  (princ "\n    With neither, the points are ordered automatically.")
  (pf:tut-pause)
  (princ "\nTHE SEVEN QUESTIONS")
  (princ "\n  1. Max distance a point may sit from the line (2 inch ceiling).")
  (princ (strcat "\n  2. Percent of points allowed off the line (Enter = "
                 (itoa (fix (+ 0.5 (* 100.0 (pf:miss-knob)))))
                 ", rounded"))
  (princ "\n     UP to whole points - the slack that buys longer arcs).")
  (princ (strcat "\n  3. Curve cap (Enter = Auto: one curve per "
                 (rtos *PF-ARC-DIV* 2 0)
                 " points, rounded to"))
  (princ "\n     the nearest, worked out once they are selected.  None =")
  (princ "\n     unlimited; either way it binds in every mode).")
  (princ "\n  4. Dead-straight walls: name both ends, dashed marker, comes out")
  (princ "\n     as a straight LINE no arc may swallow or cross.")
  (princ "\n  5. Sharp corners: name points where tangency is waived.")
  (princ "\n  6. Held points: name points the line must pass through EXACTLY -")
  (princ "\n     never fudged, never spent from the miss allowance; tangency")
  (princ "\n     still applies at them (they are not corners).")
  (princ "\n     A point is NAMED the way PERPMARK names one: click it, or type")
  (princ "\n     its number (17, Pt.17 and #17 are the same point).  A click has")
  (princ (strcat "\n     to land within " (rtos *PF-SNAP* 2 0)
                 " of a point; a miss is re-asked, never snapped"))
  (princ "\n     to whatever was nearest.")
  (princ "\n  7. Select the points (and the POOL guide if you have one).")
  (princ "\n  SIMPABHD asks NONE of the first three and draws five perimeters")
  (princ "\n  instead of three - the least error there is, the fewest curves")
  (princ "\n  that hold an inch, and three ready-made answers in between.")
  (princ "\n  Everything from question 4 on is the same run, rule for rule.")
  (pf:tut-pause)
  (princ "\nWHAT THE FITTER GUARANTEES")
  (princ "\n  * Arc endpoints sit ON survey points; arc middles pass through a")
  (princ "\n    point too (3-point arcs) whenever such an arc holds the span;")
  (princ "\n    floating arcs are a rare last resort.")
  (princ "\n  * Joints meet within 8 degrees of tangent; when nothing fits the")
  (princ "\n    window it stretches 1.25x then 1.5x rather than being dropped,")
  (princ "\n    and then a one-point stub carries the tangent on.  A SECOND")
  (princ "\n    stub straight after it keeps only what the window allows, so a")
  (princ "\n    mismatch dies away instead of doubling at every stub.")
  (princ "\n  * No arc may sweep further than the points it covers actually")
  (princ (strcat "\n    turn, plus "
                 (rtos (* 180.0 (/ *PF-ARC-SLACK* pi)) 2 0)
                 " degrees - so a shaky survey comes out as a"))
  (princ "\n    shape, not as a string of loops.")
  (princ "\n  * A stray shot can be given up rather than fought over: up to")
  (princ (strcat "\n    " (rtos (* 100.0 *PF-DROP-PCT*) 2 0)
                 " percent of the points may end further off than your"
                 " distance"))
  (princ "\n    (counted \"not held\" and ringed).  Only a point plainly off -")
  (princ (strcat "\n    past " (rtos *PF-DROP-MULT* 2 0)
                 "x that distance - can go, only where holding it would"))
  (princ "\n    break the run, and never a held point, a corner or a wall")
  (princ "\n    point.  The red fit gives up none.  A shot thrown far enough")
  (princ "\n    sideways to read as a corner ENDS a span, so the line still")
  (princ "\n    runs through it - leave it out at step 8 or a Redo if it")
  (princ "\n    is wrong.")
  (princ "\n  * Radii snap to whole feet, half feet, then inches - only when")
  (princ "\n    the points allow it; the points always outrank pretty radii.")
  (princ "\n  * Turns over 45 degrees are corners and are never buried inside")
  (princ "\n    an arc; the loop is checked for crossing itself.")
  (pf:tut-pause)
  (princ "\nCHOOSING A FIT")
  (princ "\n  Three candidates draw at once, the two ends of the curves-against-")
  (princ "\n  accuracy trade and the middle: red spends the most curves to get")
  (princ "\n  the error near nothing (it ignores your distance and the curve")
  (princ "\n  cap), yellow is your settings exactly, cyan holds that same")
  (princ "\n  distance with the fewest curves it can.  Each is numbered on")
  (princ "\n  screen with its figures, plus a table: segs, curves, worst off,")
  (princ "\n  avg all, avg off, not held - all measured against the distance")
  (princ "\n  you typed.  Click the one to keep, or type 1/2/3;")
  (princ "\n  All keeps the trio, None erases everything.")
  (princ "\n  The kept fit moves onto the POOL layer in ByLayer colour.")
  (pf:tut-pause)
  (princ "\nWHAT GETS FLAGGED")
  (princ "\n  Points no fit built to your distance can hold are called out")
  (princ "\n  before you choose (the tight fit threads every point it can")
  (princ "\n  reach, so it abstains from that count).  The kept fit rings its")
  (princ "\n  unheld points (4 inch circles on FGStep) and")
  (princ "\n  lists them beside the pool, worst first, by point number - and")
  (princ "\n  rings the points you LEFT OUT the same way, each measured")
  (princ "\n  against the line you kept, because that number is what says")
  (princ "\n  whether leaving it out was right.  Under the list goes one")
  (princ "\n  line naming them all: \"- Pt.12, Pt.15 and Pt.20 are bad.\"")
  (princ "\n  Only ABHD's own stamped objects on FGStep are ever replaced.")
  (pf:tut-pause)
  (princ "\nREDO")
  (princ "\n  Redo at the choose prompt refits without leaving the command:")
  (princ "\n  leave more points out by clicking them (clicking a ringed one")
  (princ "\n  restores it - omissions carry across redos), add/remove walls,")
  (princ "\n  sharp corners and held points, then the three numbers are asked")
  (princ "\n  again with Enter keeping each.  Repeat until a fit is kept.")
  (pf:tut-pause)
  (princ "\nTHE POOL BOTTOM")
  (princ "\n  After keeping one fit (or via ADAB over any existing perimeter):")
  (princ "\n  pick the SHALLOW BREAK ends, then the DEEP BREAK ends.  The back")
  (princ "\n  of the hopper is found automatically - the survey point nearest")
  (princ "\n  a ray cast from the deep break's middle, away from the shallow.")
  (princ "\n  Three offsets are asked by point number (type 42 or 3'6 - the")
  (princ "\n  format picks the dim style on the back/waypoint dims: SIDE")
  (princ "\n  DIMENSION for feet-inches, STANDARD INCHES for inches).")
  (pf:tut-pause)
  (princ "\n  The hopper's corners land ON the deep break line, which is drawn")
  (princ "\n  as three lines: DASHED2 stubs wall-to-corner, solid across.  Its")
  (princ "\n  dims form the K/L/M string a foot off the line on the shallow")
  (princ "\n  side.  Each slope line to the shallow break is asked Straight,")
  (princ "\n  Guided (follows the perimeter, easing to nothing), or Points")
  (princ "\n  (pick points with pinned offsets, square off the wall, each")
  (princ "\n  dimensioned).  Offsets draw as few merged arcs, not facets, and")
  (princ "\n  every line and dim lands on the POOL layer.")
  (pf:tut-pause)
  (princ "\nHOUSEKEEPING")
  (princ "\n  ADAB needs only the perimeter selected - the survey points on it")
  (princ "\n  are picked up automatically (strays are set aside).  Scaffolding")
  (princ "\n  - markers, previews, labels - sweeps itself on any exit, ESC")
  (princ "\n  included, and a run interrupted mid-flight is tidied by the next.")
  (princ (strcat "\n  This is ABHD " pf:*version*
                 " - the versioned twin file carries the same name."))
  (princ))

;; The watching tour: draw it, fit it, choose it, floor it, clean up.
(defun pf:tut-demo ( / cp tour dpts allow bb hgt cap v segs ent cand
                       kept d1 d2 s1 s2 sp1 sp2 dp1 dp2 back lines q
                       pts npt pf-nmoved pf-ptnames pf-miss-pct pf-walls
                       pf-corners pf-holds pf-dim-warned)
  (setq pf-phase "picking a spot for the demo")
  (princ "\n\n  The demo draws a practice pool about 30 ft wide, walks it")
  (princ "\n  through the whole flow, and cleans up after itself.")
  (setq cp (getpoint "\n  Pick a clear spot for it: "))
  (if lzd:ask (lzd:ask "\n  Pick a clear spot for it: " cp) cp)
  (if (null cp)
    (princ "\n  (no spot picked - tutorial ended, nothing drawn)")
    (progn
      ;; the demo draws its captions, its candidates and its labels on
      ;; the preview layer, and entmake onto a layer the drawing does
      ;; not have fails - so a first-time drawing, which is exactly who
      ;; runs a tutorial, got an empty tour.  pf:compare gates the same
      ;; layer for the same reason
      (pf:ensure-layer *PF-OUT-LAYER* *PF-OUT-COLOUR*)
      ;; the click is in the drafter's UCS and the tour is entmade in
      ;; world numbers - taken raw, a moved UCS drew it away from the spot
      ;; that was picked for it
      (setq cp   (pf:2d (trans cp 1 0))
            npt  0
            pf-nmoved 0
            tour (pf:tut-survey cp)
            dpts (pf:dedupe pts)
            bb   (pf:bbox dpts)
            hgt  (/ (- (caddr bb) (car bb)) 24.0)
            allow (pf:ceil (* (pf:misspct) (length dpts))))
      (setq cap (pf:tut-cap (list (car bb) (+ (cadddr bb) hgt))
                  "1. The survey: ab_pt blocks or POINTs on POINTS"
                  hgt))
      (princ "\n\n  1. A surveyor shot these points along the pool edge.")
      (pf:tut-pause)
      ;; the walking order
      (if (and cap (entget cap)) (entdel cap))
      (setq cap (pf:tut-cap (list (car bb) (+ (cadddr bb) hgt))
                  "2. The points are ordered into a loop" hgt)
            ent (pf:temp-add (pf:tag-mine
                  (pf:make-pline
                    (mapcar '(lambda (p) (list p 0.0)) tour)
                    *PF-OUT-LAYER* 8))))
      (princ "\n  2. ABHD orders them into a closed loop (a lines-only sketch")
      (princ "\n     on POOL can dictate this order instead).")
      (pf:tut-pause)
      (if (and ent (entget ent)) (entdel ent))
      ;; the three candidates
      (if (and cap (entget cap)) (entdel cap))
      (setq cap (pf:tut-cap (list (car bb) (+ (cadddr bb) hgt))
                  "3. Three candidates: red tight, yellow asked, cyan few"
                  hgt)
            cand nil)
      (foreach v *PF-COMPARE*
        (setq segs (pf:build tour nil pts dpts 1.0 allow (car v))
              ent  (pf:temp-add (pf:tag-mine
                     (pf:make-pline
                       (mapcar '(lambda (s) (list (car s) (caddr s)))
                               segs)
                       *PF-OUT-LAYER* (cadr v))))
              cand (cons (list segs ent) cand)))
      (setq cand (reverse cand))
      (princ "\n  3. Three fits draw at once - the most curves for the least")
      (princ "\n     error, your settings exactly, and the fewest curves that")
      (princ "\n     still hold your distance - each numbered with its figures,")
      (princ "\n     plus a table at the command line.  Every arc runs point to")
      (princ "\n     point, joints within 8 degrees of tangent, radii on feet")
      (princ "\n     and inches where the points allow.")
      (pf:tut-pause)
      ;; keep the middle one
      (if (and cap (entget cap)) (entdel cap))
      (setq cap (pf:tut-cap (list (car bb) (+ (cadddr bb) hgt))
                  "4. Click one to keep - Redo refits, leaves more out"
                  hgt))
      (setq q (cadr (car cand)))
      (if (and q (entget q)) (entdel q))
      (setq q (cadr (caddr cand)))
      (if (and q (entget q)) (entdel q))
      (setq kept (car (cadr cand)))
      (pf:set-bylayer (cadr (cadr cand)))
      (princ "\n  4. Click the outline you like (or type its number) - the")
      (princ "\n     rest are swept.  Unheld points - and any you left out at")
      (princ "\n     step 8 - would be ringed on FGStep, listed by number with")
      (princ "\n     how far off each landed, and named on one line under the")
      (princ "\n     list.  Redo refits with new settings, more points left")
      (princ "\n     out, and edited walls or corners.")
      (pf:tut-pause)
      ;; the bottom
      (if (and cap (entget cap)) (entdel cap))
      (setq cap (pf:tut-cap (list (car bb) (+ (cadddr bb) hgt))
                  "5. The bottom: breaks, hopper, K/L/M dims, slopes"
                  hgt))
      (setq d1  (nth 4 tour)  d2 (nth 40 tour)
            s1  (nth 18 tour) s2 (nth 26 tour)
            sp1 (pf:curve-near s1 kept) sp2 (pf:curve-near s2 kept)
            dp1 (pf:curve-near d1 kept) dp2 (pf:curve-near d2 kept)
            back (pf:hopper-back dp1 dp2 sp1 sp2 dpts))
      (pf:ensure-layer *PF-POOL-LAYER* *PF-POOL-COLOUR*)
      ;; where the drawing stood BEFORE the break lines: the walk below
      ;; has to start behind them, because bottom-draw takes them out
      ;; of the registry along with its own output.  Started after them
      ;; instead, the shallow break line was dropped and never picked
      ;; back up - so a swept demo left one line on the POOL layer
      (setq q (entlast))
      (setq lines (list (pf:temp-add (pf:tag-mine
                          (pf:make-line sp1 sp2 nil nil)))
                        (pf:temp-add (pf:tag-mine
                          (pf:make-line dp1 dp2 nil nil)))))
      (pf:bottom-draw kept sp1 sp2 dp1 dp2 back 12.0 12.0 18.0 nil
                      lines (list T nil))
      ;; bottom-draw promotes its output out of the scaffolding
      ;; registry; a tutorial must still clean it, so re-register
      ;; everything it just made
      (while (setq q (entnext q)) (pf:temp-add q))
      (princ "\n\n  5. ADAB (or the offer after keeping a fit) added the")
      (princ "\n     breaks, found the back point by itself, pulled the")
      (princ "\n     hopper in at your three offsets (asked by point number),")
      (princ "\n     dimensioned them a foot off the deep break on the")
      (princ "\n     shallow side, and ran one")
      (princ "\n     slope guided along the curve, the other straight.")
      (pf:tut-pause)
      (if (and cap (entget cap)) (entdel cap))
      (princ "\n\n  That is the whole flow.  TUTORIALABHD Checks lists every")
      (princ "\n  rule; ABHD runs it on your survey; ADAB does just the")
      (princ "\n  bottom over any perimeter.")
      (initget "Yes No")
      (if (= "Yes" ((lambda (v) (if lzd:ask (lzd:ask "\n  Keep the demo drawing to poke at? [Yes/No] <No>: " v) v))
                     (getkword
                       "\n  Keep the demo drawing to poke at? [Yes/No] <No>: ")))
        (progn
          (setq pf-temp nil)
          (princ "\n  Kept - erase it whenever; every piece is stamped ABHD."))
        (princ "\n  Swept - the drawing is as it was.")))))

(defun c:TUTORIALABHD ( / mode pf-temp pf-phase *error* pf-old-err)
  (setq pf-temp   nil
        pf-old-err *error*
        *error*
          (lambda (m)
            (if (and m (not (wcmatch (strcase m)
                     "*BREAK*,*CANCEL*,*QUIT*,*EXIT*")))
              (princ (strcat "\nTUTORIALABHD stopped -- " m)))
            (pf:temp-clear)
            (setq *error* pf-old-err)
            (if lzd:report (lzd:report "TUTORIALABHD" pf:*version* m))
            (princ)))
          (if lzd:begin (lzd:begin "TUTORIALABHD" pf:*version*))
  (princ (strcat "\n\nTUTORIALABHD - how the ABHD pool fitter works ("
                 pf:*version* ")."))
  ;; one bracket, exactly the keyword list (STANDARDS section 1 rule
  ;; 1), and the standard tutorial selector with Both
  (initget "Checks Demo Both")
  (setq mode (getkword
               "\n  Read the checks it applies, watch a drawn demo, or both? [Checks/Demo/Both] <Both>: "))
  (if lzd:ask (lzd:ask "\n  Read the checks it applies, watch a drawn demo, or both? [Checks/Demo/Both] <Both>: " mode) mode)
  (cond ((= mode "Checks") (pf:tut-checks))
        ((= mode "Demo")   (pf:tut-demo))
        (t (pf:tut-checks) (pf:tut-demo)))
  (pf:temp-clear)
  (setq *error* pf-old-err)
  (if lzd:end (lzd:end "TUTORIALABHD"))
  (princ))

;; The same tutorial under the bottom command's name, for whoever
;; goes looking for it there.
(defun c:TUTORIALADAB () (c:TUTORIALABHD))

;; Which build is loaded - the first thing to check when a run does
;; something the notes above say it should not.
(defun c:ABHDVER ()
  (princ (strcat "\nABHD " pf:*version*))
  (princ))

;; Quiet inside the whole build: LAZPASS.lsp and
;; CALOFIN-LOADER.lsp set the flag while they load their members,
;; because one file's greeting is a greeting and sixty-three of
;; them is a wall the drafter scrolls past in every drawing they
;; open.  APPLOADed alone the flag is nil and this prints, which
;; is the one time somebody wants to be told.  CALVER reports the
;; whole roster whenever it is asked.
(if (not *calofin-quiet*)
  (progn
    (princ (strcat "\nABHD " pf:*version*
                   " loaded.  ABHD fits the pool perimeter through its"
                   " points;"))
    (princ "\nSIMPABHD does the same with nothing to decide first;")
    (princ "\nADAB draws the pool bottom over an existing perimeter;")
    (princ "\nTUTORIALABHD (or TUTORIALADAB) walks new users through everything.")))
(princ)
