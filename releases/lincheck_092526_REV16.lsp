;;; ===================================================================
;;; LINCHECK.LSP - Liner tech drawing checklist
;;;
;;; Interactive AutoLISP routine that runs down the liner drawing
;;; checklist one item at a time, prompting the tech to complete /
;;; answer each item, then prints a report of everything that was
;;; checked, answered, and noted along the way.
;;;
;;; Every item after the first also offers Back (type B; Undo works
;;; too), which re-asks the previous item and drops what it logged -
;;; a mis-answered question never means Esc and a fresh start.  At the
;;; typed prompts (notes, values, cross dims) Back is typed like a
;;; note: B, BACK, U or UNDO alone, any case.
;;;
;;; Load with APPLOAD (or (load "lincheck.lsp")) and run the
;;; LINCHECK command.
;;; ===================================================================

;;; ------------------------------------------------------------------
;;; Helpers
;;; ------------------------------------------------------------------

(setq *lincheck-version* "v1.6")   ; announced on load; release_lisp.py
                                      ; stamps the dated twin in releases/

;;; ======================================================================
;;;  TUNABLES -- every value LINCHECK reads that someone might want to
;;;  change lives in this block, and nowhere else in the file.
;;;
;;;  How to change one: edit the value, save, and APPLOAD the file
;;;  again.  To try a value for one session only, type the setq at the
;;;  command line, because every knob is read when the command runs,
;;;  not when the file loads.
;;;
;;;  What is NOT here, on purpose: the checklist's questions.  This
;;;  tool IS its questions -- their wording, their order and which
;;;  answer opens which follow-up are one thing, held in the lin:
;;;  functions below, and a table of prompts split from the branching
;;;  that reads them would be two places to keep in step instead of
;;;  one.  The knobs here are how the checklist TALKS, not what it asks.
;;; ----------------------------------------------------------------------

;; -- how the report reads ------------------------------------------------

;; The report is printed to the command line, one line per item.  These
;; are the pieces every line is built from: the tick that marks a done
;; item, what separates an item from a note typed against it, and what
;; separates a question from the answer picked.
(setq lin:*tick*     "[x] ")
(setq lin:*note-sep* " -- ")
(setq lin:*ans-sep*  " -> ")

;; A cross dimension is logged indented under its heading by this.
(setq lin:*indent*   "    ")

;; A section heading, in the report and on the command line.  The two
;; differ on purpose: the report's is quieter, since it is read as a
;; block rather than watched as it goes by.
(setq lin:*head-in*  "== ")
(setq lin:*head-out* "==")
(setq lin:*head-echo-in*  "=== ")
(setq lin:*head-echo-out* "===")

;; The banner the printed report is boxed in, and its title.  RULE is
;; drawn as-is, so its width is what sets the box's; the title is
;; centred inside a line of the same character.
(setq lin:*rule*     "############################################")
(setq lin:*title*    "#          LINER CHECKLIST REPORT          #")

;; -- what a typed answer may say -----------------------------------------

;; A getstring prompt cannot take initget keywords, so "go back a step"
;; has to be typed like a note.  These are the words that mean it,
;; matched case-blind and whole; add a synonym and every typed prompt
;; takes it.
(setq lin:*back-words* '("B" "BACK" "U" "UNDO"))

;;; ----------------------------------------------------------------------
;;;  END TUNABLES.  The two globals below are STATE, not knobs: what
;;;  one run of the checklist has collected so far.

(setq *lin:log* nil)   ; collected report lines

(setq *lin:prev* nil)  ; each question's previous answer, keyed by its
                       ; exact prompt text.  Session memory on purpose:
                       ; it only ever supplies a <default> the user must
                       ; still Enter through, never an answer by itself,
                       ; so a re-run over the same job is Enter-Enter
                       ; down the unchanged questions
;;; ======================================================================

;; Record a line for the report.
(defun lin:log (msg)
  (setq *lin:log* (append *lin:log* (list msg)))
  msg
)

;; Keep only the first N report lines - the rollback when a Back drops
;; what an item logged.
(defun lin:trim (n / out i)
  (setq out nil i 0)
  (foreach l *lin:log*
    (if (< i n) (setq out (cons l out)))
    (setq i (1+ i))
  )
  (setq *lin:log* (reverse out))
)

;; T when a typed string means "go back a step" - getstring prompts
;; cannot take initget keywords, so Back is typed like a note.
(defun lin:back-word (s)
  (member (strcase s) lin:*back-words*)
)

;; Section header - printed to the command line and added to the report.
(defun lin:head (title)
  (princ (strcat "\n\n" lin:*head-echo-in* title lin:*head-echo-out*))
  (lin:log "")
  (lin:log (strcat lin:*head-in* title lin:*head-out*))
)

;; Simple check-off item.  Shows the item, waits for the tech to press
;; Enter when done (or type a note/value to record with it).  With back
;; non-nil, B (Back) returns the symbol LIN-BACK instead of logging.
(defun lin:check (item back / val)
  (setq val (getstring T (strcat "\n[ ] " item
                                 "\n      (Enter = done"
                                 (if back ", B = back" "")
                                 ", or type a note): ")))
  (if lzd:ask (lzd:ask (getvar "LASTPROMPT") val) val)
  (cond
    ((and back (lin:back-word val)) 'LIN-BACK)
    ((= val "") (lin:log (strcat lin:*tick* item)) val)
    (T (lin:log (strcat lin:*tick* item lin:*note-sep* val)) val)
  )
)

;; Ask the user to pick one keyword out of a list.  With back non-nil
;; the choices also take Back (Undo accepted as a hidden synonym),
;; returning the symbol LIN-BACK.
;; The first time a question is ever asked Enter is rejected - the
;; checklist stays deliberate - but its answer is remembered in
;; *lin:prev*, so every later ask offers it as the <default>.
(defun lin:ask (prompt kwlist back / ans dflt)
  (setq dflt (cdr (assoc prompt *lin:prev*)))
  (while (not ans)
    (initget (if dflt 0 1)
             (if back (strcat kwlist " Back Undo") kwlist))
    (setq ans (getkword (strcat "\n" prompt " ["
                                (vl-string-translate " " "/" kwlist)
                                (if back "/Back" "") "]"
                                (if dflt (strcat " <" dflt ">") "") ": ")))
    (if lzd:ask (lzd:ask prompt ans) ans)
    (if (and (null ans) dflt) (setq ans dflt))
  )
  (if (member ans '("Back" "Undo"))
    'LIN-BACK
    (progn (setq *lin:prev* (cons (cons prompt ans) *lin:prev*))
           (lin:log (strcat lin:*tick* prompt lin:*ans-sep* ans)) ans)
  )
)

;; Yes/No convenience wrapper.  Returns T for Yes, nil for No, or the
;; symbol LIN-BACK.
(defun lin:yesno (prompt back / v)
  (setq v (lin:ask prompt "Yes No" back))
  (if (eq v 'LIN-BACK) v (= v "Yes"))
)

;; Ask for a value; records the value, or "NA" if none was provided.
;; With back non-nil, B (Back) returns the symbol LIN-BACK instead.
(defun lin:value (label back / val)
  (setq val (getstring T (strcat "\n    " label " (value or NA"
                                 (if back ", B = back" "") "): ")))
  (if lzd:ask (lzd:ask (getvar "LASTPROMPT") val) val)
  (cond
    ((and back (lin:back-word val)) 'LIN-BACK)
    ((or (= val "") (= (strcase val) "NA") (= (strcase val) "N/A"))
     (lin:log (strcat "    " label ": NA (not provided)")) val)
    (T (lin:log (strcat "    " label ": " val)) val)
  )
)

;; Run the checklist as a list of one-question stages with Back between
;; them.  Each stage is (test-expr . fn): a stage whose test evaluates
;; nil is skipped, and tests are re-evaluated on every pass, so backing
;; up and changing an answer re-routes the branch.  A stage returning
;; LIN-BACK rewinds to the previous asked stage and drops everything
;; logged since just before it; LIN-STOP ends the run early (the report
;; still prints).  Stage 1 has nowhere to go back to, so it re-asks.
(defun lin:stages (fns / i n v it asked mark)
  (setq i 0 n (length fns) asked nil)
  (while (< i n)
    (setq it (nth i fns))
    (if (and (car it) (not (eval (car it))))
      (setq i (1+ i))                       ; branch not taken - skip
      (progn
        (setq mark (length *lin:log*)
              v    (apply (cdr it) nil))
        (cond
          ((eq v 'LIN-BACK)
           (lin:trim mark)                  ; drop the aborted item's log
           (if asked
             (progn
               (setq i (caar asked))
               (lin:trim (cdar asked))
               (setq asked (cdr asked))
             )
             (princ "\n  Already at the first item.")
           ))
          ((eq v 'LIN-STOP) (setq i n))
          (T
           (setq asked (cons (cons i mark) asked)
                 i     (1+ i))
          )
        )
      )
    )
  )
)

;;; ------------------------------------------------------------------
;;; Checklist stages (one question each; heads travel with the first
;;; question under them so a Back re-prints the section header too)
;;; ------------------------------------------------------------------

(defun lin:st-read ()
  (lin:head "Job Review")
  (lin:check "Read all WSN (White Screen Notes), Notes from Merlin, and Customer Info" nil)
)

(defun lin:st-gate (/ v)
  (setq v (lin:yesno "Does this job actually require a Tech drawing?" T))
  (cond
    ((eq v 'LIN-BACK) v)
    ((null v)
     (lin:log "")
     (lin:log ">> Job does NOT require a Tech drawing - stopping checklist.")
     'LIN-STOP)
    (T v)
  )
)

(defun lin:st-wallht-chk ()
  (lin:head "Walls & Depth")
  (lin:check "Verify Finished Wall Ht & Pool Depth" T)
)

(defun lin:st-wallht-val ()
  (lin:value "Finished Wall Ht (single value, or \"Varies\")" T)
)

(defun lin:st-glp ()
  (lin:head "Liner Pattern & Bead")
  (lin:check "Place liner pattern block (GLP) - delete \"Not Supplied\" text" T)
)

(defun lin:st-bead ()
  (lin:value "Pool bead type / overlap (AG, etc.)" T)
)

(defun lin:st-perim ()
  (lin:head "Dimensions & Orientation")
  (lin:check "Pool perimeter & overall dims" T)
)

(defun lin:st-orient ()
  (lin:check "Verify orientation: Shallow end to the RIGHT of page" T)
)

(defun lin:st-crossdims ()
  ;; Report ALL cross dimensions provided by the customer.
  (princ "\nReport ALL cross dimensions provided by customer.")
  (princ "\n  Enter each as label=value (e.g. A-C=24'6\"), or NA. Blank line to finish.")
  (lin:log "[x] Cross dimensions provided by customer:")
  (lin:crossdims T)
)

(defun lin:st-corners ()
  (lin:head "Corners")
  (lin:check "Pool corners with dimensions" T)
)

(defun lin:st-mfgrs ()
  (lin:check (strcat "Watch for special mfgrs: Esther Williams (3x3, 5x5) "
                     "or Foxx (37\" Deep)") T)
)

(defun lin:st-cove ()
  (lin:head "Special Bottom Conditions")
  (lin:yesno "Does the shallow end have a Cove?" T)
)

(defun lin:st-ledge ()
  (lin:yesno "Does the pool have a Safety Ledge?" T)
)

(defun lin:st-depths ()
  (lin:yesno "Did the customer provide various depths for the bottom?" T)
)

(defun lin:st-sideview ()
  (lin:yesno "Does the pool require a side view?" T)
)

(defun lin:st-hopper ()
  (lin:head "Bottom & Trowel Lines")
  (lin:yesno "Are hopper corners radius?" T)
)

(defun lin:st-trowel ()
  (lin:check "Draw trowel lines accurately" T)
)

(defun lin:st-fib (/ v)
  (lin:head "Steps / Bench - Fiberglass")
  (setq v (lin:yesno "Are steps / bench Fiberglass?" T))
  (if (not (eq v 'LIN-BACK)) (setq fib v))
  v
)

(defun lin:st-fib-note ()
  (lin:check "Place FGS note or draw step outline if dimensions were provided" T)
)

(defun lin:st-fib-type ()
  (lin:ask "Is the step Straight or Radius? (ask if not given)"
           "Straight Radius" T)
)

(defun lin:st-vin (/ v)
  (lin:head "Steps / Bench - Vinyl-Covered")
  (setq v (lin:yesno "Are steps / bench Vinyl-covered?" T))
  (if (not (eq v 'LIN-BACK)) (setq vin v))
  v
)

(defun lin:st-vin-corner ()
  (lin:check "Verify step corner type & dimensions" T)
)

(defun lin:st-vin-attach ()
  (lin:check "Place Step Attachment block" T)
)

(defun lin:st-vin-attype ()
  (lin:yesno "Is the attachment type provided?" T)
)

(defun lin:st-vin-side ()
  (lin:check "Place side views for all steps and benches" T)
)

(defun lin:st-final ()
  (lin:head "Final")
  (lin:check "Did you scale the titleblock?  ** REDVIEW! **" T)
)

;;; ------------------------------------------------------------------
;;; Checklist
;;; ------------------------------------------------------------------

(defun c:LINCHECK (/ *error* fib vin)
  ;; a walker: it changes no setting and opens no undo group, so the
  ;; handler's whole job is to keep a cancel from printing a raw
  ;; AutoLISP message at the user (STANDARDS section 5)
  (defun *error* (msg)
    (if (and msg (not (wcmatch (strcase msg)
                               "*BREAK*,*CANCEL*,*QUIT*,*EXIT*")))
        (princ (strcat "\nLINCHECK error: " msg)))
    (if lzd:report (lzd:report "LINCHECK" *lincheck-version* msg))
    (princ))
  (if lzd:begin (lzd:begin "LINCHECK" *lincheck-version*))

  (setq *lin:log* nil fib nil vin nil)
  (princ "\n--- Liner Tech Drawing Checklist ---")
  (princ "\nWork down each item; the report prints at the end.")
  (princ "\n(after the first item, Back re-asks the previous one)\n")
  (lin:stages (list
    (cons nil  'lin:st-read)
    (cons nil  'lin:st-gate)
    (cons nil  'lin:st-wallht-chk)
    (cons nil  'lin:st-wallht-val)
    (cons nil  'lin:st-glp)
    (cons nil  'lin:st-bead)
    (cons nil  'lin:st-perim)
    (cons nil  'lin:st-orient)
    (cons nil  'lin:st-crossdims)
    (cons nil  'lin:st-corners)
    (cons nil  'lin:st-mfgrs)
    (cons nil  'lin:st-cove)
    (cons nil  'lin:st-ledge)
    (cons nil  'lin:st-depths)
    (cons nil  'lin:st-sideview)
    (cons nil  'lin:st-hopper)
    (cons nil  'lin:st-trowel)
    (cons nil  'lin:st-fib)
    (cons 'fib 'lin:st-fib-note)
    (cons 'fib 'lin:st-fib-type)
    (cons nil  'lin:st-vin)
    (cons 'vin 'lin:st-vin-corner)
    (cons 'vin 'lin:st-vin-attach)
    (cons 'vin 'lin:st-vin-attype)
    (cons 'vin 'lin:st-vin-side)
    (cons nil  'lin:st-final)
  ))
  (lin:report)
  (if lzd:end (lzd:end "LINCHECK"))
  (princ)
)

;; Collect the customer's cross dimensions (loop until a blank entry).
;; B (Back) removes the last entry, or - when there is none and back is
;; non-nil - leaves the stage with LIN-BACK.
(defun lin:crossdims (back / entry n done)
  (setq n 0 done nil)
  (while (not done)
    (setq entry (getstring T (strcat "\n  Cross dim (label=value / NA"
                                     ", B = back, blank to finish): ")))
    (if lzd:ask (lzd:ask (getvar "LASTPROMPT") entry) entry)
    (cond
      ((lin:back-word entry)
       (if (> n 0)
         (progn
           (setq n (1- n))
           (lin:trim (1- (length *lin:log*)))
           (princ "\n  Stepping back one cross dim.")
         )
         (if back
           (setq done 'LIN-BACK)
           (princ "\n  Already at the first cross dim.")
         )
       ))
      ((= entry "") (setq done T))
      (T (setq n (1+ n)) (lin:log (strcat lin:*indent* entry)))
    )
  )
  (if (eq done 'LIN-BACK)
    'LIN-BACK
    (progn (if (= n 0) (lin:log (strcat lin:*indent* "(none provided)"))) n)
  )
)

;; Print the collected report.
(defun lin:report ()
  (princ "\n\n")
  (princ lin:*rule*)
  (princ (strcat "\n" lin:*title*))
  (princ (strcat "\n" lin:*rule*))
  (foreach line *lin:log*
    (princ (strcat "\n" line))
  )
  (princ (strcat "\n" lin:*rule*))
  (princ "\n")
  (princ)
)

(defun c:LINCHECKVER ()
  (princ (strcat "\nLINCHECK " *lincheck-version*))
  (princ))

;; -------------------- self tests ---------------------------------------
;; What LAZDIAG runs on the drafter's machine after this tool fails, and
;; writes into the report: the tool's own helpers on inputs whose answers
;; are KNOWN, so the report says whether the arithmetic was sound where
;; it ran.  (label expression expected) passes when the value is equal
;; to expected (to 1e-6); (label expression) passes when it is not nil,
;; and the value is written down either way.  Nothing here may prompt,
;; draw or (command): it is evaluated from inside *error*.
;; tests/test_selftests.py runs every entry in the VM at both tiers.
(defun lin:selftests ()
  (list
    (list "back-word takes a lower-case b"
          '(if (lin:back-word "b") T)                       T)
    (list "back-word takes the whole word Undo, case-blind"
          '(if (lin:back-word "Undo") T)                    T)
    (list "back-word refuses a note that only starts with one"
          '(lin:back-word "backfill")                       nil)
    (list "back-word refuses an empty answer (Enter)"
          '(lin:back-word "")                               nil)
    (list "every piece a report line is built from is text"
          '(= (type (strcat lin:*tick* lin:*note-sep* lin:*ans-sep* lin:*indent*
                            lin:*head-in* lin:*head-out*
                            lin:*head-echo-in* lin:*head-echo-out*))
              'STR)                                          T)
    (list "the previous-answer memory is empty or a list"
          '(or (null *lin:prev*) (listp *lin:prev*))        T)
    (list "the report box lines up: rule and title are the same width"
          '(= (strlen lin:*rule*) (strlen lin:*title*))    T)
    (list "the Back words are a list of strings; value is how many"
          '(if (and lin:*back-words*
                    (not (member nil (mapcar '(lambda (w) (= (type w) 'STR))
                                             lin:*back-words*))))
             (length lin:*back-words*)))))

(foreach c '("LINCHECK")
  (setq *calofin-selftests*
        (cons (cons c 'lin:selftests) *calofin-selftests*)))

;; Quiet inside the whole build: LAZPASS.lsp and
;; CALOFIN-LOADER.lsp set the flag while they load their members,
;; because one file's greeting is a greeting and sixty-three of
;; them is a wall the drafter scrolls past in every drawing they
;; open.  APPLOADed alone the flag is nil and this prints, which
;; is the one time somebody wants to be told.  CALVER reports the
;; whole roster whenever it is asked.
(if (not *calofin-quiet*)
  (princ (strcat "\nLINCHECK " *lincheck-version*
                 " loaded. Type LINCHECK to run the liner checklist.")))
(princ)
